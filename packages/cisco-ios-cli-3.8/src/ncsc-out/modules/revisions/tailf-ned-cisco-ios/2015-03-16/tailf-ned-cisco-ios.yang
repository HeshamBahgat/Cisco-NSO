module tailf-ned-cisco-ios {
  // Generated by yanger -t ncs
  tailf:mount-id cisco-ios-cli-3.8:cisco-ios-cli-3.8;
  tailf:ncs-device-type "cli-ned";

  namespace "urn:ios";
  prefix ios;

  import tailf-common {
    prefix tailf;
  }
  import ietf-inet-types {
    prefix inet;
  }
  import ietf-yang-types {
    prefix yang;
  }
  import "cisco-ios-cli-3.8" {
    prefix "cisco-ios-cli-3.8";
  }
  import tailf-ncs {
    prefix ncs;
  }

  revision 2015-03-16 {
    description
      "3.8.0
       Enhancements:
       Support for NCS-3.4.
       Removed all specific snmp-server enable traps. Replaced by generic list.
       Additions to the YANG model:
       csdb tcp|udp|icmp|session
       snmp-server queue-limit notification-host
       router bgp * / bgp additional-paths
       interface pseudowire * / service-policy
       interface * / xconnect encapsulation / mtu
       interface * / switchport private-vlan
       interface * / wrr-queue dscp-map *
       interface * / priority-queue dscp-map *
       interface * / priority-queue queue-limit
       Merged cloudvpn-develop (commit: 13d3dc9 from 2015-03-05):
       Enhancements:
        Added license command under live-status, e.g.:
         devices device csr1000v live-status exec license smart deregister
        Implemented support for 'default' exec commands in config mode, e.g.:
         devname(config) default crypto ikev2 authorization policy
        Additions to the YANG model:
         aaa attribute list *
         class-map * / match protocal attribute category *
         crypto dynamic-map *
         crypto ikev2 profile * / aaa authorization group
         crypto ikev2 authorization policy *
         crypto ikev2 keyring * / peer * / identity
         crypto ikev2 profile * / nat keepalive
         crypto ikev2 profile * / match fvrf
         crypto isakmp nat
         crypto isakmp profile *
         crypto keyring *
         crypto map * ipsec-isakmp|ipsec-manual
         crypto logging ikev2
         ip dhcp pool * / vrf
         ip nat inside source route-map *
         ip sla * / * / vrf
         ip ssh stricthostkeycheck
         logging source-interface * vrf
         pnp startup-vlan
         pnp tag
         .. and more minor additions ..
       Corrections:
        Remove ip sla entry before modifying it upon error from device.
        Modifications in the YANG model:
         aaa accounting exec *
         crypto ikev2 profile * / authentication
         crypto isakmp policy * / encryption
         crypto map *
         interface * / ipv6 nd ra suppress
         interface * / ntp multicast client
         ip nat outside source
         pnp profile * / transport
         .. and more minor various bugfixes ..
       Corrections:
       Changed router * / passive-interface from a leaf to a list.
       Fixed deletion of 'no passive-interface' on router config.
       Bugfixed router eigrp and router rip.
       Fixed order dependancy between service instance and ethernet evc.
      ";
  }
  revision 2015-03-04 {
    description
      "3.7.0.3
       Enhancements:
       Additions to the YANG model:
        interface * / l2protocol-tunnel lldp
        interface * / l2protocol point-to-point
       Corrections:
       Fixed dependency issues:
       On Catalyst devices there is a dependency between:
        interface * / switchport and interface * / l2protocol-tunnel.
       The config under l2protocol-tunnel must always be deleted before
        switchport is deleted.
       The same dependency also applies to
        interface * / switchport and interface * / service.
      ";
  }
  revision 2015-02-19 {
    description
      "3.7.0.1
       Enhancements:
       Added interface BRI and Async basic configuration.
       Populated router bgp * / peer-policy & peer-session lists.
       Expanded policy-map class random-detect config.
       Corrections:
       Numerous router rip,ospf,ospfv3,isis and bgp bug fixes.
      ";
  }
  revision 2015-02-13 {
    description
      "3.6.0
       Enhancements:
       Corrections:
       Do not delete config in set-hook's if talking Netconf.
      ";
  }
  revision 2015-02-11 {
    description
      "3.5.0.7
       Enhancements:
       Corrections:
       Improved expect of sent commands at login, solving login problems
        on asr903 device.
       Bugfixed copy, reload and traceroute commands under live-status.
       Removed auto-create of vlan when configuring bridge-domain.
       Fixed order dependancy problem with service-policy.
      ";
  }
  revision 2015-02-09 {
    description
      "3.5.0.6
       Enhancements:
       Expanded ethernet cfm config.
       Added aaa accounting update periodic config.
       Added interface ip ospf authentication config.
       Added numerous ASR903/ASR920 L2 config.
       Added ip tcp mss config.
       Added copy, reload and traceroute commands under live-status.
       Corrections:
       Remodelled ethernet cfm service evc to list.
      ";
  }
  revision 2015-01-28 {
    description
      "3.5.0.5
       Enhancements:
       Expanded cable config.
       Support for vlan ranges in service instance encapsulation dot1q config.
       Added generic snmp-server enable traps list accepting all entries.
       Expanded router lisp config.
       Corrections:
       Restored router bgp / address family ipv6 configuration mode.
       Fixed banner config bug which ended in additional 'C' in message.
      ";
  }
  revision 2015-01-12 {
    description
      "3.5.0.4
       Enhancements:
       Added support for ip explicit-path identifier.
       Added cable modulation-profile, tag, service, qos, filter, submgmt,
         logging, sflog, docsis30-voice, util-interval, clock, dsg and
         load-balance config.
       Added basic interface Cable config.
       Corrections:
       Reworked ip explicit-path to support delete/modify of entries by making
        index value for next-address and exclude-address mandatory.
      ";
  }
  revision 2014-12-19 {
    description
      "3.5.0.3
       Enhancements:
       Added support for aaa accounting connection. (RT17164)
       Added support for sub-interface Port-channel #.#
       Automatically delete channel-group and shutdown dependant ethernet
        interfaces when Port-channel interface is deleted. (RT17422 / #12304)
       General config expansion for improved MPLS and L2VPN support.
       Corrections:
       Reworked aaa accounting lists method options. (RT17164)
       Fixed bug in router ospf * / redistribute bgp|eigrp config.
       Fixed bug with setting banners. (RT17300 / #12300). Removed
        delimiter config to avoid compare config diff.
       Fixed ordering problem when deleting switchport mode trunk and
        switchport trunk encapsulation dot1q. (RT17421 / #12312)
       Do not delete switchport container when member leaves are deleted.
      ";
  }
  revision 2014-12-10 {
    description
      "3.5.0.2
       Enhancements:
       Added basic support for cable l2vpn and cable  dot1q-vc-map
       Corrections:
      ";
  }
  revision 2014-12-03 {
    description
      "3.5.0.1
       Enhancements:
       Corrections:
       Reworked aaa authentication and authorization lists method options.
        Non-backwards compatible 'aaa authorization network' model.
      ";
  }
  revision 2014-12-01 {
    description
      "3.4.0
       Enhancements:
       Support for NCS-3.3.
       YANG data model updates: mls qos map ip-prec-dscp (R17250).
       Added ping and clear exec commands under live-status, e.g.:
        devices device c7200 live-status exec ping 192.168.1.1
        devices device c7200 live-status exec clear ppp queues
       Corrections:
      ";
  }
  revision 2014-11-19 {
    description
      "3.3.0.1
       Enhancements:
       Added basic support for new L2VPN config, YANG data model adds:
        interface pseudowire
        l2vpn xconnect context
       Added route-map / continue config.
       Updated for new NCS features 'trim-defaults' which hides config
        set to default values.
       Corrections:
       Fixed problem with route-map * / set community reordering values.
       Remove ip prefix sequence entry before modifying it.
       Fixed problem with deleting ip vrf *, bad prefix used.
       Ignore incomplete crypto profile warning.
      ";
  }
  revision 2014-11-05 {
    description
      "3.2.0
       Master merge and release.
      ";
  }
  revision 2014-11-04 {
    description
      "3.1.4.4
       Enhancements:
       Added ncs java log and ned trace print of TransactionId.
       Added crypto ssl support.
       Added crypto pki enroll <name> command.
       Added crypto pki trustpoint create&remove hook for automatic creation
        and removal of corresponding pki certificate chain.
       Added pnp profile config.
       Cleaned up router rip config.
       Corrections:
       Fixed policy-map / class / bandwidth percent modification bug.
       Fixed dependency between interface switchport and service instance
        delete.
       Removed 'no switchport' lines on all device types.
       Bugfixed ipv6 route.
       Bugfixed snmp-server host vrf.
       Bugfixed router ospf vrf.
      ";
  }
  revision 2014-10-24 {
    description
      "3.1.4.3
       Enhancements:
       General config expansion in multiple areas.
       Added l3vpn encapsulation ip config.
       Added track config.
       Simplified event manager applet / action to support all commands.
       Expanded ip pim, using grouping from ip pim vrf *.
       Corrections:
       Bugfixed policy-map / class / random-detect precedence-based.
        In order to delete and create two different xxx-based configs
        in the same transaction, ncs-3.2.2.2 or newer is required.
      ";
  }
  revision 2014-10-21 {
    description
      "3.1.4.2
       Enhancements:
        Added connect command.
        Expanded ip mobile router config.
        Added controller Cellular *
        Implemented support for 'crypto pki server <cs-lbl> [rollover [cancel]]
         exec commands in config mode.
        Introduced 'tailfned police' options: cirmode|cirflat|bpsflat|numflat
        Added bridge-domain hook for auto creating vlans with same <id>.
       Corrections:
        Repaired support for multiple certificates.
        Only add/delete ip route-cache with switchport mods for me340x devices.
        Improved access-list patterns (removed no.*) to only add valid entries.
        Bugfixed policy-map / class / random-detect dscp and discard.
        Reworked and bugfixed all routers 'distribute-list' lists.
      ";
  }
  revision 2014-10-13 {
    description
      "3.1.4.1
       Enhancements:
        Added tailfned config container for device specific config control.
        Added REMOVE hooks on /ip/vrf and /vrf/definition lists to
         automatically delete routes on same vrf.
        Added 'backup peer' and 'synchronous mode' interface commands.
        Disabled device-specific policy-map/class/police config.
        Added support for c7350 policy-map/class/police command syntax.
        Reworked interface switchport support with special support for c7600.
       Corrections:
        Fixed problem with 'no media-type' clearing duplex on interface.
        Fixed ip domain-name, domain-list and domain-lookup sync from device.
        Minor update for XE BGP neighbor remote-as leaf value.
        Reworked xconnect in interface and interface service instance.
      ";
  }
  revision 2014-09-30 {
    description
      "3.1.3.2
       Minor update for XE BGP neighbor remote-as leaf value.
      ";
  }
  revision 2014-09-26 {
    description
      "3.1.3.1
       Enhancements:
        Expanded mobile ip and dialer config.
        Expanded LISP config.
        Expanded crypto config.
       Corrections:
        Change argument to setTimeout() from seconds to millisecs in
         NED Java code due to NCS NED API change.
      ";
  }
  revision 2014-09-24 {
    description
      "3.1.2.1
       Enhancements:
       Implemented support for 'show' commands under live-status exec, e.g.
        devices device c7200 live-status exec show running-config brief
       Implemented support for 'crypto key' exec commands in config mode.
       Expanded crypto settings.
       Reviewed and reordered /ipv6 config.
       Reworked 'ipv6 route' list config to support all interfaces.
       Reviewed and reordered /aaa config.
       Numerous order rearrangements made from testing on a c7200.
       Corrections:
       Reviewed, reordered and bugfixed /service config.
       Reviewed, reordered and bugfixed /vrf definition config.
       Reviewed, reordered and bugfixed /ip config.
      ";
  }
  revision 2014-09-19 {
    description
      "3.1.1.1
       Enhancements:
       Added basic crypto isakmp and crypto ipsec support.
       Moved policy-map description to before class.
       Corrections:
       Fixed order dependency issues in policy-map/class/police when switching
         between an aggregate and policer.
         NOTE: Requires support for 'tailf:cli-trigger-on-set' option.
       Bugfixed mls qos srr-queue.
      ";
  }
  revision 2014-09-16 {
    description
      "3.0.3.3
       Enhancements:
       Expanded mls qos srr-queue.
       Corrections:
      ";
  }
  revision 2014-09-15 {
    description
      "3.0.3.2
       Enhancements:
       Corrections:
       Moved policy-map/class/police aggregate out of police choice.
      ";
  }
  revision 2014-08-18 {
    description
      "3.0.3.1
       Enhancements:
       Corrections:
       Display 'switchport port-security' on a separate line.
       Added cli-show-no to shutdown leaf in in order to be able to bring
         down (send 'no shutdown') interface after creation.
      ";
  }
  revision 2014-08-07 {
    description
      "Added support for 'sequence' keyword to ipv6 access-list
       Added interface-ethernet-grouping to Port-channel interface
       Added error check: 'please remove the service-policy on the zone-pair'
       Added error check: 'in use, cannot'
       Moved table-map,mls,policer,class-map and policy-map to before interface
       Remodelled interface/ip access-group to support both in and out entries
       Removed 'ntp clock-period' because auto changed by device
      ";
  }
  revision 2014-07-02 {
    description
      "Fixed issue with remove before change on the following leafs:
       interface * / service-policy / input
       interface * / service-policy / output
      ";
  }
  revision 2014-06-27 {
    description
      "Implemented basic crypto ikev2 config support.
       Added other single config items in various areas.
      ";
  }
  revision 2014-06-26 {
    description
      "Implemented basic VoIP config support.
       Added other single config items in various areas.
      ";
  }
  revision 2014-06-19 {
    description
      "Added minimal router eigrp support.
       Populated ip dhcp pool config.
       Reworked card config.
       Added other single config items in various areas.
      ";
  }
  revision 2014-06-16 {
    description
      "Expanded ip pim vrf config.
      ";
  }
  revision 2014-06-13 {
    description
      "Added storm-control action shutdown|trap config items.
       Added Ethernet interface.
       Expanded Tunnel interface config.
       Added minimal ip explicit-path config.
       Added minimal pseudowire-class config.
       Added ip flow-aggregation cache config.
       Added other single config items in various areas.
      ";
  }
  revision 2014-06-11 {
    description
      "Additional config supported for PPP/Ethernet/Frame Relay Bundled Service
          and Ethernet MPLS L2VPN.
       Added MFR - Multilink Frame Relay bundle - (sub)interface.
       Added Tunnel interface.
      ";
  }
  revision 2014-05-26 {
    description
      "Implemented full support for NTP configuration, modified/expanded:
          ntp and interface / ntp commands.
       Implemented full support for SNTP configuration, implemented:
          sntp command.
      ";
  }
  revision 2014-05-21 {
    description
      "Implemented full support for DNS configuration, modified/expanded:
          ip host, ip name-server and ip domain commands.
      ";
  }
  revision 2014-05-09 {
    description
      "Added support for match config in router bgp redistribute ospf list
      ";
  }
  revision 2014-04-29 {
    description
      "Expanded various config, mainly in routing areas
       Added config error check for 'not configured'
       Added support for interface service instance config
      ";
  }
  revision 2014-04-04 {
    description
      "Added basic support for Locator/ID Separation Protocol (LISP)
      ";
  }
  revision 2014-02-12 {
    description
      "Fixed show live-status for interfaces.
      ";
  }
  revision 2014-02-10 {
    description
      "[ip] vrf forwarding fix on interfaces.
      ";
  }
  revision 2014-02-06 {
    description
      "Fixed interface 'no ip address' bug
       Preliminary IOS XE support work
       Added 'interface Virtual-Template *'
       Added 'interface * / peer default ip' support'
       Expanded 'interface * / ppp' support'
       Merged interface encapsulation config (API change)
       Merged all fixes/adds in confd-4.3 ios-xe between r59179 and r65905.
      ";
  }
  revision 2014-01-30 {
    description
      "Merged from confd-5.0.
       Expanded 'ip nat'
      ";
  }
  revision 2014-01-28 {
    description
      "Fixed bugs in 'ip route'. API changes to list due to variable
       number of keys.
      ";
  }
  revision 2013-12-09 {
    description
      "Police and policer work
      ";
  }
  revision 2013-11-25 {
    description
      "API-cleaning for Juniper and bugfixes
       Made cir,bc and be keywords mandatory in policy-map/class police
      ";
  }
  revision 2013-11-12 {
    description
      "Rewrote police-map/class police command to support more combos";
  }
  revision 2013-10-14 {
    description
      "Merged all yang files to one file.";
  }
  revision 2013-08-15 {
    description
      "Added switchport commands
       Added spanning-tree top level commands
       Added a number of SNMP traps
       Added support for OSPFv3
       Added support for IPv6 prefix-lists
      ";
  }
  revision 2013-08-08 {
    description
      "Added support for Cisco 7600 constructs.";
  }
  revision 2013-06-25 {
    description
      "Renamed YANG module, submodule and namespace.";
  }
  revision 2013-04-18 {
    description
      "Restructuring using new file ios-common0.yang and
        augment(s) in order to fix order dependencies.
       Added model constructs for Cisco 2800.
      ";
  }

  typedef ipsec-window-size-type {
    type enumeration {
      enum "1024" {
        tailf:info
          "Window size of 1024";
      }
      enum "128" {
        tailf:info
          "Window size of 128";
      }
      enum "256" {
        tailf:info
          "Window size of 256";
      }
      enum "512" {
        tailf:info
          "Window size of 512";
      }
      enum "64" {
        tailf:info
          "Window size of 64 (default)";
      }
    }
  }

  typedef aaa-group-type {
    type union {
      type string {
        tailf:info
          "WORD;;Server-group name";
      }
      type enumeration {
        enum "ldap" {
          tailf:info
            "Use list of all LDAP hosts.";
        }
        enum "radius" {
          tailf:info
            "Use list of all Radius hosts.";
        }
        enum "tacacs+" {
          tailf:info
            "Use list of all Tacacs+ hosts.";
        }
      }
    }
  }

  typedef aaa-accounting-name-type {
    type union {
      type enumeration {
        enum "default" {
          tailf:info
            "The default accounting list.";
        }
      }
      type string {
        tailf:info
          "WORD;;Named Accounting list (max 31 characters).";
        length "1..31";
      }
    }
  }

  typedef aaa-authentication-name-type {
    type union {
      type enumeration {
        enum "default" {
          tailf:info
            "The default authentication list.";
        }
      }
      type string {
        tailf:info
          "WORD;;Named authentication list (max 31 characters).";
        length "1..31";
      }
    }
  }

  typedef aaa-authorization-name-type {
    type union {
      type enumeration {
        enum "default" {
          tailf:info
            "The default authorization list.";
        }
      }
      type string {
        tailf:info
          "WORD;;Named authorization list (max 31 characters).";
        length "1..31";
      }
    }
  }

  typedef crypto-ipsec-transform-type {
    type enumeration {
      enum "ah-md5-hmac" {
        tailf:info
          "AH-HMAC-MD5 transform";
      }
      enum "ah-sha-hmac" {
        tailf:info
          "AH-HMAC-SHA transform";
      }
      enum "ah-sha256-hmac" {
        tailf:info
          "AH-HMAC-SHA256 transform";
      }
      enum "ah-sha384-hmac" {
        tailf:info
          "AH-HMAC-SHA384 transform";
      }
      enum "ah-sha512-hmac" {
        tailf:info
          "AH-HMAC-SHA512 transform";
      }
      enum "comp-lzs" {
        tailf:info
          "IP Compression using the LZS compression algorithm";
      }
      enum "esp-3des" {
        tailf:info
          "ESP transform using 3DES(EDE) cipher (168 bits)";
      }
      enum "esp-aes" {
        tailf:info
          "ESP transform using AES cipher";
      }
      enum "esp-des" {
        tailf:info
          "ESP transform using DES cipher (56 bits)";
      }
      enum "esp-gcm" {
        tailf:info
          "ESP transform using GCM";
      }
      enum "esp-gmac" {
        tailf:info
          "ESP transform using GMAC cipher";
      }
      enum "esp-md5-hmac" {
        tailf:info
          "ESP transform using HMAC-MD5 auth";
      }
      enum "esp-null" {
        tailf:info
          "ESP transform w/o cipher";
      }
      enum "esp-seal" {
        tailf:info
          "ESP transform using SEAL cipher (160 bits)";
      }
      enum "esp-sha-hmac" {
        tailf:info
          "ESP transform using HMAC-SHA auth";
      }
      enum "esp-sha256-hmac" {
        tailf:info
          "ESP transform using HMAC-SHA256 auth";
      }
      enum "esp-sha384-hmac" {
        tailf:info
          "ESP transform using HMAC-SHA384 auth";
      }
      enum "esp-sha512-hmac" {
        tailf:info
          "ESP transform using HMAC-SHA512 auth";
      }
    }
  }

  typedef crypto-ipsec-transform-bits-type {
    type enumeration {
      enum "128" {
        tailf:info
          "128 bit keys.";
      }
      enum "192" {
        tailf:info
          "192 bit keys.";
      }
      enum "256" {
        tailf:info
          "256 bit keys.";
      }
    }
  }

  typedef police-burst-type {
    type uint32 {
      tailf:info
        "<1000-512000000>;;Burst bytes";
      range "1000..512000000";
    }
  }

  typedef police-bps-type {
    type uint64 {
      tailf:info
        "<8000-64000000000>;;Bits per second";
      range "8000..64000000000";
    }
  }

  typedef police-pps-bps-type {
    type enumeration {
      enum "pps" {
        tailf:info
          "pps  Treat 'rate' value in packets-per-second";
      }
      enum "bps" {
        tailf:info
          "pps  Treat 'rate' value in bytes-per-second";
      }
    }
  }

  typedef police-packets-bytes-type {
    type enumeration {
      enum "packets" {
        tailf:info
          "Treat 'burst' value as packets";
      }
      enum "bytes" {
        tailf:info
          "Treat 'burst' value as bytes";
      }
    }
  }

  typedef operator-type {
    type enumeration {
      enum "eq" {
        tailf:info
          "Equal to";
      }
      enum "ge" {
        tailf:info
          "Greater than or equal to";
      }
      enum "gt" {
        tailf:info
          "Greater than";
      }
      enum "le" {
        tailf:info
          "Less than or equal to";
      }
      enum "lt" {
        tailf:info
          "Less than";
      }
      enum "ne" {
        tailf:info
          "Not equal to";
      }
    }
  }

  typedef logging-level-type {
    type union {
      type uint16 {
        tailf:info
          "<0-7>;;Logging severity level";
        range "0..7";
      }
      type enumeration {
        enum "alerts" {
          tailf:info
            "Immediate action needed (severity=1)";
        }
        enum "critical" {
          tailf:info
            "Critical conditions (severity=2)";
        }
        enum "debugging" {
          tailf:info
            "Debugging messages (severity=7)";
        }
        enum "emergencies" {
          tailf:info
            "System is unusable (severity=0)";
        }
        enum "errors" {
          tailf:info
            "Error conditions (severity=3)";
        }
        enum "informational" {
          tailf:info
            "Informational messages (severity=6)";
        }
        enum "notifications" {
          tailf:info
            "Normal but significant conditions (severity=5)";
        }
        enum "warnings" {
          tailf:info
            "Warning conditions (severity=4)";
        }
      }
    }
  }

  typedef authentication-level-type {
    type enumeration {
      enum "level-1" {
        tailf:info
          "ISIS authentication for level-1";
      }
      enum "level-2" {
        tailf:info
          "ISIS authentication for level-2";
      }
    }
  }

  typedef isis-level-type {
    type enumeration {
      enum "level-1" {
        tailf:info
          "Level-1 only";
      }
      enum "level-1-2" {
        tailf:info
          "Level-1-2";
      }
      enum "level-2" {
        tailf:info
          "Level-2 only";
      }
    }
  }

  typedef limit-dc-non-dc-type {
    type union {
      type uint32 {
        tailf:info
          "<1-255>;;The maximum number of retransmissions";
        range "1..255";
      }
      type enumeration {
        enum "disable" {
          tailf:info
            "Disable the feature";
        }
      }
    }
  }

  typedef ospf-metric-type {
    type uint32 {
      tailf:info
        "<1-2>;;OSPF Link State type";
      range "1..2";
    }
  }

  typedef ospf-area-type {
    type union {
      type uint32 {
        tailf:info
          "<0-4294967295>;;OSPF area ID as a decimal value";
        range "0..4294967295";
      }
      type inet:ipv4-address {
        tailf:info
          "A.B.C.D;;OSPF area ID in IP address format";
      }
    }
  }

  typedef redist-ospf-external-type {
    type enumeration {
      enum "1" {
        tailf:info
          "Redistribute external type 1 routes";
      }
      enum "2" {
        tailf:info
          "Redistribute external type 2 routes";
      }
    }
  }

  typedef prec_value-type {
    type union {
      type uint8 {
        tailf:info
          "<0-7>;;new precedence";
        range "0..7";
      }
      type enumeration {
        enum "cos" {
          tailf:info
            "Set packet precedence from cos";
          value 1001;
        }
        enum "dscp" {
          tailf:info
            "Set packet precedence from dscp";
          value 1002;
        }
        enum "exp" {
          tailf:info
            "Set packet precedence from exp";
          value 1003;
        }
        enum "precedence" {
          tailf:info
            "Set packet precedence from precedence";
          value 1004;
        }
      }
    }
  }

  typedef exp_value-type {
    type union {
      type uint8 {
        tailf:info
          "<0-7>;;new exp";
        range "0..7";
      }
      type enumeration {
        enum "cos" {
          tailf:info
            "Set packet exp from cos";
          value 1001;
        }
        enum "dscp" {
          tailf:info
            "Set packet exp from dscp";
          value 1002;
        }
        enum "exp" {
          tailf:info
            "Set packet exp from exp";
          value 1003;
        }
        enum "precedence" {
          tailf:info
            "Set packet exp from precedence";
          value 1004;
        }
      }
    }
  }

  typedef qos_value-type {
    type union {
      type uint8 {
        tailf:info
          "<0-99>;;new qos-group";
        range "0..99";
      }
      type enumeration {
        enum "cos" {
          tailf:info
            "Set packet qos from cos";
          value 1001;
        }
        enum "dscp" {
          tailf:info
            "Set packet qos from dscp";
          value 1002;
        }
        enum "exp" {
          tailf:info
            "Set packet qos from exp";
          value 1003;
        }
        enum "precedence" {
          tailf:info
            "Set packet qos from precedence";
          value 1004;
        }
      }
    }
  }

  typedef cos_value-type {
    type union {
      type uint8 {
        tailf:info
          "<0-7>;;new cos value";
        range "0..7";
      }
      type enumeration {
        enum "cos" {
          tailf:info
            "Set packet cos from cos";
          value 1001;
        }
        enum "dscp" {
          tailf:info
            "Set packet cos from dscp";
          value 1002;
        }
        enum "exp" {
          tailf:info
            "Set packet cos from exp";
          value 1003;
        }
        enum "precedence" {
          tailf:info
            "Set packet cos from precedence";
          value 1004;
        }
      }
    }
  }

  typedef precedence-type {
    type union {
      type uint8 {
        tailf:info
          "<0-7>;;Precedence value";
        range "0..7";
      }
      type enumeration {
        enum "critical" {
          tailf:info
            "Set packets with critical precedence (5)";
        }
        enum "flash" {
          tailf:info
            "Set packets with flash precedence (3)";
        }
        enum "flash-override" {
          tailf:info
            "Set packets with flash override precedence (4)";
        }
        enum "immediate" {
          tailf:info
            "Set packets with immediate precedence (2)";
        }
        enum "internet" {
          tailf:code-name "prec_internet";
          tailf:info
            "Set packets with internetwork control precedence (6)";
        }
        enum "network" {
          tailf:info
            "Set packets with network control precedence (7)";
        }
        enum "priority" {
          tailf:code-name "prec_priority";
          tailf:info
            "Set packets with priority precedence (1)";
        }
        enum "routine" {
          tailf:info
            "Set packets with routine precedence (0)";
        }
      }
    }
  }

  typedef dscp-type {
    type union {
      type uint8 {
        tailf:info
          "<0-63>;;Differentiated services codepoint value";
        range "0..63";
      }
      type enumeration {
        enum "af11" {
          tailf:info
            "Match packets with AF11 dscp (001010)";
          value 10011;
        }
        enum "af12" {
          tailf:info
            "Match packets with AF12 dscp (001100)";
          value 10012;
        }
        enum "af13" {
          tailf:info
            "Match packets with AF13 dscp (001110)";
          value 10013;
        }
        enum "af21" {
          tailf:info
            "Match packets with AF21 dscp (010010)";
          value 10021;
        }
        enum "af22" {
          tailf:info
            "Match packets with AF22 dscp (010100)";
          value 10022;
        }
        enum "af23" {
          tailf:info
            "Match packets with AF23 dscp (010110)";
          value 10023;
        }
        enum "af31" {
          tailf:info
            "Match packets with AF31 dscp (011010)";
          value 10031;
        }
        enum "af32" {
          tailf:info
            "Match packets with AF32 dscp (011100)";
          value 10032;
        }
        enum "af33" {
          tailf:info
            "Match packets with AF33 dscp (011110)";
          value 10033;
        }
        enum "af41" {
          tailf:info
            "Match packets with AF41 dscp (100010)";
          value 10041;
        }
        enum "af42" {
          tailf:info
            "Match packets with AF42 dscp (100100)";
          value 10042;
        }
        enum "af43" {
          tailf:info
            "Match packets with AF43 dscp (100110)";
          value 10043;
        }
        enum "cs1" {
          tailf:info
            "Match packets with CS1(precedence 1) dscp (001000)";
          value 10001;
        }
        enum "cs2" {
          tailf:info
            "Match packets with CS2(precedence 2) dscp (010000)";
          value 10002;
        }
        enum "cs3" {
          tailf:info
            "Match packets with CS3(precedence 3) dscp (011000)";
          value 10003;
        }
        enum "cs4" {
          tailf:info
            "Match packets with CS4(precedence 4) dscp (100000)";
          value 10004;
        }
        enum "cs5" {
          tailf:info
            "Match packets with CS5(precedence 5) dscp (101000)";
          value 10005;
        }
        enum "cs6" {
          tailf:info
            "Match packets with CS6(precedence 6) dscp (110000)";
          value 10006;
        }
        enum "cs7" {
          tailf:info
            "Match packets with CS7(precedence 7) dscp (111000)";
          value 10007;
        }
        enum "default" {
          tailf:info
            "Match packets with default dscp (000000)";
          tailf:code-name "dscp_default";
          value 1000;
        }
        enum "dscp" {
          tailf:info
            "Set packet dscp from dscp";
          value 1001;
        }
        enum "ef" {
          tailf:info
            "Match packets with EF dscp (101110)";
          value 1002;
        }
        enum "precedence" {
          tailf:info
            "Set packet dscp from precedence";
          value 1003;
        }
      }
    }
  }

  typedef spanning-tree-cost-type {
    type union {
      type uint32 {
        tailf:info
          "<1-200000000>;;Port path cost";
        range "1..200000000";
      }
      type enumeration {
        enum "auto" {
          tailf:code-name "spanning-tree-cost-type-auto";
          tailf:info
            "Determine cost based on media speed of this interface";
        }
      }
    }
  }

  typedef mst-cost-type {
    type union {
      type uint32 {
        tailf:info
          "<1-200000000>;;Port path cost";
        range "1..200000000";
      }
      type enumeration {
        enum "auto" {
          tailf:code-name "mst_cost_type_auto";
          tailf:info
            "Determine cost based on media speed of this interface";
        }
      }
    }
  }

  typedef ldp-discovery-address-type {
    type union {
      type enumeration {
        enum "interface" {
          tailf:code-name "ldp_interface";
          tailf:info
            "Use interface address for LDP transport address";
        }
      }
      type inet:ipv4-address {
        tailf:info
          "A.B.C.D;;IP address to use for LDP transport address";
      }
    }
  }

  typedef rip-offset-list-id-type {
    type union {
      type uint32 {
        tailf:info
          "<0-99>;;Access list of networks to apply offset (0 selects all networks)";
        range "0..99";
      }
      type uint32 {
        tailf:info
          "<1300-1999>;;Access list of networks to apply offset (expanded range)";
        range "1300..1999";
      }
      type string {
        tailf:info
          "WORD;;Access-list name";
      }
    }
  }

  typedef exp-ip-acl-type {
    type union {
      type uint16 {
        tailf:info
          "<1-199>;;IP access list";
        range "1..199";
      }
      type uint16 {
        tailf:info
          "<1300-2699>;;IP expanded access list";
        range "1300..2699";
      }
      type string {
        tailf:info
          "WORD;;Access-list name";
      }
    }
  }

  typedef ext-ip-acl-type {
    type union {
      type uint16 {
        tailf:info
          "<100-199>;;IP access list number";
        range "100..199";
      }
      type uint16 {
        tailf:info
          "<2000-2699>;;IP access list number (expanded range)";
        range "2000..2699";
      }
      type string {
        tailf:info
          "WORD;;Access-list name";
      }
    }
  }

  typedef ext-acl-type {
    type union {
      type uint16 {
        tailf:info
          "<100-199>;;Access list number";
        range "100..199";
      }
      type uint16 {
        tailf:info
          "<2000-2699>;;Access list number (expanded range)";
        range "2000..2699";
      }
      type string {
        tailf:info
          "WORD;;IP Named Extended Access list";
      }
    }
  }

  typedef std-ip-acl-type {
    type union {
      type uint16 {
        tailf:info
          "<1-99>;;Standard IP access list";
        range "1..99";
      }
      type uint16 {
        tailf:info
          "<1300-1999>;;Standard IP access list (expanded range)";
        range "1300..1999";
      }
      type string {
        tailf:info
          "WORD;;Named access list";
      }
    }
  }

  typedef std-acl-type {
    type union {
      type uint16 {
        tailf:info
          "<1-99>;;Standard access list";
        range "1..99";
      }
      type uint16 {
        tailf:info
          "<1300-1999>;;Standard access list (expanded range)";
        range "1300..1999";
      }
      type string {
        tailf:info
          "WORD;;Named access list";
      }
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef weekday-type {
    type enumeration {
      enum "Mon";
      enum "Tue";
      enum "Wed";
      enum "Thu";
      enum "Fri";
      enum "Sat";
      enum "Sun";
    }
  }

  typedef hhmm-type {
    type string {
      pattern '([0-1]?[0-9]|2[0-4]):([0-5][0-9])(:[0-5][0-9])?';
    }
  }

  typedef asn-ip-type {
    type string {
      tailf:info
        "ASN:nn or IP-address:nn";
      pattern '(([0-9]+)|((([0-9]|[1-9][0-9]|1[0-9][0-9]|2[0-4][0-9]|25[0-5])\\.){3}([0-9]|[1-9][0-9]|1[0-9][0-9]|2[0-4][0-9]|25[0-5]))):[0-9]+';
    }
  }

  typedef vpn-id-type {
    type string {
      tailf:info
        "OUI:VPN-Index;;, format (hex) <3 bytes OUI:4 bytes VPN_Index>";
      pattern '[0-9a-fA-F][0-9a-fA-F]?[0-9a-fA-F]?:[0-9a-fA-F][0-9a-fA-F]?[0-9a-fA-F]?[0-9a-fA-F]?';
    }
  }

  typedef rd-type {
    type string {
      tailf:info
        "ASN:nn or IP-address:nn;;VPN Route Distinguisher";
      pattern '(\d*(.\d*)*)?:(\d*(.\d*)*)?';
    }
  }

  typedef host-v4v6-type {
    type union {
      type inet:ipv4-address {
        tailf:info
          "Hostname or A.B.C.D;;ip address or host name";
      }
      type inet:domain-name {
        tailf:info
          "";
      }
      type inet:ipv6-address {
        tailf:info
          "X:X:X:X::X;;IPv6 address";
      }
    }
  }

  typedef host-type {
    type union {
      type inet:ip-address {
        tailf:info
          "";
      }
      type inet:domain-name {
        tailf:info
          "";
      }
    }
  }

  typedef ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))';
      pattern '(([^:]+:){6}(([^:]+:[^:]+)|(.*\\..*)))|((([^:]+:)*[^:]+)?::(([^:]+:)*[^:]+)?)(/.+)';
    }
  }

  typedef ipv4-prefix {
    type string {
      pattern '(([0-9]|[1-9][0-9]|1[0-9][0-9]|2[0-4][0-9]|25[0-5])\\.){3}([0-9]|[1-9][0-9]|1[0-9][0-9]|2[0-4][0-9]|25[0-5])/(([0-9])|([1-2][0-9])|(3[0-2]))';
    }
  }

  typedef percentage-type {
    type uint8 {
      tailf:info
        "<1-100>;;Percentage";
      range "1..100";
    }
  }

  grouping ncs_template_redistribute-ospf-match-grouping {
    leaf internal {
      type empty;
    }
    container external-1 {
      leaf external {
        type string;
      }
    }
    container external-2 {
      leaf external {
        type string;
      }
    }
    container nssa-external-1 {
      leaf nssa-external {
        type string;
      }
    }
    container nssa-external-2 {
      leaf nssa-external {
        type string;
      }
    }
  }

  grouping ncs_template_police-action-transmit-grouping {
    leaf transmit {
      type empty;
    }
  }

  grouping ncs_template_police-action-drop-grouping {
    leaf drop {
      type empty;
    }
  }

  grouping ncs_template_police-conform-action-grouping {
    container conform-set-clp-transmit {
      container conform-action {
        leaf set-clp-transmit {
          type empty;
        }
      }
    }
    container conform-set-cos-transmit {
      container conform-action {
        leaf set-cos-transmit {
          type string;
        }
      }
    }
    container conform-set-cos-transmit-table {
      container conform-action {
        leaf set-cos-transmit {
          type string;
        }
        leaf table {
          type string;
        }
      }
    }
    container conform-set-discard-class-transmit {
      container conform-action {
        leaf set-discard-class-transmit {
          type string;
        }
      }
    }
    container conform-set-dscp-transmit {
      container conform-action {
        leaf set-dscp-transmit {
          type string;
        }
      }
    }
    container conform-set-dscp-transmit-table {
      container conform-action {
        leaf set-dscp-transmit {
          type string;
        }
        leaf table {
          type string;
        }
      }
    }
    container conform-set-frde-transmit {
      container conform-action {
        leaf set-frde-transmit {
          type empty;
        }
      }
    }
    container conform-set-mpls-exp-imposition-transmit {
      container conform-action {
        leaf set-mpls-exp-imposition-transmit {
          type string;
        }
      }
    }
    container conform-set-mpls-exp-imposition-transmit-table {
      container conform-action {
        leaf set-mpls-exp-imposition-transmit {
          type string;
        }
        leaf table {
          type string;
        }
      }
    }
    container conform-set-mpls-exp-topmost-transmit {
      container conform-action {
        leaf set-mpls-exp-topmost-transmit {
          type string;
        }
      }
    }
    container conform-set-mpls-exp-topmost-transmit-table {
      container conform-action {
        leaf set-mpls-exp-topmost-transmit {
          type string;
        }
        leaf table {
          type string;
        }
      }
    }
    container conform-set-prec-transmit {
      container conform-action {
        leaf set-prec-transmit {
          type string;
        }
      }
    }
    container conform-set-prec-transmit-table {
      container conform-action {
        leaf set-prec-transmit {
          type string;
        }
        leaf table {
          type string;
        }
      }
    }
    container conform-set-qos-transmit {
      container conform-action {
        leaf set-qos-transmit {
          type string;
        }
      }
    }
    container conform-set-qos-transmit-table {
      container conform-action {
        leaf set-qos-transmit {
          type string;
        }
        leaf table {
          type string;
        }
      }
    }
    container conform-transmit {
      container conform-action {
        uses ncs_template_police-action-transmit-grouping;
      }
    }
    container conform-drop {
      container conform-action {
        uses ncs_template_police-action-drop-grouping;
      }
    }
  }

  grouping ncs_template_police-exceed-action-grouping {
    container exceed-dscp {
      container exceed-action {
        leaf dscp {
          type string;
        }
      }
    }
    container exceed-set-clp-transmit {
      container exceed-action {
        leaf set-clp-transmit {
          type empty;
        }
      }
    }
    container exceed-set-cos-transmit {
      container exceed-action {
        leaf set-cos-transmit {
          type string;
        }
      }
    }
    container exceed-set-discard-class-transmit {
      container exceed-action {
        leaf set-discard-class-transmit {
          type string;
        }
      }
    }
    container exceed-set-dscp-transmit {
      container exceed-action {
        leaf set-dscp-transmit {
          type string;
        }
      }
    }
    container exceed-set-frde-transmit {
      container exceed-action {
        leaf set-frde-transmit {
          type empty;
        }
      }
    }
    container exceed-set-mpls-exp-imposition-transmit {
      container exceed-action {
        leaf set-mpls-exp-imposition-transmit {
          type string;
        }
      }
    }
    container exceed-set-mpls-exp-topmost-transmit {
      container exceed-action {
        leaf set-mpls-exp-topmost-transmit {
          type string;
        }
      }
    }
    container exceed-set-prec-transmit {
      container exceed-action {
        leaf set-prec-transmit {
          type string;
        }
      }
    }
    container exceed-set-qos-transmit {
      container exceed-action {
        leaf set-qos-transmit {
          type string;
        }
      }
    }
    container exceed-transmit {
      container exceed-action {
        uses ncs_template_police-action-transmit-grouping;
      }
    }
    container exceed-drop {
      container exceed-action {
        uses ncs_template_police-action-drop-grouping;
      }
    }
  }

  grouping ncs_template_police-violate-action-grouping {
    container violate-set-clp-transmit {
      container violate-action {
        leaf set-clp-transmit {
          type empty;
        }
      }
    }
    container violate-set-cos-transmit {
      container violate-action {
        leaf set-cos-transmit {
          type string;
        }
      }
    }
    container violate-set-discard-class-transmit {
      container violate-action {
        leaf set-discard-class-transmit {
          type string;
        }
      }
    }
    container violate-set-dscp-transmit {
      container violate-action {
        leaf set-dscp-transmit {
          type string;
        }
      }
    }
    container violate-set-frde-transmit {
      container violate-action {
        leaf set-frde-transmit {
          type empty;
        }
      }
    }
    container violate-set-mpls-exp-imposition-transmit {
      container violate-action {
        leaf set-mpls-exp-imposition-transmit {
          type string;
        }
      }
    }
    container violate-set-mpls-exp-topmost-transmit {
      container violate-action {
        leaf set-mpls-exp-topmost-transmit {
          type string;
        }
      }
    }
    container violate-set-prec-transmit {
      container violate-action {
        leaf set-prec-transmit {
          type string;
        }
      }
    }
    container violate-set-qos-transmit {
      container violate-action {
        leaf set-qos-transmit {
          type string;
        }
      }
    }
    container violate-transmit {
      container violate-action {
        uses ncs_template_police-action-transmit-grouping;
      }
    }
    container violate-drop {
      container violate-action {
        uses ncs_template_police-action-drop-grouping;
      }
    }
  }

  grouping ncs_template_police-action-grouping {
    container actions {
      uses ncs_template_police-conform-action-grouping;
      uses ncs_template_police-exceed-action-grouping;
      uses ncs_template_police-violate-action-grouping;
    }
  }

  grouping ncs_template_password-grouping {
    container password-container {
      leaf encryption {
        type string;
      }
      leaf password {
        type string;
      }
    }
  }

  grouping ncs_template_crypto-key-grouping {
    leaf encryption {
      type string;
    }
    leaf secret {
      type string;
    }
  }

  grouping ncs_template_distribute-list-content-grouping {
    choice distribute-type {
      case access-list {
        leaf access-list-name {
          type string;
        }
      }
      case prefix-list-gateway {
        leaf prefix {
          type string;
        }
        leaf gateway {
          type string;
        }
      }
      case route-map {
        leaf routemap {
          type string;
        }
      }
    }
  }

  grouping ncs_template_router-distribute-list-grouping {
    list distribute-list {
      // NCS patched for predictable order
      ordered-by user;
      key "direction";
      leaf direction {
        type string;
      }
      uses ncs_template_distribute-list-content-grouping;
    }
    container distribute-list-interface {
      list distribute-list {
        // NCS patched for predictable order
        ordered-by user;
        key "direction interface";
        leaf direction {
          type string;
        }
        leaf interface {
          // NCS drop tailf-common:cli-diff-dependency statement
          type string;
        }
        uses ncs_template_distribute-list-content-grouping;
      }
    }
  }

  grouping ncs_template_passive-interface-grouping {
    container passive-interface {
      choice passive-interface-choice {
        leaf default {
          type empty;
        }
        list interface {
          // NCS patched for predictable order
          ordered-by user;
          key "name";
          leaf name {
            type string;
          }
        }
      }
    }
    container disable {
      // NCS drop when statement
      list passive-interface {
        // NCS patched for predictable order
        ordered-by user;
        key "interface";
        leaf interface {
          type string;
        }
      }
    }
  }

  grouping ncs_template_interface-name-grouping {
    choice interface-choice {
      leaf Null {
        type string;
      }
      leaf Loopback {
        type string;
      }
      leaf Embedded-Service-Engine {
        type string;
      }
      leaf Tunnel {
        type string;
      }
      leaf Port-channel {
        type string;
      }
      container Port-channel-subinterface {
        leaf Port-channel {
          type string;
        }
      }
      leaf Multilink {
        type string;
      }
      leaf MFR {
        type string;
      }
      container MFR-subinterface {
        leaf MFR {
          type string;
        }
      }
      leaf BRI {
        type string;
      }
      leaf Ethernet {
        type string;
      }
      leaf FastEthernet {
        type string;
      }
      leaf GigabitEthernet {
        type string;
      }
      leaf TenGigabitEthernet {
        type string;
      }
      leaf BDI {
        type string;
      }
      leaf Cable {
        type string;
      }
      leaf Modular-Cable {
        type string;
      }
      leaf Wideband-Cable {
        type string;
      }
      leaf Bundle {
        type string;
      }
      leaf Cellular {
        type string;
      }
      leaf Vlan {
        type string;
      }
      leaf Async {
        type string;
      }
      leaf Group-Async {
        type string;
      }
      leaf Serial {
        type string;
      }
      container Serial-subinterface {
        leaf Serial {
          type string;
        }
      }
      leaf Virtual-Template {
        type string;
      }
      leaf pseudowire {
        type string;
      }
      leaf LISP {
        type string;
      }
      container LISP-subinterface {
        leaf LISP {
          type string;
        }
      }
    }
  }

  grouping ncs_template_ip-community-list-standard-grouping {
    container deny {
      presence "true";
      list deny-list {
        // NCS patched for predictable order
        ordered-by user;
        key "expr";
        leaf expr {
          type string;
        }
      }
    }
    container permit {
      presence "true";
      list permit-list {
        // NCS patched for predictable order
        ordered-by user;
        key "expr";
        leaf expr {
          type string;
        }
      }
    }
  }

  grouping ncs_template_ip-community-list-expanded-grouping {
    container deny {
      presence "true";
      list deny-list {
        // NCS patched for predictable order
        ordered-by user;
        key "expr";
        leaf expr {
          type string;
        }
      }
    }
    container permit {
      presence "true";
      list permit-list {
        // NCS patched for predictable order
        ordered-by user;
        key "expr";
        leaf expr {
          type string;
        }
      }
    }
  }

  grouping ncs_template_ip-route-options-grouping {
    leaf metric {
      type string;
    }
    leaf global {
      type empty;
    }
    leaf name {
      type string;
    }
    leaf permanent {
      type empty;
    }
    leaf multicast {
      type empty;
    }
    leaf dhcp {
      type empty;
    }
    leaf tag {
      type string;
    }
    leaf track {
      type string;
    }
  }

  grouping ncs_template_ip-route-grouping {
    list ip-route-interface-forwarding-list {
      // NCS patched for predictable order
      ordered-by user;
      key "prefix mask interface forwarding-address";
      leaf prefix {
        type string;
      }
      leaf mask {
        type string;
      }
      leaf interface {
        // NCS drop tailf-common:cli-diff-dependency statement
        type string;
      }
      leaf forwarding-address {
        type string;
      }
      uses ncs_template_ip-route-options-grouping;
    }
    list ip-route-forwarding-list {
      // NCS patched for predictable order
      ordered-by user;
      key "prefix mask forwarding-address";
      leaf prefix {
        type string;
      }
      leaf mask {
        type string;
      }
      leaf forwarding-address {
        type string;
      }
      uses ncs_template_ip-route-options-grouping;
    }
    list ip-route-interface-list {
      // NCS patched for predictable order
      ordered-by user;
      key "prefix mask interface";
      leaf prefix {
        type string;
      }
      leaf mask {
        type string;
      }
      leaf interface {
        // NCS drop tailf-common:cli-diff-dependency statement
        type string;
      }
      uses ncs_template_ip-route-options-grouping;
    }
  }

  grouping ncs_template_ipv6-route-options-grouping {
    leaf distance {
      type string;
    }
    choice type-choice {
      leaf multicast {
        type empty;
      }
      leaf unicast {
        type empty;
      }
    }
    leaf tag {
      type string;
    }
  }

  grouping ncs_template_ipv6-route-grouping {
    list ipv6-route-interface-destination-list {
      // NCS patched for predictable order
      ordered-by user;
      key "prefix interface destination";
      leaf prefix {
        type string;
      }
      leaf interface {
        // NCS drop tailf-common:cli-diff-dependency statement
        type string;
      }
      leaf destination {
        type string;
      }
      uses ncs_template_ipv6-route-options-grouping;
    }
    list ipv6-route-destination-list {
      // NCS patched for predictable order
      ordered-by user;
      key "prefix destination";
      leaf prefix {
        type string;
      }
      leaf destination {
        type string;
      }
      uses ncs_template_ipv6-route-options-grouping;
    }
    list ipv6-route-interface-list {
      // NCS patched for predictable order
      ordered-by user;
      key "prefix interface";
      leaf prefix {
        type string;
      }
      leaf interface {
        // NCS drop tailf-common:cli-diff-dependency statement
        type string;
      }
      uses ncs_template_ipv6-route-options-grouping;
    }
  }

  grouping ncs_template_random-detect-grouping {
    leaf min-threshold {
      type string;
    }
    leaf min-threshold-unit {
      type string;
    }
    leaf max-threshold {
      type string;
    }
    leaf max-threshold-unit {
      type string;
    }
    leaf denominator {
      type string;
    }
  }

  grouping ncs_template_class-map-match-grouping {
    container access-group {
      leaf index {
        type string;
      }
      leaf-list name {
        // NCS patched for predictable order
        ordered-by user;
        type string;
      }
    }
    leaf any {
      type empty;
    }
    leaf-list class-map {
      // NCS patched for predictable order
      ordered-by user;
      type string;
    }
    leaf-list cos {
      // NCS patched for predictable order
      ordered-by user;
      // NCS drop max-elements statement
      type string;
    }
    container destination-address {
      leaf-list mac {
        // NCS patched for predictable order
        ordered-by user;
        type string;
      }
    }
    leaf-list discard-class {
      // NCS patched for predictable order
      ordered-by user;
      type string;
    }
    leaf-list dscp {
      // NCS patched for predictable order
      ordered-by user;
      type string;
    }
    leaf fr-de {
      type empty;
    }
    leaf-list fr-dlci {
      // NCS patched for predictable order
      ordered-by user;
      type string;
    }
    leaf-list input-interface {
      // NCS patched for predictable order
      ordered-by user;
      type string;
    }
    container ip {
      leaf-list dscp {
        // NCS patched for predictable order
        ordered-by user;
        type string;
      }
      leaf-list precedence {
        // NCS patched for predictable order
        ordered-by user;
        type string;
      }
      list rtp {
        // NCS patched for predictable order
        ordered-by user;
        key "port1 port2";
        leaf port1 {
          type string;
        }
        leaf port2 {
          type string;
        }
      }
    }
    container mpls {
      container experimental {
        leaf-list topmost {
          // NCS patched for predictable order
          ordered-by user;
          type string;
        }
      }
    }
    container packet {
      container length {
        leaf max {
          type string;
        }
        leaf min {
          type string;
        }
      }
    }
    leaf-list precedence {
      // NCS patched for predictable order
      ordered-by user;
      type string;
    }
    container protocol {
      leaf x802-11-iapp {
        tailf:alt-name "802-11-iapp";
        type empty;
      }
      leaf ace-svr {
        type empty;
      }
      leaf aol {
        type empty;
      }
      leaf appleqtc {
        type empty;
      }
      leaf biff {
        type empty;
      }
      leaf bittorrent {
        type empty;
      }
      leaf bootpc {
        type empty;
      }
      leaf bootps {
        type empty;
      }
      leaf cddbp {
        type empty;
      }
      leaf cifs {
        type empty;
      }
      leaf cisco-fna {
        type empty;
      }
      leaf cisco-net-mgmt {
        type empty;
      }
      leaf cisco-svcs {
        type empty;
      }
      leaf cisco-sys {
        type empty;
      }
      leaf cisco-tdp {
        type empty;
      }
      leaf cisco-tna {
        type empty;
      }
      leaf citriximaclient {
        type empty;
      }
      leaf clp {
        type empty;
      }
      leaf creativepartnr {
        type empty;
      }
      leaf creativeserver {
        type empty;
      }
      leaf daytime {
        type empty;
      }
      leaf dbase {
        type empty;
      }
      leaf dbcontrol_agent {
        type empty;
      }
      leaf ddns-v3 {
        type empty;
      }
      leaf dhcp-failover {
        type empty;
      }
      leaf directconnect {
        type empty;
      }
      leaf discard {
        type empty;
      }
      leaf dnsix {
        type empty;
      }
      leaf echo {
        type empty;
      }
      leaf entrust-svc-hdlr {
        type empty;
      }
      leaf entrust-svcs {
        type empty;
      }
      leaf exec {
        type empty;
      }
      leaf fcip-port {
        type empty;
      }
      leaf ftps {
        type empty;
      }
      leaf gdoi {
        type empty;
      }
      leaf giop {
        type empty;
      }
      leaf gtpv0 {
        type empty;
      }
      leaf gtpv1 {
        type empty;
      }
      leaf h225ras {
        type empty;
      }
      leaf h323callsigalt {
        type empty;
      }
      leaf hp-alarm-mgr {
        type empty;
      }
      leaf hp-collector {
        type empty;
      }
      leaf hp-managed-node {
        type empty;
      }
      leaf hsrp {
        type empty;
      }
      leaf https {
        type empty;
      }
      leaf ica {
        type empty;
      }
      leaf icabrowser {
        type empty;
      }
      leaf ident {
        type empty;
      }
      leaf igmpv3lite {
        type empty;
      }
      leaf imap3 {
        type empty;
      }
      leaf imaps {
        type empty;
      }
      leaf ipass {
        type empty;
      }
      leaf ipsec-msft {
        type empty;
      }
      leaf irc-serv {
        type empty;
      }
      leaf ircs {
        type empty;
      }
      leaf ircu {
        type empty;
      }
      leaf isakmp {
        type empty;
      }
      leaf iscsi {
        type empty;
      }
      leaf iscsi-target {
        type empty;
      }
      leaf kermit {
        type empty;
      }
      leaf ldap-admin {
        type empty;
      }
      leaf ldaps {
        type empty;
      }
      leaf login {
        type empty;
      }
      leaf lotusmtap {
        type empty;
      }
      leaf lotusnote {
        type empty;
      }
      leaf microsoft-ds {
        type empty;
      }
      leaf ms-cluster-net {
        type empty;
      }
      leaf ms-dotnetster {
        type empty;
      }
      leaf ms-sna {
        type empty;
      }
      leaf ms-sql {
        type empty;
      }
      leaf ms-sql-m {
        type empty;
      }
      leaf msexch-routing {
        type empty;
      }
      leaf msnmsgr {
        type empty;
      }
      leaf msrpc {
        type empty;
      }
      leaf mysql {
        type empty;
      }
      leaf n2h2server {
        type empty;
      }
      leaf ncp {
        type empty;
      }
      leaf net8-cman {
        type empty;
      }
      leaf netbios-dgm {
        type empty;
      }
      leaf netbios-ns {
        type empty;
      }
      leaf netbios-ssn {
        type empty;
      }
      leaf netstat {
        type empty;
      }
      leaf oem-agent {
        type empty;
      }
      leaf oracle {
        type empty;
      }
      leaf oracle-em-vp {
        type empty;
      }
      leaf oraclenames {
        type empty;
      }
      leaf orasrv {
        type empty;
      }
      leaf pcanywheredata {
        type empty;
      }
      leaf pcanywherestat {
        type empty;
      }
      leaf pop3s {
        type empty;
      }
      leaf pwdgen {
        type empty;
      }
      leaf qmtp {
        type empty;
      }
      leaf r-winsock {
        type empty;
      }
      leaf radius {
        type empty;
      }
      leaf rdb-dbs-disp {
        type empty;
      }
      leaf realmedia {
        type empty;
      }
      leaf realsecure {
        type empty;
      }
      leaf router {
        type empty;
      }
      leaf rsvp-encap {
        type empty;
      }
      leaf rsvp_tunnel {
        type empty;
      }
      leaf rtc-pm-port {
        type empty;
      }
      leaf rtelnet {
        type empty;
      }
      leaf send {
        type empty;
      }
      leaf shell {
        type empty;
      }
      leaf sip-tls {
        type empty;
      }
      leaf sms {
        type empty;
      }
      leaf snmptrap {
        type empty;
      }
      leaf sql-net {
        type empty;
      }
      leaf sqlserv {
        type empty;
      }
      leaf sqlsrv {
        type empty;
      }
      leaf sshell {
        type empty;
      }
      leaf ssp {
        type empty;
      }
      leaf syslog-conn {
        type empty;
      }
      leaf tacacs {
        type empty;
      }
      leaf tacacs-ds {
        type empty;
      }
      leaf tarantella {
        type empty;
      }
      leaf tcp {
        type empty;
      }
      leaf telnets {
        type empty;
      }
      leaf time {
        type empty;
      }
      leaf timed {
        type empty;
      }
      leaf tr-rsrb {
        type empty;
      }
      leaf ttc {
        type empty;
      }
      leaf udp {
        type empty;
      }
      leaf uucp {
        type empty;
      }
      leaf vqp {
        type empty;
      }
      leaf webster {
        type empty;
      }
      leaf who {
        type empty;
      }
      leaf wins {
        type empty;
      }
      leaf x11 {
        type empty;
      }
      leaf xdmcp {
        type empty;
      }
      leaf ymsgr {
        type empty;
      }
      leaf aarp {
        type empty;
      }
      leaf appletalk {
        type empty;
      }
      leaf arp {
        type empty;
      }
      leaf bgp {
        type empty;
      }
      leaf bridge {
        type empty;
      }
      leaf bstun {
        type empty;
      }
      leaf cdp {
        type empty;
      }
      container citrix {
        presence "enable citrix system protocol matching";
        leaf ica-tag {
          type string;
        }
      }
      leaf clns {
        type empty;
      }
      leaf clns_es {
        type empty;
      }
      leaf clns_is {
        type empty;
      }
      leaf cmns {
        type empty;
      }
      leaf compressedtcp {
        type empty;
      }
      leaf cuseeme {
        type empty;
      }
      leaf decnet {
        type empty;
      }
      leaf decnet_node {
        type empty;
      }
      leaf decnet_router-l1 {
        type empty;
      }
      leaf decnet_router-l2 {
        type empty;
      }
      leaf dhcp {
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        presence "enable fasttrack matching";
        leaf file-transfer {
          type string;
        }
      }
      leaf finger {
        type empty;
      }
      leaf ftp {
        type empty;
      }
      container gnutella {
        presence "enable gnutella matching";
        leaf file-transfer {
          type string;
        }
      }
      leaf gopher {
        type empty;
      }
      leaf gre {
        type empty;
      }
      leaf h323 {
        type empty;
      }
      container http {
        presence "enable http traffic matching";
        leaf c-header-field {
          type string;
        }
        leaf host {
          type string;
        }
        leaf mime {
          type string;
        }
        leaf s-header-field {
          type string;
        }
        leaf url {
          type string;
        }
      }
      leaf icmp {
        type empty;
      }
      leaf imap {
        type empty;
      }
      leaf ip {
        type empty;
      }
      leaf ipinip {
        type empty;
      }
      leaf ipsec {
        type empty;
      }
      leaf ipv6 {
        type empty;
      }
      leaf ipx {
        type empty;
      }
      leaf irc {
        type empty;
      }
      container kazaa2 {
        presence "enable kazaa version 2 matching";
        leaf file-transfer {
          type string;
        }
      }
      leaf kerberos {
        type empty;
      }
      leaf l2tp {
        type empty;
      }
      leaf ldap {
        type empty;
      }
      leaf llc2 {
        type empty;
      }
      leaf mgcp {
        type empty;
      }
      container napster {
        presence "enable napster matching";
        leaf non-std {
          type empty;
        }
      }
      leaf netbios {
        type empty;
      }
      leaf netshow {
        type empty;
      }
      leaf nfs {
        type empty;
      }
      leaf nntp {
        type empty;
      }
      leaf notes {
        type empty;
      }
      leaf novadigm {
        type empty;
      }
      leaf ntp {
        type empty;
      }
      leaf ospf {
        type empty;
      }
      leaf pad {
        type empty;
      }
      leaf pcanywhere {
        type empty;
      }
      leaf pop3 {
        type empty;
      }
      leaf pppoe {
        type empty;
      }
      leaf pptp {
        type empty;
      }
      leaf printer {
        type empty;
      }
      leaf qllc {
        type empty;
      }
      leaf rcmd {
        type empty;
      }
      leaf rip {
        type empty;
      }
      leaf rsrb {
        type empty;
      }
      leaf rsvp {
        type empty;
      }
      leaf rtcp {
        type empty;
      }
      container rtp {
        presence "enable rtp matching";
        leaf audio {
          type empty;
        }
        leaf payload-type {
          type string;
        }
        leaf video {
          type empty;
        }
      }
      leaf rtsp {
        type empty;
      }
      leaf secure-ftp {
        type empty;
      }
      leaf secure-http {
        type empty;
      }
      leaf secure-imap {
        type empty;
      }
      leaf secure-irc {
        type empty;
      }
      leaf secure-ldap {
        type empty;
      }
      leaf secure-nntp {
        type empty;
      }
      leaf secure-pop3 {
        type empty;
      }
      leaf secure-telnet {
        type empty;
      }
      leaf sip {
        type empty;
      }
      leaf skinny {
        type empty;
      }
      leaf smtp {
        type empty;
      }
      leaf snapshot {
        type empty;
      }
      leaf snmp {
        type empty;
      }
      leaf socks {
        type empty;
      }
      leaf sqlnet {
        type empty;
      }
      leaf sqlserver {
        type empty;
      }
      leaf ssh {
        type empty;
      }
      leaf streamwork {
        type empty;
      }
      leaf stun {
        type empty;
      }
      leaf sunrpc {
        type empty;
      }
      leaf syslog {
        type empty;
      }
      leaf telnet {
        type empty;
      }
      leaf tftp {
        type empty;
      }
      leaf vdolive {
        type empty;
      }
      leaf vofr {
        type empty;
      }
      leaf winmx {
        type empty;
      }
      leaf xwindows {
        type empty;
      }
      container attribute {
        list category {
          // NCS patched for predictable order
          ordered-by user;
          key "category-type";
          leaf category-type {
            type string;
          }
        }
      }
    }
    leaf-list qos-group {
      // NCS patched for predictable order
      ordered-by user;
      type string;
    }
    container source-address {
      leaf-list mac {
        // NCS patched for predictable order
        ordered-by user;
        type string;
      }
    }
    leaf-list vlan {
      // NCS patched for predictable order
      ordered-by user;
      type string;
    }
  }

  grouping ncs_template_ip-name-server-grouping {
    list name-server-list {
      // NCS patched for predictable order
      ordered-by user;
      // NCS drop max-elements statement
      key "address";
      leaf address {
        type string;
      }
    }
  }

  grouping ncs_template_ip-host-grouping {
    list host-list {
      // NCS patched for predictable order
      ordered-by user;
      key "hostname";
      leaf hostname {
        type string;
      }
      leaf tcp-port-number {
        type string;
      }
      leaf-list ip-address1 {
        // NCS patched for predictable order
        ordered-by user;
        type string;
      }
    }
  }

  grouping ncs_template_ip-dhcp-excluded-address-grouping {
    list low-list {
      // NCS patched for predictable order
      ordered-by user;
      key "low";
      leaf low {
        type string;
      }
    }
    list low-high-list {
      // NCS patched for predictable order
      ordered-by user;
      key "low high";
      leaf low {
        type string;
      }
      leaf high {
        type string;
      }
    }
  }

  grouping ncs_template_ntp-peer-grouping {
    list peer-list {
      // NCS patched for predictable order
      ordered-by user;
      key "name";
      leaf name {
        type string;
      }
      leaf burst {
        type empty;
      }
      leaf iburst {
        type empty;
      }
      leaf key {
        type string;
      }
      leaf maxpoll {
        type string;
      }
      leaf minpoll {
        type string;
      }
      leaf normal-sync {
        type empty;
      }
      leaf prefer {
        type empty;
      }
      container source {
        uses ncs_template_interface-name-grouping;
      }
      leaf version {
        type string;
      }
    }
  }

  grouping ncs_template_sntp-server-grouping {
    list server-list {
      // NCS patched for predictable order
      ordered-by user;
      key "name";
      leaf name {
        type string;
      }
      leaf key {
        type string;
      }
      leaf version {
        type string;
      }
    }
  }

  grouping ncs_template_line-grouping {
    leaf absolute-timeout {
      type string;
    }
    container access-class {
      list access-list {
        // NCS patched for predictable order
        ordered-by user;
        key "direction";
        leaf direction {
          type string;
        }
        leaf access-list {
          type string;
          // NCS drop mandatory statement
        }
        leaf vrf-also {
          type empty;
        }
      }
    }
    container activation-character-choice {
      choice activation-character-choice {
        leaf activation-character {
          type string;
          // NCS drop default statement
        }
        container activation-character-conf {
          leaf activation-character {
            type string;
          }
        }
      }
    }
    leaf escape-character {
      type string;
    }
    container script {
      leaf dialer {
        type string;
      }
    }
    container modem {
      leaf enable {
        type string;
      }
      leaf InOut {
        type empty;
      }
      container autoconfigure {
        leaf discovery {
          type empty;
        }
      }
    }
    container exec-choice {
      choice exec-choice {
        leaf exec {
          type string;
          // NCS drop default statement
        }
        container exec-conf {
          container exec {
            container prompt {
              leaf timestamp {
                type empty;
              }
            }
          }
        }
      }
    }
    container exec-timeout {
      leaf minutes {
        type string;
      }
      leaf seconds {
        type string;
      }
    }
    container session-disconnect-warning {
      leaf seconds {
        type string;
      }
      leaf message {
        type string;
      }
    }
    container logging {
      container synchronous {
        presence "true";
      }
    }
    container login {
      presence "true";
      leaf local {
        type empty;
      }
      leaf authentication {
        type string;
      }
    }
    leaf logout-warning {
      type string;
    }
    container ipv6 {
      list access-class {
        // NCS patched for predictable order
        ordered-by user;
        key "direction";
        leaf direction {
          type string;
        }
        leaf access-list {
          type string;
        }
      }
    }
    container history {
      leaf size {
        type string;
      }
    }
    container password {
      uses ncs_template_password-07-grouping;
    }
    container privilege {
      leaf level {
        type string;
      }
    }
    container session-timeout {
      leaf session-timeout-value {
        type string;
      }
      leaf output {
        type empty;
      }
    }
    leaf stopbits {
      type string;
    }
    container telnet {
      leaf transparent {
        type empty;
      }
    }
    container transport {
      leaf-list input {
        // NCS patched for predictable order
        ordered-by user;
        type string;
      }
      leaf-list output {
        // NCS patched for predictable order
        ordered-by user;
        type string;
      }
      leaf preferred {
        type string;
      }
    }
    leaf rxspeed {
      type string;
    }
    leaf txspeed {
      type string;
    }
    leaf length {
      type string;
    }
    leaf width {
      type string;
    }
  }

  grouping ncs_template_queue-size-grouping {
    leaf queue-size-1 {
      type string;
    }
    leaf queue-size-2 {
      type string;
    }
    leaf queue-size-3 {
      type string;
    }
    leaf queue-size-4 {
      type string;
    }
    leaf queue-size-5 {
      type string;
    }
    leaf queue-size-6 {
      type string;
    }
    leaf queue-size-7 {
      type string;
    }
    leaf queue-size-8 {
      type string;
    }
  }

  grouping ncs_template_interface-common-pre-grouping {
    leaf description {
      type string;
    }
    leaf mac-address {
      type string;
    }
  }

  grouping ncs_template_interface-common-grouping {
    container authentication {
      leaf port-control {
        type string;
      }
    }
    container mab {
      presence "true";
      leaf eap {
        type empty;
      }
    }
    container l2protocol-tunnel {
      presence "true";
      leaf cdp {
        type empty;
      }
      container drop-threshold {
        leaf packet-rate {
          type string;
        }
        leaf cdp {
          type string;
        }
        leaf stp {
          type string;
        }
        leaf vtp {
          type string;
        }
      }
      container shutdown-threshold {
        leaf packet-rate {
          type string;
        }
        leaf cdp {
          type string;
        }
        leaf stp {
          type string;
        }
        leaf vtp {
          type string;
        }
        leaf lldp {
          type string;
        }
      }
      leaf stp {
        type empty;
      }
      leaf vtp {
        type empty;
      }
      leaf lldp {
        type empty;
      }
      container point-to-point {
        leaf lacp {
          type empty;
        }
        leaf pagp {
          type empty;
        }
        leaf udld {
          type empty;
        }
      }
    }
    container encapsulation {
      container dot1Q {
        leaf vlan-id {
          type string;
        }
        leaf second-dot1q {
          type string;
        }
        leaf native {
          type empty;
        }
      }
      container isl {
        leaf vlan-id {
          type string;
        }
      }
      container ppp {
        presence "true";
      }
      container slip {
        presence "true";
      }
      container frame-relay {
        presence "true";
        leaf IETF {
          type empty;
        }
        leaf MFR {
          type string;
        }
      }
      container hdlc {
        presence "true";
      }
    }
    container frame-relay {
      leaf lmi-type {
        type string;
      }
      leaf intf-type {
        type string;
      }
      container interface-dlci {
        leaf dlci {
          type string;
        }
        leaf encapsulation {
          type string;
        }
      }
    }
    container fair-queue {
      presence "true";
      leaf congestive-discard-threshold {
        type string;
      }
      leaf dynamic-queues {
        type string;
      }
      leaf reservable-queues {
        type string;
      }
    }
    container flowcontrol {
      leaf receive {
        type string;
      }
      leaf send {
        type string;
      }
    }
    choice keepalive-choice {
      leaf keepalive {
        type string;
        // NCS drop default statement
      }
      container keepalive-period {
        leaf keepalive {
          type string;
          // NCS drop default statement
        }
      }
      container keepalive-period-retries {
        container keepalive {
          leaf period {
            type string;
          }
          leaf retries {
            type string;
          }
        }
      }
    }
    container snmp {
      container ifindex {
        leaf persist {
          type empty;
        }
      }
      container trap {
        leaf link-status {
          type string;
          // NCS drop default statement
        }
        container link-status-capas {
          container link-status {
            container permit {
              leaf duplicates {
                type empty;
              }
            }
          }
        }
      }
    }
    container flow-sampler {
      leaf name {
        type string;
      }
      container egress {
        leaf name {
          type string;
        }
        leaf egress {
          type empty;
        }
      }
    }
    container bfd {
      leaf echo {
        type empty;
      }
      container interval {
        leaf msecs {
          type string;
        }
        leaf min_rx {
          type string;
        }
        leaf multiplier {
          type string;
        }
      }
    }
    container bandwidth {
      leaf inherit {
        type empty;
      }
      leaf kilobits {
        type string;
      }
    }
    container cdp {
      leaf enable {
        type string;
        // NCS drop default statement
      }
      container tlv {
        container app {
          presence "true";
          leaf tlvtype {
            type string;
          }
          leaf value {
            type string;
          }
        }
        leaf server-location {
          type empty;
        }
        leaf location {
          type empty;
        }
      }
    }
    container mop {
      leaf xenabled {
        tailf:alt-name "enabled";
        type string;
        // NCS drop default statement
      }
    }
    container dampening {
      presence "true";
      leaf dampening-time {
        type string;
      }
    }
    list hold-queue {
      // NCS patched for predictable order
      ordered-by user;
      key "direction";
      leaf direction {
        type string;
      }
      leaf queue-length {
        type string;
      }
    }
    container mpls {
      container accounting {
        container experimental {
          leaf input {
            type empty;
          }
          leaf output {
            type empty;
          }
        }
      }
      container bgp {
        leaf forwarding {
          type empty;
        }
      }
      container label {
        leaf protocol {
          type string;
        }
      }
      container ldp {
        container discovery {
          leaf transport-address {
            type string;
          }
        }
      }
      leaf mtu {
        type string;
        // NCS drop default statement
      }
      container traffic-eng {
        leaf administrative-weight {
          type string;
        }
        leaf backup-path {
          type string;
        }
        leaf attribute-flags {
          type string;
        }
        container flooding {
          container thresholds {
            leaf-list down {
              // NCS patched for predictable order
              ordered-by user;
              type string;
            }
            leaf-list up {
              // NCS patched for predictable order
              ordered-by user;
              type string;
            }
          }
        }
        leaf tunnels {
          type empty;
        }
      }
      leaf ip {
        type empty;
      }
    }
    container isis {
      container bfd {
        presence "true";
      }
      leaf circuit-type {
        type string;
        // NCS drop default statement
      }
      leaf network {
        type string;
      }
      choice metric-choice {
        case default-case {
          leaf metric {
            type string;
          }
        }
        case level-case {
          container metric-level {
            list metric {
              // NCS patched for predictable order
              ordered-by user;
              key "level";
              leaf level {
                type string;
              }
              leaf default {
                type string;
              }
            }
          }
        }
      }
      uses ncs_template_router-isis-interface-grouping;
      container ipv6 {
        container metric-level {
          list metric {
            // NCS patched for predictable order
            ordered-by user;
            key "level";
            leaf level {
              type string;
            }
            leaf value {
              type string;
            }
          }
        }
      }
    }
    choice vrf-choice {
      container ip-vrf {
        container ip {
          container vrf {
            leaf forwarding {
              type string;
            }
          }
        }
      }
      container vrf {
        leaf forwarding {
          type string;
        }
      }
    }
    container ip {
      list access-group {
        // NCS patched for predictable order
        ordered-by user;
        key "direction";
        leaf direction {
          type string;
        }
        leaf access-list {
          type string;
        }
      }
      container accounting {
        presence "true";
        leaf access-violations {
          type empty;
        }
        leaf output-packets {
          type empty;
        }
      }
      container vrf {
        leaf receive {
          type string;
        }
        leaf sitemap {
          type string;
        }
      }
      choice address-choice {
        leaf unnumbered {
          type string;
        }
        container no-address {
          leaf address {
            type string;
            // NCS drop default statement
          }
        }
        container address {
          choice address-choice {
            case fixed-case {
              container primary {
                leaf address {
                  // NCS drop tailf-common:cli-diff-dependency statement
                  // NCS drop tailf-common:cli-diff-dependency statement
                  // NCS drop mandatory statement
                  type string;
                }
                leaf mask {
                  // NCS drop mandatory statement
                  type string;
                }
              }
              list secondary {
                // NCS patched for predictable order
                ordered-by user;
                // NCS drop tailf-common:cli-diff-dependency statement
                key "address mask";
                leaf address {
                  type string;
                }
                leaf mask {
                  type string;
                }
                leaf secondary {
                  type empty;
                }
              }
            }
            case dhcp-case {
              container dhcp {
                presence "true";
                container client-id {
                  uses ncs_template_interface-name-grouping;
                }
                leaf hostname {
                  type string;
                }
              }
            }
            case negotiated-case {
              container negotiated {
                presence "true";
                leaf previous {
                  type empty;
                }
              }
            }
          }
        }
      }
      container directed-broadcast {
        presence "true";
        leaf access-list {
          type string;
        }
      }
      container router {
        container isis {
          presence "true";
          leaf tag {
            type string;
          }
        }
      }
      container flow {
        leaf ingress {
          type empty;
        }
        leaf egress {
          type empty;
        }
      }
      container helper-address {
        choice helper-choice {
          leaf global {
            type empty;
          }
          leaf vrf {
            // NCS drop tailf-common:cli-diff-dependency statement
            // NCS drop tailf-common:cli-diff-dependency statement
            type string;
          }
        }
        leaf address {
          type string;
        }
      }
      container ospf {
        list process-id {
          // NCS patched for predictable order
          ordered-by user;
          key "id";
          leaf id {
            type string;
          }
          leaf area {
            type string;
          }
          leaf secondaries {
            type empty;
          }
          leaf none {
            type empty;
          }
        }
        container authentication {
          presence "true";
          leaf option {
            type string;
          }
        }
        list message-digest-key {
          // NCS patched for predictable order
          ordered-by user;
          key "id";
          leaf id {
            type string;
          }
          leaf md5 {
            type empty;
          }
          leaf enc-type {
            type string;
          }
          leaf password {
            type string;
          }
        }
        leaf network {
          type string;
        }
        leaf hello-interval {
          type string;
        }
        container bfd {
          presence "true";
          leaf enable {
            type string;
          }
        }
        leaf cost {
          type string;
        }
        leaf priority {
          type string;
        }
      }
      container pim {
        leaf query-interval {
          type string;
        }
        leaf sparse-mode {
          // NCS drop tailf-common:cli-diff-dependency statement
          type empty;
        }
        leaf dr-priority {
          type string;
        }
        leaf snooping {
          type empty;
        }
      }
      container multicast {
        list boundary {
          // NCS patched for predictable order
          ordered-by user;
          key "access-list";
          leaf access-list {
            type string;
          }
        }
      }
      container policy {
        leaf route-map {
          type string;
        }
      }
      leaf unreachables {
        type string;
        // NCS drop default statement
      }
      leaf proxy-arp {
        type string;
        // NCS drop default statement
      }
      container route-cache-conf {
        leaf route-cache {
          type string;
          // NCS drop default statement
        }
      }
      container route-cache {
        leaf cef {
          type string;
          // NCS drop default statement
        }
        leaf flow {
          type string;
          // NCS drop default statement
        }
        leaf policy {
          type string;
          // NCS drop default statement
        }
        leaf same-interface {
          type string;
          // NCS drop default statement
        }
      }
      container igmp {
        list join-group {
          // NCS patched for predictable order
          ordered-by user;
          key "address";
          leaf address {
            type string;
          }
          leaf source {
            type string;
          }
        }
        container static-group {
          list groups {
            // NCS patched for predictable order
            ordered-by user;
            key "name";
            leaf name {
              type string;
            }
          }
          list class-map {
            // NCS patched for predictable order
            ordered-by user;
            key "id";
            leaf id {
              type string;
            }
          }
        }
        leaf version {
          type string;
        }
        leaf access-group {
          type string;
        }
      }
      leaf redirects {
        type empty;
      }
      container nhrp {
        leaf network-id {
          type string;
        }
        container shortcut {
          presence "true";
          leaf virtual-template {
            type string;
          }
        }
        container redirect {
          presence "true";
          leaf timeout {
            type string;
          }
        }
      }
      container tcp {
        leaf adjust-mss {
          type string;
        }
        container header-compression {
          presence "true";
          leaf type {
            type string;
          }
        }
      }
      container rtp {
        container header-compression {
          leaf type {
            type string;
          }
          leaf periodic-refresh {
            type empty;
          }
        }
        leaf compression-connections {
          type string;
        }
      }
      container mobile {
        container router-service {
          container roam {
            // NCS drop tailf-common:cli-diff-dependency statement
            presence "true";
            leaf priority {
              type string;
            }
          }
          leaf description {
            type string;
          }
          leaf link-type {
            type string;
          }
          container tunnel {
            leaf mode {
              type string;
            }
          }
          container collocated {
            leaf gateway {
              type string;
            }
            leaf ccoa-only {
              type empty;
            }
            container registration {
              leaf retry {
                type string;
                // NCS drop default statement
              }
              container nat {
                container traversal {
                  presence "true";
                  leaf keepalive {
                    type string;
                  }
                  leaf force {
                    type empty;
                  }
                }
              }
            }
            leaf encapsulation {
              type string;
            }
          }
        }
      }
      container virtual-reassembly {
        leaf max-reassemblies {
          type string;
        }
        leaf max-fragments {
          type string;
        }
        leaf timeout {
          type string;
        }
        leaf drop-fragments {
          type empty;
        }
        leaf in {
          type empty;
        }
        leaf out {
          type empty;
        }
      }
      container dhcp {
        container relay {
          container information {
            container check-reply {
              presence "true";
              leaf none {
                type empty;
              }
            }
            container option {
              leaf subscriber-id {
                type string;
              }
            }
            container option-insert {
              presence "true";
              leaf none {
                type empty;
              }
            }
            leaf policy-action {
              type string;
            }
            leaf trusted {
              type empty;
            }
          }
        }
        container snooping {
          container limit {
            leaf rate {
              type string;
            }
          }
          leaf trust {
            type empty;
          }
          list vlan {
            // NCS patched for predictable order
            ordered-by user;
            key "id";
            leaf id {
              type string;
            }
            container information {
              container option {
                container format-type {
                  container circuit-id {
                    leaf string {
                      type string;
                    }
                  }
                }
              }
            }
          }
          list bridge-domain {
            // NCS patched for predictable order
            ordered-by user;
            key "id";
            leaf id {
              type string;
            }
            container information {
              container option {
                container format-type {
                  container circuit-id {
                    leaf string {
                      type string;
                    }
                  }
                }
              }
            }
          }
        }
      }
      leaf mtu {
        type string;
      }
      container nat {
        leaf allow-static-host {
          type empty;
        }
        leaf enable {
          type empty;
        }
        choice nat-choice {
          leaf inside {
            type empty;
          }
          leaf outside {
            type empty;
          }
        }
      }
      container rsvp {
        container bandwidth {
          presence "true";
        }
        container signalling {
          container hello {
            presence "true";
            container graceful-restart {
              presence "true";
            }
          }
        }
        container resource-provider {
          choice resource-provider-choice {
            leaf none {
              type empty;
            }
            leaf wfq {
              type string;
            }
          }
        }
      }
      container verify {
        container unicast {
          container reverse-path {
            presence "true";
          }
          container source {
            leaf reachable-via {
              type string;
            }
            leaf allow-self-ping {
              type empty;
            }
            leaf allow-default {
              type empty;
            }
          }
        }
      }
      container rip {
        container receive {
          leaf version {
            type string;
          }
        }
        container authentication {
          leaf mode {
            type string;
          }
          leaf key-chain {
            type string;
          }
        }
      }
    }
    container ipv6 {
      container address {
        choice address-choice {
          case autoconfig-case {
            container autoconfig {
              presence "true";
              leaf default {
                type empty;
              }
            }
          }
          case manual-case {
            list prefix-list {
              // NCS patched for predictable order
              ordered-by user;
              key "prefix";
              leaf prefix {
                type string;
              }
              leaf anycast {
                type empty;
              }
              leaf eui-64 {
                type empty;
              }
            }
          }
        }
      }
      leaf enable {
        type empty;
      }
      list traffic-filter {
        // NCS patched for predictable order
        ordered-by user;
        key "direction";
        leaf direction {
          type string;
        }
        leaf access-list {
          type string;
        }
      }
      container nd {
        container dad {
          leaf attempts {
            type string;
          }
        }
        container prefix {
          list prefix-list {
            // NCS patched for predictable order
            ordered-by user;
            key "ipv6-prefix";
            leaf ipv6-prefix {
              type string;
            }
            choice advertise-choice {
              case no-advertise {
                leaf no-advertise {
                  type empty;
                }
              }
              case advertise {
                leaf valid-lifetime {
                  type string;
                }
                leaf preferred-lifetime {
                  type string;
                }
                leaf off-link {
                  type empty;
                }
                leaf no-autoconfig {
                  type empty;
                }
                leaf no-rtr-address {
                  type empty;
                }
                leaf no-onlink {
                  type empty;
                }
              }
            }
          }
        }
        leaf managed-config-flag {
          type empty;
        }
        leaf other-config-flag {
          type empty;
        }
        container ra {
          container suppress {
            presence "true";
            leaf all {
              type empty;
            }
          }
          container interval {
            choice interval-choice {
              leaf seconds {
                type string;
              }
              leaf msec {
                type string;
              }
            }
          }
        }
      }
      container mld {
        leaf access-group {
          type string;
        }
      }
      leaf redirects {
        type string;
        // NCS drop default statement
      }
      leaf unreachables {
        type string;
        // NCS drop default statement
      }
      container router {
        container isis {
          presence "true";
          leaf tag {
            type string;
          }
        }
      }
      container ospf {
        list process {
          // NCS patched for predictable order
          ordered-by user;
          key "id";
          leaf id {
            type string;
          }
          leaf area {
            type string;
          }
          leaf instance {
            type string;
          }
        }
        container bfd {
          presence "true";
          leaf disable {
            type empty;
          }
        }
        leaf cost {
          type string;
        }
        container database-filter {
          choice database {
            leaf all {
              type string;
            }
            leaf disable {
              type empty;
            }
          }
        }
        leaf dead-interval {
          type string;
        }
        container demand-circuit {
          presence "true";
          leaf disable {
            type empty;
          }
        }
        container flood-reduction {
          presence "true";
          leaf disable {
            type empty;
          }
        }
        leaf hello-interval {
          type string;
        }
        container mtu-ignore {
          presence "true";
          leaf disable {
            type empty;
          }
        }
        leaf priority {
          type string;
        }
        leaf retransmit-interval {
          type string;
        }
        leaf transmit-delay {
          type string;
        }
      }
      leaf mtu {
        type string;
      }
      container crypto {
        container map {
          leaf map-name {
            type string;
          }
          leaf redundancy {
            type string;
          }
          leaf stateful {
            // NCS drop when statement
            type empty;
          }
        }
      }
      container verify {
        container unicast {
          container reverse-path {
            presence "true";
            leaf access-list {
              type string;
            }
          }
        }
      }
      container dhcp {
        container relay {
          list destination {
            // NCS patched for predictable order
            ordered-by user;
            key "ipv6-address";
            leaf ipv6-address {
              type string;
            }
            leaf source-address {
              type string;
            }
            leaf link-address {
              type string;
            }
          }
        }
      }
    }
    leaf delay {
      type string;
    }
    leaf load-interval {
      type string;
    }
    container logging {
      container event {
        leaf link-status {
          type empty;
        }
        leaf subif-link-status {
          type empty;
        }
      }
    }
    leaf max-reserved-bandwidth {
      type string;
    }
    container mls {
      container qos {
        leaf channel-consistency {
          type string;
          // NCS drop default statement
        }
        leaf trust {
          type string;
        }
        leaf vlan-based {
          type empty;
        }
      }
    }
    leaf mtu {
      type string;
    }
    container ntp {
      container broadcast {
        presence "true";
        container client {
          presence "true";
        }
        list destination {
          // NCS patched for predictable order
          ordered-by user;
          key "address";
          leaf version {
            type string;
          }
          leaf key {
            type string;
          }
          leaf address {
            type string;
          }
        }
        container version-key {
          leaf version {
            type string;
          }
          leaf key {
            type string;
          }
        }
      }
      leaf disable {
        type empty;
      }
      container multicast {
        presence "true";
        list address-list {
          // NCS patched for predictable order
          ordered-by user;
          key "group-address";
          leaf group-address {
            type string;
          }
          leaf version {
            type string;
          }
          leaf key {
            type string;
          }
          leaf ttl {
            type string;
          }
        }
        leaf version {
          type string;
        }
        leaf key {
          type string;
        }
        leaf ttl {
          type string;
        }
        container client-list {
          leaf-list client {
            // NCS patched for predictable order
            ordered-by user;
            type string;
          }
        }
        leaf client {
          type empty;
        }
      }
    }
    container power {
      container inline {
        leaf consumption {
          type string;
        }
      }
    }
    list rate-limit {
      // NCS patched for predictable order
      ordered-by user;
      key "dir bps bc be conform-action exceed-action";
      leaf dir {
        type string;
      }
      leaf dscp {
        type string;
      }
      leaf bps {
        type string;
      }
      leaf bc {
        type string;
      }
      leaf be {
        type string;
      }
      leaf conform-action {
        type string;
      }
      leaf exceed-action {
        type string;
      }
    }
    container service-policy {
      leaf history {
        type empty;
      }
      uses ncs_template_service-policy-grouping;
      container type {
        container performance-monitor {
          leaf direction {
            type string;
          }
          leaf name {
            type string;
          }
        }
      }
    }
    leaf shutdown {
      type empty;
    }
    container standby {
      leaf version {
        type string;
      }
      leaf bfd {
        type empty;
      }
      container delay {
        leaf minimum {
          type string;
        }
        leaf reload {
          type string;
        }
      }
      leaf mac-refresh {
        type string;
      }
      container use-bia {
        presence "true";
        container scope {
          leaf interface {
            type empty;
          }
        }
      }
      list standby-list {
        // NCS patched for predictable order
        ordered-by user;
        key "group-number";
        leaf group-number {
          type string;
        }
        container authentication {
          choice auth {
            leaf word {
              type string;
            }
            container md5 {
              leaf key-chain {
                type string;
              }
              container key-string {
                leaf encrypt {
                  type string;
                }
                leaf string {
                  type string;
                }
                leaf timeout {
                  type string;
                }
              }
            }
            leaf text {
              type string;
            }
          }
        }
        leaf follow {
          type string;
        }
        container ip {
          presence "true";
          leaf address {
            type string;
          }
          leaf secondary {
            type empty;
          }
        }
        leaf ipv6 {
          type string;
        }
        leaf mac-address {
          type string;
        }
        leaf name {
          type string;
        }
        container preempt {
          presence "true";
          container delay {
            leaf minimum {
              type string;
            }
            leaf reload {
              type string;
            }
            leaf sync {
              type string;
            }
          }
        }
        leaf priority {
          type string;
        }
        container redirect {
          container advertisement {
            container authentication {
              container md5 {
                leaf key-chain {
                  type string;
                }
                container key-string {
                  leaf encrypt {
                    type string;
                  }
                  leaf string {
                    type string;
                  }
                  leaf timeout {
                    type string;
                  }
                }
              }
            }
          }
          container timers {
            leaf advertisement {
              type string;
            }
            leaf holddown {
              type string;
            }
          }
          leaf unknown {
            type empty;
          }
        }
        container timers {
          container hello-interval {
            choice hello-interval-choice {
              leaf seconds {
                type string;
              }
              leaf msec {
                type string;
              }
            }
          }
          container hold-time {
            choice hold-time-choice {
              leaf seconds {
                type string;
              }
              leaf msec {
                type string;
              }
            }
          }
        }
        list track {
          // NCS patched for predictable order
          ordered-by user;
          key "name";
          leaf name {
            type string;
          }
          choice options {
            case interface {
              leaf priority-decrement {
                type string;
              }
            }
            case group-number {
              leaf decrement {
                type string;
              }
              leaf shutdown {
                type empty;
              }
            }
          }
        }
      }
    }
    container storm-control {
      container action {
        leaf shutdown {
          type empty;
        }
        leaf trap {
          type empty;
        }
        leaf level {
          type string;
        }
      }
      container broadcast {
        leaf level {
          type string;
        }
        uses ncs_template_storm-control-level-bps-pps-grouping;
        container include {
          leaf multicast {
            type empty;
          }
        }
      }
      container multicast {
        leaf level {
          type string;
        }
        uses ncs_template_storm-control-level-bps-pps-grouping;
      }
      container unicast {
        leaf level {
          type string;
        }
        uses ncs_template_storm-control-level-bps-pps-grouping;
      }
    }
    container wrr-queue {
      container bandwidth {
        choice bandwidth-choice {
          case a {
            leaf weight-1 {
              type string;
            }
            leaf weight-2 {
              type string;
            }
            leaf weight-3 {
              type string;
            }
            leaf weight-4 {
              type string;
            }
            leaf weight-5 {
              type string;
            }
            leaf weight-6 {
              type string;
            }
            leaf weight-7 {
              type string;
            }
          }
          case b {
            container percent {
              leaf percent-1 {
                type string;
              }
              leaf percent-2 {
                type string;
              }
              leaf percent-3 {
                type string;
              }
              leaf percent-4 {
                type string;
              }
              leaf percent-5 {
                type string;
              }
              leaf percent-6 {
                type string;
              }
              leaf percent-7 {
                type string;
              }
            }
          }
        }
      }
      list dscp-map {
        // NCS patched for predictable order
        ordered-by user;
        key "queue threshold";
        leaf queue {
          type string;
        }
        leaf threshold {
          type string;
        }
        list values {
          // NCS patched for predictable order
          ordered-by user;
          key "value";
          leaf value {
            type string;
          }
        }
      }
      list cos-map {
        // NCS patched for predictable order
        ordered-by user;
        key "queue-id threshold-id";
        leaf queue-id {
          type string;
        }
        leaf threshold-id {
          type string;
        }
        leaf-list cos-values {
          // NCS patched for predictable order
          ordered-by user;
          // NCS drop max-elements statement
          type string;
        }
      }
      container queue-limit {
        leaf weight-a {
          type string;
        }
        leaf weight-b {
          type string;
        }
        leaf weight-c {
          type string;
        }
        leaf weight-d {
          type string;
        }
        leaf weight-e {
          type string;
        }
        leaf weight-f {
          type string;
        }
        leaf weight-g {
          type string;
        }
      }
      container random-detect {
        list max-threshold {
          // NCS patched for predictable order
          ordered-by user;
          key "id";
          leaf id {
            type string;
          }
          uses ncs_template_queue-size-grouping;
        }
        list min-threshold {
          // NCS patched for predictable order
          ordered-by user;
          key "id";
          leaf id {
            type string;
          }
          uses ncs_template_queue-size-grouping;
        }
      }
      list threshold {
        // NCS patched for predictable order
        ordered-by user;
        key "id";
        leaf id {
          type string;
        }
        uses ncs_template_queue-size-grouping;
      }
    }
    container priority-queue {
      leaf queue-limit {
        type string;
      }
      list dscp-map {
        // NCS patched for predictable order
        ordered-by user;
        key "id";
        leaf id {
          type string;
        }
        list values {
          // NCS patched for predictable order
          ordered-by user;
          key "value";
          leaf value {
            type string;
          }
        }
      }
      container cos-map {
        leaf id {
          type string;
        }
        leaf-list cos-values {
          // NCS patched for predictable order
          ordered-by user;
          // NCS drop max-elements statement
          type string;
        }
      }
      leaf out {
        type empty;
      }
    }
    container rep {
      container block {
        container port {
          choice port-choice {
            leaf neighbor-offset {
              type string;
            }
            leaf id {
              type string;
            }
            leaf preferred {
              type empty;
            }
          }
          leaf vlan {
            type string;
          }
        }
      }
      container preempt {
        leaf delay {
          type string;
        }
      }
      container segment {
        leaf id {
          type string;
        }
        leaf edge {
          type empty;
        }
        leaf primary {
          // NCS drop when statement
          type empty;
        }
        leaf preferred {
          type empty;
        }
      }
      container stcn {
        leaf segment {
          type string;
        }
        leaf stp {
          type empty;
        }
      }
    }
    container rcv-queue {
      list cos-map {
        // NCS patched for predictable order
        ordered-by user;
        key "queue-id threshold-id";
        leaf queue-id {
          type string;
        }
        leaf threshold-id {
          type string;
        }
        leaf-list cos-values {
          // NCS patched for predictable order
          ordered-by user;
          // NCS drop max-elements statement
          type string;
        }
      }
    }
    container udld {
      container port {
        presence "true";
        choice port-choice {
          leaf aggressive {
            type empty;
          }
          leaf disable {
            type empty;
          }
        }
      }
    }
    container peer {
      container default {
        container ip {
          container address {
            choice address-choice {
              leaf dhcp {
                type empty;
              }
              container dhcp-pool {
                presence "true";
                leaf pools {
                  type string;
                }
              }
              container pool {
                presence "true";
                leaf pools {
                  type string;
                }
              }
            }
          }
        }
      }
    }
    container clns {
      leaf route-cache {
        type string;
        // NCS drop default statement
      }
    }
    container dsu {
      leaf bandwidth {
        type string;
      }
    }
    container isdn {
      leaf switch-type {
        type string;
      }
      leaf protocol-emulate {
        type string;
      }
      container incoming-voice {
        choice incoming-voice-choice {
          leaf voice {
            type empty;
          }
          container data {
            presence "true";
            leaf kbps {
              type string;
            }
          }
          container modem {
            presence "true";
            leaf kbps {
              type string;
            }
          }
        }
      }
      container supp-service {
        container name {
          container calling {
            presence "true";
          }
        }
      }
    }
    leaf trunk-group {
      type string;
    }
    container crypto {
      container map {
        container ipv4 {
          leaf map-name {
            type string;
          }
          leaf redundancy {
            type string;
          }
          leaf stateful {
            // NCS drop when statement
            type empty;
          }
        }
        container ipv6 {
          leaf map-name {
            type string;
          }
          leaf redundancy {
            type string;
          }
          leaf stateful {
            // NCS drop when statement
            type empty;
          }
        }
      }
    }
    container routing {
      leaf dynamic {
        type string;
        // NCS drop default statement
      }
    }
  }

  grouping ncs_template_interface-tunnel-grouping {
    container tunnel {
      leaf source {
        type string;
      }
      leaf destination {
        type string;
      }
      container mode {
        choice mode-choice {
          container ipsec {
            container ipv4 {
              presence "true";
            }
          }
          container mpls {
            container traffic-eng {
              presence "true";
              leaf gre-ip {
                type empty;
              }
            }
          }
        }
      }
      container path-mtu-discovery {
        presence "true";
      }
      container protection {
        container ipsec {
          leaf profile {
            type string;
          }
        }
      }
      container mpls {
        container traffic-eng {
          container affinity {
            leaf attributes {
              type string;
            }
            leaf mask {
              type string;
            }
          }
          container autoroute {
            leaf announce {
              type empty;
            }
          }
          container priority {
            leaf setup-priority {
              type string;
            }
            leaf hold-priority {
              type string;
            }
          }
          leaf bandwidth {
            type string;
          }
          list path-option {
            // NCS patched for predictable order
            ordered-by user;
            key "id";
            leaf id {
              type string;
            }
            choice path-option-choice {
              container dynamic {
                presence "true";
              }
              container explicit {
                choice explicit-choice {
                  leaf name {
                    type string;
                  }
                  leaf identifier {
                    type string;
                  }
                }
              }
            }
            container lockdown {
              presence "true";
            }
          }
          container fast-reroute {
            presence "true";
          }
        }
      }
    }
  }

  grouping ncs_template_interface-ethernet-pre-grouping {
    leaf port-type {
      type string;
    }
  }

  grouping ncs_template_interface-ethernet-grouping {
    leaf media-type {
      type string;
    }
    container carrier-delay {
      choice delay-choice {
        leaf seconds {
          type string;
        }
        leaf msec {
          type string;
        }
      }
    }
    container channel-group {
      leaf number {
        type string;
      }
      leaf mode {
        type string;
      }
    }
    leaf channel-protocol {
      type string;
    }
    container ethernet {
      container oam {
        presence "true";
        leaf max-rate {
          type string;
        }
        leaf min-rate {
          type string;
        }
        leaf mode {
          type string;
        }
        leaf timeout {
          type string;
        }
      }
      container dot1ad {
        choice dot1ad-choice {
          leaf nni {
            type empty;
          }
          container uni {
            choice uni-choice {
              container c-port {
                presence "true";
                leaf isolate {
                  type empty;
                }
              }
              container s-port {
                presence "true";
                leaf isolate {
                  type empty;
                }
              }
            }
          }
        }
      }
      container cfm {
        container mep {
          list mep-list {
            // NCS patched for predictable order
            ordered-by user;
            key "mpid";
            leaf mpid {
              type string;
            }
            leaf domain {
              type string;
            }
            container service {
              choice service-choice {
                leaf short-ma-name {
                  type string;
                }
                leaf number {
                  type string;
                }
              }
            }
          }
        }
      }
    }
    container negotiation {
      leaf auto {
        type string;
      }
    }
    container synchronous {
      leaf mode {
        type empty;
      }
    }
    leaf duplex {
      // NCS drop tailf-common:cli-diff-dependency statement
      type string;
    }
    leaf full-duplex {
      type empty;
    }
    leaf speed {
      // NCS drop tailf-common:cli-diff-dependency statement
      type string;
    }
    uses ncs_template_interface-xconnect-grouping;
    container pppoe {
      container enable {
        presence "true";
        leaf group {
          type string;
        }
      }
      leaf max-sessions {
        type string;
      }
    }
    container service {
      // NCS drop tailf-common:cli-diff-dependency statement
      list instance {
        // NCS patched for predictable order
        ordered-by user;
        // NCS drop tailf-common:cli-diff-dependency statement
        key "id";
        leaf id {
          type string;
        }
        leaf trunk {
          type empty;
        }
        leaf ethernet {
          type empty;
        }
        leaf ethernet-evc-name {
          type string;
        }
        leaf description {
          type string;
        }
        leaf evc-name {
          type string;
        }
        container encapsulation {
          container dot1q {
            leaf-list id {
              // NCS patched for predictable order
              ordered-by user;
              type string;
            }
            leaf second-dot1q {
              type string;
            }
            leaf cos {
              type string;
            }
            leaf etype {
              type string;
            }
          }
          container dot1ad {
            leaf-list id {
              // NCS patched for predictable order
              ordered-by user;
              type string;
            }
          }
          container untagged {
            presence "true";
          }
          container default {
            presence "true";
          }
        }
        container rewrite {
          container ingress {
            container tag {
              choice tag-choice {
                leaf pop {
                  type string;
                }
                case push {
                  leaf push {
                    type string;
                  }
                  leaf vlan-id {
                    type string;
                  }
                }
              }
              leaf mode {
                type string;
              }
            }
          }
        }
        leaf group {
          type string;
        }
        container errdisable {
          container recovery {
            container cause {
              leaf mac-security {
                type string;
              }
            }
          }
        }
        container snmp {
          container trap {
            leaf link-status {
              type empty;
            }
          }
          container ifindex {
            leaf persist {
              type empty;
            }
          }
        }
        leaf shutdown {
          type empty;
        }
        container bridge-domain {
          leaf from-encapsulation {
            type empty;
          }
          leaf bridge-id {
            type string;
          }
          container split-horizon {
            leaf group {
              type string;
            }
          }
        }
        container mac {
          container security {
            presence "true";
            list address {
              // NCS patched for predictable order
              ordered-by user;
              key "operation mac-address";
              leaf operation {
                type string;
              }
              leaf mac-address {
                type string;
              }
            }
            container maximum {
              leaf addresses {
                type string;
              }
            }
            leaf violation {
              type string;
            }
          }
          container static {
            list address {
              // NCS patched for predictable order
              ordered-by user;
              key "mac-addr";
              leaf mac-addr {
                type string;
              }
            }
          }
          list access-group {
            // NCS patched for predictable order
            ordered-by user;
            key "direction";
            leaf direction {
              type string;
            }
            leaf access-list {
              type string;
            }
          }
        }
        container l2protocol {
          container peer {
            presence "true";
            leaf-list protocol {
              // NCS patched for predictable order
              ordered-by user;
              type string;
            }
          }
          container forward {
            presence "true";
            leaf-list protocol {
              // NCS patched for predictable order
              ordered-by user;
              type string;
            }
          }
          container tunnel {
            presence "true";
          }
        }
        container service-policy {
          // NCS drop tailf-common:cli-diff-dependency statement
          list input {
            // NCS patched for predictable order
            ordered-by user;
            // NCS drop max-elements statement
            key "name";
            leaf name {
              type string;
            }
          }
          list output {
            // NCS patched for predictable order
            ordered-by user;
            // NCS drop max-elements statement
            key "name";
            leaf name {
              type string;
            }
          }
        }
        uses ncs_template_interface-xconnect-grouping;
        container cfm {
          container mep {
            leaf domain {
              type string;
            }
            leaf mpid {
              type string;
            }
            container continuity-check {
              container static {
                leaf rmep {
                  type empty;
                }
              }
            }
            container rmep {
              leaf mpid {
                type string;
              }
            }
            leaf cos {
              type string;
            }
          }
        }
        container ethernet-if-srv {
          container ethernet {
            container lmi {
              container ce-vlan {
                leaf-list map {
                  // NCS patched for predictable order
                  ordered-by user;
                  type string;
                }
              }
            }
            container loopback {
              container permit {
                leaf external {
                  type empty;
                }
                leaf internal {
                  type empty;
                }
              }
            }
          }
        }
      }
    }
  }

  grouping ncs_template_interface-zone-member-grouping {
    container zone-member {
      leaf security {
        type string;
      }
    }
  }

  grouping ncs_template_interface-pointtopoint-grouping {
    container ppp {
      leaf accounting {
        type string;
      }
      container authentication {
        leaf method {
          type string;
        }
        leaf list-name {
          type string;
        }
        leaf chap {
          // NCS drop when statement
          type empty;
        }
        leaf callback {
          type empty;
        }
        leaf callin {
          type empty;
        }
        leaf callout {
          type empty;
        }
        leaf default {
          type empty;
        }
        leaf eap {
          // NCS drop when statement
          type empty;
        }
        leaf ms-chap {
          // NCS drop when statement
          type empty;
        }
        leaf ms-chap-v2 {
          // NCS drop when statement
          type empty;
        }
        leaf one-time {
          type empty;
        }
        leaf optional {
          type empty;
        }
        leaf pap {
          // NCS drop when statement
          type empty;
        }
      }
      leaf authorization {
        type string;
      }
      container ipcp {
        container dns {
          leaf primary {
            type string;
          }
        }
      }
      container multilink {
        presence "true";
        leaf interleave {
          type empty;
        }
        container links {
          container minimum {
            leaf minimum-value {
              type string;
            }
            leaf mandatory {
              type empty;
            }
          }
        }
        leaf group {
          type string;
        }
        container fragment {
          leaf disable {
            type empty;
          }
          container delay {
            leaf delay-value {
              type string;
            }
            leaf additional-delay-value {
              type string;
            }
          }
        }
        container queue {
          container depth {
            leaf fifo {
              type string;
            }
            leaf qos {
              type string;
            }
          }
        }
      }
    }
    container dialer {
      container in-band {
        presence "true";
        leaf parity {
          type string;
        }
      }
      container idle-timeout {
        leaf seconds {
          type string;
        }
        leaf direction {
          type string;
        }
      }
      leaf enable-timeout {
        type string;
      }
      leaf string {
        type string;
      }
      leaf watch-group {
        type string;
      }
    }
    leaf physical-layer {
      type string;
    }
    container async {
      container mode {
        leaf dedicated {
          type empty;
        }
        leaf interactive {
          type empty;
        }
      }
    }
    container pulse-time {
      choice pulse-time-choice {
        leaf seconds {
          type string;
        }
        leaf msec {
          type string;
        }
      }
    }
  }

  grouping ncs_template_crypto-pki-token-grouping {
    container removal {
      leaf timeout {
        type string;
      }
    }
  }

  grouping ncs_template_router-bgp-max-path-grouping {
    container paths {
      leaf number-of-paths {
        type string;
        // NCS drop default statement
      }
      leaf import {
        type string;
      }
    }
  }

  grouping ncs_template_router-bgp-redistribute-grouping {
    leaf metric {
      type string;
    }
    leaf route-map {
      type string;
    }
  }

  grouping ncs_template_route-map-metric-grouping {
    leaf route-map {
      type string;
    }
    leaf metric {
      type string;
    }
  }

  grouping ncs_template_redistribute-isis-grouping {
    choice osi-ip-choice {
      leaf ip {
        type empty;
      }
      leaf clns {
        type empty;
      }
    }
    leaf level {
      type string;
    }
    uses ncs_template_router-bgp-redistribute-grouping;
  }

  grouping ncs_template_router-bgp-grouping {
    container bgp-top {
      container bgp {
        container bestpath {
          container as-path {
            leaf multipath-relax {
              type empty;
            }
          }
        }
      }
    }
    container timers {
      container bgp {
        leaf keepalive {
          type string;
        }
        leaf holdtime {
          type string;
        }
        leaf min-holdtime {
          type string;
        }
      }
    }
  }

  grouping ncs_template_router-bgp-peer-policy-grouping {
    leaf advertisement-interval {
      type string;
    }
    container send-community {
      presence "true";
      leaf send-community-where {
        type string;
      }
    }
    container maximum-prefix {
      leaf max-prefix-no {
        type string;
      }
      leaf threshold {
        type string;
      }
      leaf restart {
        type string;
      }
      leaf warning-only {
        type empty;
      }
    }
    container allowas-in {
      presence "accept as-paths";
      leaf as-number {
        type string;
      }
    }
    container as-override {
      presence "true";
      leaf disable {
        type empty;
      }
    }
  }

  grouping ncs_template_router-bgp-peer-session-grouping {
    leaf remote-as {
      type string;
    }
    container password {
      leaf enctype {
        type string;
      }
      leaf text {
        type string;
      }
    }
    container ttl-security {
      leaf hops {
        type string;
      }
    }
    container timers {
      leaf keepalive-interval {
        type string;
      }
      leaf holdtime {
        type string;
      }
      leaf minimum-neighbor-hold {
        type string;
      }
    }
    container fall-over {
      presence "true";
      leaf bfd {
        type empty;
      }
      leaf route-map {
        type string;
      }
    }
  }

  grouping ncs_template_router-bgp-neighbor-grouping {
    container peer-group {
      presence "true";
      leaf peer-group-name {
        type string;
      }
    }
    container local-as {
      presence "Specify a local-as number";
      leaf as-no {
        type string;
      }
      leaf no-prepend {
        type empty;
      }
      leaf replace-as {
        type empty;
      }
      leaf dual-as {
        type empty;
      }
    }
    uses ncs_template_router-bgp-peer-session-grouping;
    leaf activate {
      type empty;
    }
    uses ncs_template_router-bgp-peer-policy-grouping;
    leaf soo {
      type string;
    }
    container capability {
      container orf {
        leaf-list prefix-list {
          // NCS patched for predictable order
          ordered-by user;
          // NCS drop max-elements statement
          type string;
        }
      }
    }
    container default-originate {
      presence "enable originate default route to this neighbour";
      leaf route-map {
        type string;
      }
    }
    leaf description {
      type string;
    }
    leaf disable-connected-check {
      type empty;
    }
    uses ncs_template_router-distribute-list-grouping;
    leaf dmzlink-bw {
      type empty;
    }
    container ebgp-multihop {
      presence "Allow EBGP neighbors not on directly connected networks";
      leaf max-hop {
        type string;
      }
    }
    list filter-list {
      // NCS patched for predictable order
      ordered-by user;
      key "inout";
      leaf inout {
        type string;
      }
      leaf as-path-list {
        type string;
        // NCS drop mandatory statement
      }
    }
    container inherit {
      leaf peer-policy {
        type string;
      }
      leaf peer-session {
        type string;
      }
    }
    leaf next-hop-self {
      type empty;
    }
    container next-hop-self-arg {
      leaf next-hop-self {
        type string;
      }
    }
    leaf next-hop-unchanged {
      type empty;
    }
    list prefix-list {
      // NCS patched for predictable order
      ordered-by user;
      key "direction";
      leaf direction {
        type string;
      }
      leaf prefix-list-name {
        type string;
        // NCS drop mandatory statement
      }
    }
    leaf remove-private-as {
      type empty;
    }
    list route-map {
      // NCS patched for predictable order
      ordered-by user;
      key "direction";
      leaf direction {
        type string;
      }
      leaf route-map-name {
        type string;
        // NCS drop mandatory statement
      }
    }
    leaf route-reflector-client {
      type empty;
    }
    container send-label {
      presence "true";
      leaf explicit-null {
        type empty;
      }
    }
    leaf shutdown {
      type empty;
    }
    leaf soft-reconfiguration {
      type string;
    }
    container translate-update {
      container ipv4 {
        container multicast {
          presence "Address Family modifier";
          leaf unicast {
            type empty;
          }
        }
      }
    }
    container transport {
      leaf connection-mode {
        type string;
      }
    }
    leaf unsuppress-map {
      type string;
    }
    container update-source {
      uses ncs_template_interface-name-grouping;
    }
    leaf version {
      type string;
    }
    leaf weight {
      type string;
    }
    container ha-mode {
      container graceful-restart {
        presence "true";
        leaf disable {
          type empty;
        }
      }
      container sso {
        presence "true";
        leaf disable {
          type empty;
        }
      }
    }
    container suppress-signaling-protocol {
      leaf ldp {
        type empty;
      }
    }
    leaf prefix-length-size {
      type string;
    }
  }

  grouping ncs_template_router-bgp-af-grouping {
    container aggregate-address {
      leaf address {
        type string;
      }
      leaf mask {
        type string;
      }
      leaf advertise-map {
        type string;
      }
      leaf as-set {
        type empty;
      }
      leaf attribute-map {
        type string;
      }
      leaf as-override {
        type empty;
      }
      leaf route-map {
        type string;
      }
      leaf summary-only {
        type empty;
      }
      leaf suppress-map {
        type string;
      }
    }
    container bgp {
      leaf router-id {
        type string;
      }
      leaf always-compare-med {
        type empty;
      }
      container bestpath {
        leaf compare-routerid {
          type empty;
        }
        container cost-community {
          leaf ignore {
            type empty;
          }
        }
        container med {
          choice med-choice {
            container confed {
              presence "Compare MED among confederation paths";
              leaf missing-at-worst {
                type empty;
              }
            }
            leaf missing-at-worst {
              type empty;
            }
          }
        }
      }
      container client-to-client {
        leaf reflection {
          type empty;
        }
      }
      leaf cluster-id {
        type string;
      }
      container confederation {
        leaf identifier {
          type string;
        }
        container peers {
          presence "Peer ASs in BGP confederation";
          leaf-list peers-as {
            // NCS patched for predictable order
            ordered-by user;
            type string;
          }
        }
      }
      container dampening {
        presence "true";
        choice dampening-choice {
          leaf route-map {
            type string;
          }
          container dampen {
            leaf half-life-time {
              type string;
            }
            leaf reuse-time {
              type string;
            }
            leaf suppress-time {
              type string;
            }
            leaf max-suppress-time {
              type string;
            }
          }
        }
      }
      container default {
        leaf ipv4-unicast {
          type string;
          // NCS drop default statement
        }
        leaf ipv4-activate {
          type string;
          // NCS drop default statement
        }
        leaf local-preference {
          type string;
        }
        container route-target {
          leaf filter {
            type string;
            // NCS drop default statement
          }
        }
      }
      leaf deterministic-med {
        type empty;
      }
      leaf dmzlink-bw {
        type empty;
      }
      leaf enforce-first-as {
        type empty;
      }
      leaf fast-external-fallover {
        type empty;
      }
      container graceful-restart {
        presence "true";
        leaf restart-time {
          type string;
        }
        leaf stalepath-time {
          type string;
        }
      }
      list inject-map {
        // NCS patched for predictable order
        ordered-by user;
        key "name";
        leaf name {
          type string;
        }
        leaf exist-map {
          type string;
        }
        leaf copy-attributes {
          type empty;
        }
      }
      container transport {
        leaf path-mtu-discovery {
          type string;
          // NCS drop default statement
        }
      }
      leaf log-neighbor-changes {
        type empty;
      }
      container listen {
        presence "true";
        container range {
          leaf network-length {
            type string;
          }
          leaf peer-group {
            type string;
          }
        }
        leaf limit {
          type string;
        }
      }
      leaf maxas-limit {
        type string;
      }
      container additional-paths {
        choice send-receive-choice {
          leaf receive {
            type empty;
          }
          container send {
            presence "true";
            leaf receive {
              type empty;
            }
          }
        }
        leaf install {
          type empty;
        }
      }
      container nexthop {
        container trigger {
          leaf delay {
            type string;
          }
          leaf enable {
            type string;
            // NCS drop default statement
          }
        }
      }
      leaf redistribute-internal {
        type empty;
      }
      container regexp {
        leaf deterministic {
          type empty;
        }
      }
      leaf scan-time {
        type string;
      }
      leaf soft-reconfig-backup {
        type empty;
      }
      leaf suppress-inactive {
        type empty;
      }
      leaf update-delay {
        type string;
      }
    }
    container default-information {
      leaf originate {
        type empty;
      }
    }
    leaf default-metric {
      type string;
    }
    container distance {
      container bgp {
        leaf extern-as {
          type string;
        }
        leaf internal-as {
          type string;
        }
        leaf local {
          type string;
        }
      }
      list adm-distance {
        // NCS patched for predictable order
        ordered-by user;
        key "distance srcip wildbits";
        leaf distance {
          type string;
        }
        leaf srcip {
          type string;
        }
        leaf wildbits {
          type string;
        }
        leaf access-list {
          type string;
        }
      }
    }
    uses ncs_template_router-distribute-list-grouping;
    container maximum-paths {
      uses ncs_template_router-bgp-max-path-grouping;
      container eibgp {
        uses ncs_template_router-bgp-max-path-grouping;
      }
      container ibgp {
        choice ibgp-choice {
          // NCS drop default statement
          case a {
            container unequal-cost {
              uses ncs_template_router-bgp-max-path-grouping;
            }
          }
          case b {
            uses ncs_template_router-bgp-max-path-grouping;
          }
        }
      }
      leaf import {
        type string;
      }
    }
    container import {
      container path {
        container selection {
          choice selection-choice {
            leaf all {
              type empty;
            }
            container bestpath {
              presence "true";
              leaf strict {
                type empty;
              }
            }
            container multipaths {
              presence "true";
              leaf strict {
                type empty;
              }
            }
          }
        }
        leaf limit {
          type string;
        }
      }
    }
    container redistribute {
      container bgp {
        leaf as-no {
          type string;
        }
        uses ncs_template_router-bgp-redistribute-grouping;
      }
      container connected {
        presence "Connected";
        uses ncs_template_router-bgp-redistribute-grouping;
      }
      container static {
        presence "true";
        uses ncs_template_router-bgp-redistribute-grouping;
      }
      container dvmrp {
        presence "true";
        uses ncs_template_route-map-metric-grouping;
      }
      list eigrp {
        // NCS patched for predictable order
        ordered-by user;
        key "as-number";
        leaf as-number {
          type string;
        }
        uses ncs_template_router-bgp-redistribute-grouping;
      }
      container isis {
        presence "true";
        uses ncs_template_redistribute-isis-grouping;
        list isis-list {
          // NCS patched for predictable order
          ordered-by user;
          key "name";
          leaf name {
            type string;
          }
          uses ncs_template_redistribute-isis-grouping;
        }
      }
      container iso-igrp {
        uses ncs_template_route-map-metric-grouping;
        list iso-igrp-area {
          // NCS patched for predictable order
          ordered-by user;
          key "name";
          leaf name {
            type string;
          }
          uses ncs_template_route-map-metric-grouping;
        }
      }
      container mobile {
        presence "Mobile routes";
        uses ncs_template_router-bgp-redistribute-grouping;
      }
      container odr {
        presence "On Demand stub Routes";
        uses ncs_template_router-bgp-redistribute-grouping;
      }
      list ospf {
        // NCS patched for predictable order
        ordered-by user;
        key "id";
        leaf id {
          type string;
        }
        list vrf {
          // NCS patched for predictable order
          ordered-by user;
          // NCS drop tailf-common:cli-diff-dependency statement
          // NCS drop tailf-common:cli-diff-dependency statement
          key "name";
          leaf name {
            type string;
          }
          container match {
            uses ncs_template_redistribute-ospf-match-grouping;
            uses ncs_template_router-bgp-redistribute-grouping;
          }
        }
        container non-vrf {
          container match {
            uses ncs_template_redistribute-ospf-match-grouping;
            uses ncs_template_router-bgp-redistribute-grouping;
          }
        }
      }
      container rip {
        presence "true";
        uses ncs_template_router-bgp-redistribute-grouping;
      }
    }
    container neighbor-tag {
      list neighbor {
        // NCS patched for predictable order
        ordered-by user;
        key "id";
        leaf id {
          type string;
        }
        uses ncs_template_router-bgp-neighbor-grouping;
      }
    }
    list neighbor {
      // NCS patched for predictable order
      ordered-by user;
      key "id";
      leaf id {
        type string;
      }
      uses ncs_template_router-bgp-neighbor-grouping;
    }
    list network {
      // NCS patched for predictable order
      ordered-by user;
      key "number";
      leaf number {
        type string;
      }
      leaf backdoor {
        type empty;
      }
      leaf mask {
        type string;
      }
      leaf route-map {
        type string;
      }
    }
    leaf synchronization {
      type empty;
    }
    leaf auto-summary {
      type string;
    }
    leaf table-map {
      type string;
    }
  }

  grouping ncs_template_router-ospf-af-grouping;

  grouping ncs_template_router-ospfv3-af-grouping {
    container discard-route {
      leaf external {
        type string;
        // NCS drop default statement
      }
      leaf internal {
        type string;
        // NCS drop default statement
      }
    }
  }

  grouping ncs_template_router-ospf-common-af-grouping {
    container default-information {
      container originate {
        presence "true";
        leaf always {
          type empty;
        }
        leaf metric {
          type string;
        }
        leaf metric-type {
          type string;
          // NCS drop default statement
        }
        leaf route-map {
          type string;
        }
      }
    }
    leaf default-metric {
      type string;
    }
    container distance {
      leaf weight {
        type string;
      }
      list distance-list {
        // NCS patched for predictable order
        ordered-by user;
        key "ip-address wildcard-mask";
        leaf ip-address {
          type string;
        }
        leaf wildcard-mask {
          type string;
        }
        leaf weight {
          type string;
        }
        leaf access-list {
          type string;
        }
      }
      container ospf {
        leaf intra-area {
          type string;
        }
        leaf inter-area {
          type string;
        }
        leaf external {
          type string;
        }
      }
    }
    leaf maximum-paths {
      type string;
    }
    container redistribute {
      container bgp {
        leaf as-number {
          type string;
        }
        uses ncs_template_router-ospf-redistribute-grouping;
      }
      container connected {
        presence "Connected";
        uses ncs_template_router-ospf-redistribute-grouping;
      }
      list eigrp {
        // NCS patched for predictable order
        ordered-by user;
        key "as-number";
        leaf as-number {
          type string;
        }
        uses ncs_template_router-ospf-redistribute-grouping;
      }
      container isis {
        presence "true";
        list isis-area {
          // NCS patched for predictable order
          ordered-by user;
          key "name";
          leaf name {
            type string;
          }
          uses ncs_template_router-ospf-redistribute-grouping;
        }
        uses ncs_template_router-ospf-redistribute-grouping;
      }
      container iso-igrp {
        presence "true";
        leaf area-tag {
          type string;
        }
        leaf route-map {
          type string;
        }
        uses ncs_template_ospf-iso-igrp-redistribute-grouping;
      }
      container maximum-prefix {
        leaf number {
          type string;
        }
        container threshold-warning-only-container {
          leaf threshold {
            type string;
          }
          leaf warning-only {
            type empty;
          }
        }
      }
      container mobile {
        presence "true";
        uses ncs_template_router-ospf-redistribute-grouping;
      }
      container odr {
        presence "true";
        uses ncs_template_router-ospf-redistribute-grouping;
      }
      list ospf {
        // NCS patched for predictable order
        ordered-by user;
        key "id";
        leaf id {
          type string;
        }
        uses ncs_template_router-ospf-redistribute-grouping;
        container match {
          uses ncs_template_redistribute-ospf-match-grouping;
          uses ncs_template_ospf-redistribute-match-grouping;
        }
      }
      container rip {
        presence "true";
        uses ncs_template_router-ospf-redistribute-grouping;
        list redistribute-list-rip {
          // NCS patched for predictable order
          ordered-by user;
          key "name";
          leaf name {
            type string;
          }
          uses ncs_template_router-ospf-redistribute-grouping;
        }
      }
      container static {
        presence "Static routes";
        uses ncs_template_router-ospf-redistribute-grouping;
      }
    }
  }

  grouping ncs_template_router-ospf-common-grouping {
    list area {
      // NCS patched for predictable order
      ordered-by user;
      key "id";
      leaf id {
        type string;
      }
      container authentication {
        presence "true";
        leaf message-digest {
          type empty;
        }
      }
      container nssa {
        presence "true";
        leaf no-redistribution {
          type empty;
        }
        leaf default-information-originate {
          type empty;
        }
        leaf metric {
          // NCS drop when statement
          type string;
        }
        leaf metric-type {
          // NCS drop when statement
          type string;
          // NCS drop default statement
        }
        leaf nssa-only {
          type empty;
        }
        leaf no-ext-capability {
          type empty;
        }
        leaf no-summary {
          type empty;
        }
        container translate {
          container type7 {
            leaf always {
              type empty;
            }
            leaf suppress-fa {
              type empty;
            }
          }
        }
      }
      leaf default-cost {
        type string;
      }
      list filter-list {
        // NCS patched for predictable order
        ordered-by user;
        key "direction";
        leaf prefix {
          // NCS drop mandatory statement
          type string;
        }
        leaf direction {
          type string;
        }
      }
      list range {
        // NCS patched for predictable order
        ordered-by user;
        key "ip mask";
        leaf ip {
          type string;
        }
        leaf mask {
          type string;
        }
        choice advertise-choice {
          leaf advertise {
            type empty;
          }
          leaf not-advertise {
            type empty;
          }
        }
        leaf cost {
          type string;
        }
      }
      container range-ipv6 {
        list range {
          // NCS patched for predictable order
          ordered-by user;
          key "prefix";
          leaf prefix {
            type string;
          }
          choice advertise-choice {
            leaf advertise {
              type empty;
            }
            leaf not-advertise {
              type empty;
            }
          }
          leaf cost {
            type string;
          }
        }
      }
      list sham-link {
        // NCS patched for predictable order
        ordered-by user;
        key "source dest";
        leaf source {
          type string;
        }
        leaf dest {
          type string;
        }
        leaf cost {
          type string;
        }
      }
      container stub {
        presence "true";
        leaf no-summary {
          type empty;
        }
        leaf no-ext-capability {
          type empty;
        }
      }
      list virtual-link {
        // NCS patched for predictable order
        ordered-by user;
        key "id";
        leaf id {
          type string;
        }
        leaf retransmit-interval {
          type string;
        }
        leaf transmit-delay {
          type string;
          // NCS drop default statement
        }
        leaf hello-interval {
          type string;
        }
        leaf dead-interval {
          type string;
        }
        leaf authentication {
          type empty;
        }
        container authentication-key {
          leaf auth-type {
            type string;
            // NCS drop default statement
          }
          leaf auth-key {
            type string;
          }
        }
        list message-digest-key {
          // NCS patched for predictable order
          ordered-by user;
          key "id";
          leaf id {
            type string;
          }
          container md5 {
            leaf auth-type {
              type string;
              // NCS drop default statement
            }
            leaf auth-key {
              type string;
            }
          }
        }
      }
    }
    container auto-cost {
      presence "Calculate OSPF interface cost according to bandwidth";
      leaf reference-bandwidth {
        type string;
      }
    }
    container bfd {
      leaf all-interfaces {
        type empty;
      }
    }
    container interface-id {
      leaf snmp-if-index {
        type empty;
      }
    }
    container log-adjacency-changes {
      presence "true";
      leaf detail {
        type empty;
      }
    }
    container max-lsa {
      leaf maximum-number {
        type string;
      }
      leaf threshold-percentage {
        type string;
      }
      leaf warning-only {
        type empty;
      }
      leaf ignore-time {
        type string;
      }
      leaf reset-time {
        type string;
        // NCS drop default statement
      }
      leaf ignore-count {
        type string;
      }
    }
    uses ncs_template_passive-interface-grouping;
    container queue-depth {
      leaf hello {
        type string;
        // NCS drop default statement
      }
      leaf update {
        type string;
      }
    }
    container timers {
      container lsa {
        leaf arrival {
          type string;
        }
      }
      container pacing {
        leaf flood {
          type string;
        }
        leaf lsa-group {
          type string;
        }
        leaf retransmission {
          type string;
        }
      }
      container throttle {
        container lsa {
          leaf all {
            type empty;
          }
          leaf start-interval {
            type string;
          }
          leaf hold-interval {
            type string;
          }
          leaf max-interval {
            type string;
          }
        }
        container spf {
          leaf spf-start {
            type string;
          }
          leaf spf-hold {
            type string;
          }
          leaf spf-max-wait {
            type string;
          }
        }
      }
    }
    leaf router-id {
      type string;
    }
  }

  grouping ncs_template_router-ospf-grouping {
    container capability {
      leaf opaque {
        type string;
        // NCS drop default statement
      }
      leaf lls {
        type string;
        // NCS drop default statement
      }
      leaf transit {
        type string;
        // NCS drop default statement
      }
    }
    container compatible {
      leaf rfc1583 {
        type string;
        // NCS drop default statement
      }
    }
    uses ncs_template_router-distribute-list-grouping;
    container domain-id {
      choice domain-id-choice {
        case a {
          leaf ip-format {
            type string;
          }
          container ip-format-secondary {
            leaf ip {
              type string;
            }
            leaf secondary {
              type empty;
            }
          }
        }
        leaf Null {
          type empty;
        }
        container type {
          leaf type-leaf {
            type string;
          }
          leaf value {
            type string;
          }
        }
      }
    }
    leaf domain-tag {
      type string;
    }
    container ignore {
      container lsa {
        leaf mospf {
          type empty;
        }
      }
    }
    leaf ispf {
      type empty;
    }
    container limit {
      container retransmissions {
        leaf dc {
          type string;
        }
        leaf non-dc {
          type string;
        }
      }
    }
    container local-rib-criteria {
      leaf forwarding-address {
        type empty;
      }
      leaf inter-area-summary {
        type empty;
      }
      leaf nssa-translation {
        type empty;
      }
    }
    container max-metric {
      container router-lsa {
        presence "true";
        leaf include-stub {
          type empty;
        }
        leaf summary-lsa {
          type empty;
        }
        leaf summary-lsa-max-metric-value {
          // NCS drop when statement
          type string;
        }
        leaf external-lsa {
          type empty;
        }
        leaf external-lsa-max-metric-value {
          // NCS drop when statement
          type string;
        }
        container on-startup {
          choice time-wait-for-bgp-choice {
            leaf seconds {
              type string;
            }
            leaf wait-for-bgp {
              type empty;
            }
          }
        }
      }
    }
    container mpls {
      container ldp {
        container autoconfig {
          presence "Configure LDP automatic configuration";
          leaf area {
            type string;
          }
        }
        container sync {
          presence "Configure LDP-IGP Synchronization";
        }
      }
      container traffic-eng {
        leaf multicast-intact {
          type empty;
        }
        leaf area {
          type string;
        }
        container interface {
          leaf name {
            type string;
          }
          leaf area {
            type string;
          }
        }
        container mesh-group-container {
          leaf mesh-group {
            type string;
          }
          leaf interface {
            type string;
          }
          list area {
            // NCS patched for predictable order
            ordered-by user;
            key "id";
            leaf id {
              type string;
            }
          }
        }
        container router-id {
          leaf interface {
            type string;
          }
        }
      }
    }
    list neighbor {
      // NCS patched for predictable order
      ordered-by user;
      key "ip";
      leaf ip {
        type string;
      }
      container cost-database-filter-container {
        leaf cost {
          type string;
        }
        container database-filter {
          container all {
            leaf out {
              type empty;
            }
          }
        }
      }
      container poll-interval-priority-container {
        leaf poll-interval {
          type string;
        }
        leaf priority {
          type string;
        }
      }
    }
    list network {
      // NCS patched for predictable order
      ordered-by user;
      key "ip mask";
      leaf ip {
        type string;
      }
      leaf mask {
        type string;
      }
      leaf area {
        type string;
      }
    }
    container nsf {
      presence "true";
      container cisco {
        presence "true";
        container helper {
          presence "true";
          leaf disable {
            type empty;
          }
        }
      }
      container ietf {
        container helper {
          presence "helper support";
          leaf disable {
            type empty;
          }
          leaf strict-lsa-checking {
            type empty;
          }
        }
      }
    }
    leaf prefix-suppression {
      type empty;
    }
    container process-min-time {
      leaf percent {
        type string;
      }
    }
    container traffic-share {
      container min {
        leaf across-interfaces {
          type empty;
        }
      }
    }
    leaf shutdown {
      type string;
    }
    list summary-address {
      // NCS patched for predictable order
      ordered-by user;
      key "ip wildcard";
      leaf ip {
        type string;
      }
      leaf wildcard {
        type string;
      }
      choice tag-no-advertise-choice {
        leaf tag {
          type string;
        }
        leaf not-advertise {
          type empty;
        }
      }
    }
    container discard-route {
      presence "true";
      leaf external {
        type string;
      }
      leaf internal {
        type string;
      }
    }
  }

  grouping ncs_template_router-ospfv3-grouping;

  grouping ncs_template_ospf-redistribute-match-grouping {
    leaf metric {
      type string;
    }
    leaf subnets {
      type empty;
    }
    leaf route-map {
      type string;
    }
    leaf tag {
      type string;
    }
  }

  grouping ncs_template_ospf-iso-igrp-redistribute-grouping {
    leaf metric {
      type string;
    }
    leaf metric-type {
      type string;
      // NCS drop default statement
    }
    leaf tag {
      type string;
    }
    leaf level {
      type string;
    }
    leaf subnets {
      type empty;
    }
  }

  grouping ncs_template_router-ospf-redistribute-grouping {
    uses ncs_template_ospf-iso-igrp-redistribute-grouping;
    leaf route-map {
      type string;
    }
  }

  grouping ncs_template_router-rip-af-grouping {
    leaf auto-summary {
      type string;
      // NCS drop default statement
    }
    leaf maximum-paths {
      type string;
    }
    list neighbor {
      // NCS patched for predictable order
      ordered-by user;
      key "ip";
      leaf ip {
        type string;
      }
    }
    list network {
      // NCS patched for predictable order
      ordered-by user;
      key "ip";
      leaf ip {
        type string;
      }
    }
    leaf validate-update-source {
      type string;
      // NCS drop default statement
    }
    container default-information {
      container originate {
        presence "true";
        leaf route-map {
          type string;
        }
      }
    }
    leaf default-metric {
      type string;
    }
    container distance {
      leaf distance-leaf {
        type string;
      }
      list distance-list {
        // NCS patched for predictable order
        ordered-by user;
        key "number ip mask";
        leaf number {
          type string;
        }
        leaf ip {
          type string;
        }
        leaf mask {
          type string;
        }
        leaf access-list {
          type string;
        }
      }
    }
    uses ncs_template_router-distribute-list-grouping;
    list offset-list {
      // NCS patched for predictable order
      ordered-by user;
      key "direction";
      leaf direction {
        type string;
      }
      leaf id {
        type string;
      }
      leaf offset {
        type string;
      }
    }
    container redistribute {
      container connected {
        presence "true";
        uses ncs_template_rip-metric-route-map-grouping;
      }
      container bgp {
        leaf as-number {
          type string;
        }
        uses ncs_template_rip-metric-route-map-grouping;
      }
      list eigrp {
        // NCS patched for predictable order
        ordered-by user;
        key "as-number";
        leaf as-number {
          type string;
        }
        uses ncs_template_rip-metric-route-map-grouping;
      }
      container isis {
        presence "true";
        list isis-list {
          // NCS patched for predictable order
          ordered-by user;
          key "name";
          leaf name {
            type string;
          }
          leaf level {
            type string;
          }
          uses ncs_template_rip-metric-route-map-grouping;
        }
        leaf level {
          type string;
        }
        uses ncs_template_rip-metric-route-map-grouping;
      }
      container iso-igrp {
        presence "true";
        list iso-igrp-list {
          // NCS patched for predictable order
          ordered-by user;
          key "name";
          leaf name {
            type string;
          }
          uses ncs_template_rip-metric-route-map-grouping;
        }
        uses ncs_template_rip-metric-route-map-grouping;
      }
      container mobile {
        presence "Mobile routes";
        uses ncs_template_rip-metric-route-map-grouping;
      }
      container odr {
        presence "On Demand stub Routes";
        uses ncs_template_rip-metric-route-map-grouping;
      }
      list ospf {
        // NCS patched for predictable order
        ordered-by user;
        key "process-id";
        leaf process-id {
          type string;
        }
        uses ncs_template_rip-metric-route-map-grouping;
        container match {
          uses ncs_template_redistribute-ospf-match-grouping;
          uses ncs_template_rip-metric-route-map-grouping;
        }
      }
      container static {
        presence "Static routes";
        uses ncs_template_rip-metric-route-map-grouping;
      }
      container rip {
        presence "true";
        uses ncs_template_rip-metric-route-map-grouping;
      }
    }
    container timers {
      container basic {
        leaf updates {
          type string;
        }
        leaf invalid {
          type string;
        }
        leaf holddown {
          type string;
        }
        leaf flush {
          type string;
        }
        leaf sleep {
          type string;
        }
      }
    }
    leaf version {
      // NCS drop tailf-common:cli-diff-dependency statement
      type string;
    }
    container traffic-share {
      container min {
        leaf across-interfaces {
          type empty;
        }
      }
    }
  }

  grouping ncs_template_router-rip-grouping {
    uses ncs_template_router-rip-af-grouping;
    uses ncs_template_passive-interface-grouping;
    leaf output-delay {
      type string;
    }
    leaf input-queue {
      type string;
    }
    leaf flash-update-threshold {
      type string;
    }
  }

  grouping ncs_template_rip-metric-route-map-grouping {
    leaf metric {
      type string;
    }
    leaf route-map {
      type string;
    }
  }

  grouping ncs_template_eigrp-metric-route-map-grouping {
    container metric {
      leaf bandwidth-metric {
        type string;
      }
      leaf delay-metric {
        type string;
      }
      leaf reliability-metric {
        type string;
      }
      leaf effective-bandwidth-metric {
        type string;
      }
      leaf mtu-bytes {
        type string;
      }
    }
    leaf route-map {
      type string;
    }
  }

  grouping ncs_template_narrow-wide-transition-grouping {
    leaf narrow-wide {
      type string;
    }
    leaf transition {
      type string;
    }
  }

  grouping ncs_template_spf-intervals-grouping {
    leaf interval {
      type string;
    }
    leaf initial-wait {
      type string;
    }
    leaf minimum-wait {
      type string;
    }
  }

  grouping ncs_template_router-isis-authenticate-snp-grouping {
    leaf authenticate {
      type empty;
    }
    leaf snp {
      type string;
    }
  }

  grouping ncs_template_lsp-gen-interval-grouping {
    leaf interval {
      type string;
    }
    leaf initial-wait {
      type string;
    }
    leaf wait {
      type string;
    }
  }

  grouping ncs_template_set-overload-bit-suppress-grouping {
    leaf external {
      type empty;
    }
    leaf interlevel {
      type empty;
    }
  }

  grouping ncs_template_summary-address-metric-tag-grouping {
    leaf metric {
      type string;
    }
    leaf tag {
      type string;
    }
  }

  grouping ncs_template_authentication-level-grouping {
    leaf level {
      type string;
    }
  }

  grouping ncs_template_redist-level-grouping {
    leaf level {
      type string;
    }
  }

  grouping ncs_template_isis-redist-container-content-grouping {
    uses ncs_template_redist-level-grouping;
    leaf metric {
      type string;
    }
    leaf metric-type {
      type string;
    }
    leaf route-map {
      type string;
    }
  }

  grouping ncs_template_router-isis-redistribute-grouping {
    uses ncs_template_isis-redist-container-content-grouping;
  }

  grouping ncs_template_isis-redist-af-grouping {
    container isis-redist-af-container {
      leaf include-connected {
        type empty;
      }
      uses ncs_template_isis-redist-container-content-grouping;
    }
  }

  grouping ncs_template_isis-redist-ospf-match-grouping {
    uses ncs_template_redist-level-grouping;
    leaf metric {
      type string;
    }
    leaf route-map {
      type string;
    }
  }

  grouping ncs_template_isis-redist-clns-ip-grouping {
    uses ncs_template_router-isis-redistribute-grouping;
    container clns {
      presence "Redistribution of BGP NSAP routes";
      leaf route-map {
        type string;
      }
    }
    leaf ip {
      type empty;
    }
  }

  grouping ncs_template_router-isis-interface-grouping {
    container authentication {
      container mode {
        container md5 {
          presence "true";
          uses ncs_template_authentication-level-grouping;
        }
        container text {
          presence "true";
          uses ncs_template_authentication-level-grouping;
        }
      }
      container key-chain {
        leaf name {
          type string;
        }
        uses ncs_template_authentication-level-grouping;
      }
      container send-only {
        presence "true";
        uses ncs_template_authentication-level-grouping;
      }
    }
  }

  grouping ncs_template_router-isis-af-grouping {
    leaf adjacency-check {
      type empty;
    }
    container default-information {
      container originate {
        presence "true";
        leaf route-map {
          type string;
        }
      }
    }
    leaf maximum-paths {
      type string;
    }
    container metric {
      leaf default {
        type string;
      }
      leaf level-1-2 {
        type string;
      }
    }
    container prc-interval {
      leaf interval {
        type string;
      }
      leaf initial-wait {
        type string;
      }
      leaf minimum-wait {
        type string;
      }
    }
    container set-overload-bit {
      choice set-overload-bit-choice {
        container on-startup {
          choice on-startup-choice {
            container time {
              leaf time {
                type string;
              }
              leaf suppress {
                type empty;
              }
              uses ncs_template_set-overload-bit-suppress-grouping;
            }
            container wait-for-bgp {
              presence "Let BGP decide when to unset the overload bitW";
              container suppress {
                uses ncs_template_set-overload-bit-suppress-grouping;
              }
            }
          }
        }
        container suppress {
          uses ncs_template_set-overload-bit-suppress-grouping;
        }
      }
    }
    container spf-interval {
      choice spf-interval-choice {
        list level-1-2 {
          // NCS patched for predictable order
          ordered-by user;
          key "level";
          leaf level {
            type string;
          }
          uses ncs_template_spf-intervals-grouping;
        }
        container intervals {
          uses ncs_template_spf-intervals-grouping;
        }
      }
    }
    container traffic-share {
      container min {
        leaf across-interface {
          type empty;
        }
      }
    }
  }

  grouping ncs_template_router-isis-grouping {
    container isis-main-container {
      uses ncs_template_router-isis-af-grouping;
      uses ncs_template_router-isis-interface-grouping;
      container address-family {
        container ipv6 {
          container unicast {
            uses ncs_template_router-isis-af-grouping;
            leaf distance {
              type string;
            }
            container multi-topology {
              presence "Enable multi-topology mode";
              leaf transition {
                type empty;
              }
            }
            container redistribute {
              container bgp {
                leaf as-number {
                  type string;
                }
                uses ncs_template_isis-redist-af-grouping;
              }
              container connected {
                presence "Connected";
                uses ncs_template_router-isis-redistribute-grouping;
              }
              list eigrp {
                // NCS patched for predictable order
                ordered-by user;
                key "as-number";
                leaf as-number {
                  type string;
                }
                uses ncs_template_isis-redist-af-grouping;
              }
              container isis {
                leaf area-tag {
                  type string;
                }
                container levels {
                  leaf isis-redist-levels1 {
                    type string;
                  }
                  leaf into {
                    type empty;
                  }
                  leaf isis-redist-levels2 {
                    type string;
                  }
                  leaf distribute-list {
                    type string;
                  }
                }
              }
              container nemo {
                uses ncs_template_isis-redist-af-grouping;
              }
              list ospf {
                // NCS patched for predictable order
                ordered-by user;
                key "process-id";
                leaf process-id {
                  type string;
                }
                uses ncs_template_isis-redist-af-grouping;
                container match {
                  uses ncs_template_redistribute-ospf-match-grouping;
                  uses ncs_template_isis-redist-ospf-match-grouping;
                }
              }
              list rip {
                // NCS patched for predictable order
                ordered-by user;
                key "process";
                leaf process {
                  type string;
                }
                uses ncs_template_isis-redist-af-grouping;
              }
              container static {
                presence "Static routes";
                uses ncs_template_router-isis-redistribute-grouping;
              }
            }
            list summary-prefix {
              // NCS patched for predictable order
              ordered-by user;
              key "prefix";
              leaf prefix {
                type string;
              }
              leaf levels {
                type string;
              }
            }
          }
        }
      }
      container advertise {
        leaf passive-only {
          type empty;
        }
      }
      container area-password {
        leaf name {
          type string;
        }
        uses ncs_template_router-isis-authenticate-snp-grouping;
      }
      container nsf {
        leaf cisco {
          type empty;
        }
      }
      container bfd {
        leaf all-interfaces {
          type empty;
        }
      }
      container distance {
        container clns-container {
          leaf distance {
            type string;
          }
          leaf clns {
            type empty;
          }
        }
        container ip-container {
          leaf distance {
            type string;
          }
          leaf ip {
            type empty;
          }
        }
        container acl-container {
          leaf distance {
            type string;
          }
          list acl {
            // NCS patched for predictable order
            ordered-by user;
            key "ip wildcard";
            leaf ip {
              type string;
            }
            leaf wildcard {
              type string;
            }
            leaf access-list {
              type string;
            }
          }
        }
      }
      container domain-password {
        leaf name {
          type string;
        }
        uses ncs_template_router-isis-authenticate-snp-grouping;
      }
      container fast-flood {
        presence "Flood LSPs (that triggered SPF) before running SPF";
        leaf number {
          type string;
        }
      }
      container hello {
        container padding {
          presence "Pad hello PDU";
          leaf pad-type {
            type string;
          }
        }
      }
      container hostname {
        leaf dynamic {
          type empty;
        }
      }
      leaf ignore-lsp-errors {
        type empty;
      }
      container ip {
        container route {
          container priority {
            container high {
              leaf tag {
                type string;
              }
            }
          }
        }
      }
      leaf is-type {
        type string;
      }
      container ispf {
        leaf level {
          type string;
        }
        leaf number {
          type string;
        }
      }
      container log-adjacency-changes {
        presence "true";
        leaf all {
          type empty;
        }
      }
      container lsp-full {
        container suppress {
          choice lsp-full-choince {
            container external-interlevel-container {
              leaf external {
                type empty;
              }
              leaf interlevel {
                type empty;
              }
            }
            leaf none {
              type empty;
            }
          }
        }
      }
      container lsp-gen-interval {
        choice lsp-gen-interval-choice {
          container intervals {
            uses ncs_template_lsp-gen-interval-grouping;
          }
          container intervals-levels {
            container intervals-level-1 {
              leaf level-1 {
                type empty;
              }
              uses ncs_template_lsp-gen-interval-grouping;
            }
            container intervals-level-2 {
              leaf level-2 {
                type empty;
              }
              uses ncs_template_lsp-gen-interval-grouping;
            }
          }
        }
      }
      leaf lsp-mtu {
        type string;
      }
      leaf lsp-refresh-interval {
        type string;
      }
      leaf max-area-addresses {
        type string;
      }
      leaf max-lsp-lifetime {
        type string;
      }
      container metric-style {
        choice metric-style-choice {
          container narrow {
            presence "true";
            uses ncs_template_narrow-wide-transition-grouping;
          }
          container transition {
            presence "true";
            leaf level {
              type string;
            }
          }
          container wide {
            presence "true";
            uses ncs_template_narrow-wide-transition-grouping;
          }
        }
      }
      container mpls {
        container ldp {
          leaf sync {
            type empty;
          }
        }
        container traffic-eng {
          leaf level-1 {
            type empty;
          }
          leaf level-2 {
            type empty;
          }
          leaf multicast-intact {
            type empty;
          }
          container router-id {
            uses ncs_template_interface-name-grouping;
          }
          container scanner {
            presence "Timer parameters for TE database";
            leaf interval {
              type string;
            }
            leaf max-flash {
              type string;
            }
          }
        }
      }
      list net {
        // NCS patched for predictable order
        ordered-by user;
        key "tag";
        leaf tag {
          type string;
        }
      }
      container partition {
        leaf avoidance {
          type empty;
        }
      }
      uses ncs_template_passive-interface-grouping;
      container protocol {
        leaf shutdown {
          type empty;
        }
      }
      container redistribute {
        container bgp {
          leaf as-number {
            type string;
          }
          uses ncs_template_isis-redist-clns-ip-grouping;
        }
        container connected {
          presence "Connected";
          uses ncs_template_router-isis-redistribute-grouping;
        }
        list eigrp {
          // NCS patched for predictable order
          ordered-by user;
          key "as-number";
          leaf as-number {
            type string;
          }
          uses ncs_template_router-isis-redistribute-grouping;
        }
        container isis {
          leaf area-tag {
            type string;
          }
          container ip {
            leaf level {
              type string;
            }
            leaf into {
              type empty;
            }
            leaf level2 {
              type string;
            }
            choice isis-redist-isis-ip-choice {
              leaf distribute-list {
                type string;
              }
              leaf route-map {
                type string;
              }
            }
          }
        }
        container iso-igrp {
          presence "IGRP for OSI networks";
          choice iso-igrp-choice {
            container area-tag-route-map-container {
              leaf area-tag {
                type string;
              }
              leaf route-map {
                type string;
              }
            }
            leaf route-map {
              type string;
            }
          }
          uses ncs_template_redist-level-grouping;
          leaf metric {
            type string;
          }
          leaf metric-type {
            type string;
          }
        }
        container maximum-prefix {
          leaf number {
            type string;
          }
          leaf threshold-value {
            type string;
          }
          leaf warning-only {
            type empty;
          }
          leaf withdraw {
            type empty;
          }
        }
        container mobile {
          presence "Mobile routes";
          uses ncs_template_router-isis-redistribute-grouping;
        }
        container odr {
          presence "On Demand stub Routes";
          uses ncs_template_router-isis-redistribute-grouping;
        }
        list ospf {
          // NCS patched for predictable order
          ordered-by user;
          key "process-id";
          leaf process-id {
            type string;
          }
          uses ncs_template_router-isis-redistribute-grouping;
          container match {
            uses ncs_template_redistribute-ospf-match-grouping;
            uses ncs_template_isis-redist-ospf-match-grouping;
          }
        }
        container rip {
          presence "Routing Information Protocol (RIP)";
          uses ncs_template_router-isis-redistribute-grouping;
        }
        container static {
          presence "Static routes";
          uses ncs_template_isis-redist-clns-ip-grouping;
        }
      }
      container set-attached-bit {
        leaf route-map {
          type string;
        }
      }
      list summary-address {
        // NCS patched for predictable order
        ordered-by user;
        key "ip mask";
        leaf ip {
          type string;
        }
        leaf mask {
          type string;
        }
        container level-1 {
          presence "Summarize into level-1 area";
          uses ncs_template_summary-address-metric-tag-grouping;
        }
        container level-1-2 {
          presence "Summarize into both area and sub-domain";
          uses ncs_template_summary-address-metric-tag-grouping;
        }
        container level-2 {
          presence "Summarize into level-2 sub-domain";
          uses ncs_template_summary-address-metric-tag-grouping;
        }
        container metric-tag-container {
          uses ncs_template_summary-address-metric-tag-grouping;
        }
      }
      leaf update-queue-depth {
        type string;
      }
      container use {
        leaf external-metrics {
          type empty;
        }
      }
    }
  }

  grouping ncs_template_interface-switch-grouping {
    container switchport {
      // NCS drop tailf-common:cli-diff-dependency statement
      presence "true";
      container access {
        leaf vlan {
          // NCS drop tailf-common:cli-diff-dependency statement
          type string;
        }
      }
      container trunk {
        leaf encapsulation {
          type string;
          // NCS drop default statement
        }
        container native {
          leaf vlan {
            type string;
          }
        }
        container allowed {
          container vlan {
            choice vlan-choice {
              leaf-list vlans {
                // NCS patched for predictable order
                ordered-by user;
                type string;
              }
              leaf all {
                type empty;
              }
              leaf-list except {
                // NCS patched for predictable order
                ordered-by user;
                type string;
              }
              leaf none {
                type empty;
              }
            }
          }
        }
        container pruning {
          container vlan {
            choice vlan-choice {
              leaf-list vlans {
                // NCS patched for predictable order
                ordered-by user;
                type string;
              }
              leaf-list except {
                // NCS patched for predictable order
                ordered-by user;
                type string;
              }
              leaf none {
                type empty;
              }
            }
          }
        }
      }
      container autostate {
        leaf exclude {
          type empty;
        }
      }
      container private-vlan {
        container trunk {
          container native {
            leaf vlan {
              type string;
            }
          }
          container allowed {
            container vlan {
              choice vlan-choice {
                leaf-list vlans {
                  // NCS patched for predictable order
                  ordered-by user;
                  type string;
                }
                leaf all {
                  type empty;
                }
                leaf-list except {
                  // NCS patched for predictable order
                  ordered-by user;
                  type string;
                }
                leaf none {
                  type empty;
                }
              }
            }
          }
        }
        container association {
          list trunk {
            // NCS patched for predictable order
            ordered-by user;
            key "primary-vlan-id";
            leaf primary-vlan-id {
              type string;
            }
            leaf secondary-vlan-id {
              type string;
            }
          }
        }
      }
      container mode {
        choice mode-choice {
          container access {
            presence "true";
          }
          container dot1q-tunnel {
            presence "true";
          }
          leaf dynamic {
            type string;
          }
          container trunk {
            // NCS drop tailf-common:cli-diff-dependency statement
            presence "true";
          }
          container private-vlan {
            choice private-vlan-choice {
              leaf host {
                type empty;
              }
              leaf promiscuous {
                type empty;
              }
              container trunk {
                presence "true";
              }
            }
          }
        }
      }
      leaf nonegotiate {
        // NCS drop tailf-common:cli-diff-dependency statement
        type empty;
      }
      container block {
        leaf multicast {
          type empty;
        }
        leaf unicast {
          type empty;
        }
      }
      container voice {
        leaf vlan {
          type string;
        }
        container detect {
          container cisco-phone {
            presence "true";
            leaf full-duplex {
              type empty;
            }
          }
        }
      }
      container port-security {
        // NCS drop tailf-common:cli-diff-dependency statement
        presence "true";
        container aging {
          leaf time {
            type string;
          }
          leaf type {
            type string;
          }
        }
        container mac-address {
          leaf sticky {
            type empty;
          }
          leaf hw-address {
            type string;
          }
          leaf vlan {
            type string;
          }
        }
        container maximum {
          leaf max-addresses {
            type string;
          }
          leaf vlan {
            type string;
          }
        }
        leaf violation {
          type string;
        }
      }
      container priority {
        container extend {
          choice trust-choice {
            leaf trust {
              type empty;
            }
            leaf cos {
              type string;
            }
          }
        }
      }
      leaf protected {
        type empty;
      }
      leaf host {
        type empty;
      }
    }
    container spanning-tree {
      leaf bpdufilter {
        type string;
      }
      container bpduguard {
        choice bpduguard-choice {
          leaf disable {
            type empty;
          }
          leaf enable {
            type empty;
          }
        }
      }
      leaf cost {
        type string;
      }
      leaf guard {
        type string;
      }
      leaf link-type {
        type string;
      }
      container mst {
        choice mst-choice {
          list instance-range {
            // NCS patched for predictable order
            ordered-by user;
            key "id";
            leaf id {
              type string;
            }
            leaf cost {
              type string;
            }
            leaf port-priority {
              type string;
            }
          }
          leaf pre-standard {
            type empty;
          }
        }
      }
      container portfast {
        presence "true";
        leaf enable {
          type string;
        }
        leaf trunk {
          type empty;
        }
      }
      container loopguard {
        leaf default {
          type empty;
        }
      }
    }
    container srr-queue {
      container bandwidth {
        container shape {
          leaf weight1 {
            type string;
          }
          leaf weight2 {
            type string;
          }
          leaf weight3 {
            type string;
          }
          leaf weight4 {
            type string;
          }
        }
        container share {
          leaf weight1 {
            type string;
          }
          leaf weight2 {
            type string;
          }
          leaf weight3 {
            type string;
          }
          leaf weight4 {
            type string;
          }
        }
      }
    }
    leaf queue-set {
      type string;
    }
  }

  grouping ncs_template_password-07-grouping {
    leaf type {
      type string;
    }
    leaf secret {
      type string;
    }
  }

  grouping ncs_template_router-lisp-af4-common-grouping {
    leaf map-request-source {
      type string;
    }
    container proxy-itr {
      leaf ipv4-local-locator {
        type string;
      }
      leaf ipv6-local-locator {
        type string;
      }
    }
  }

  grouping ncs_template_router-lisp-af6-common-grouping {
    leaf map-request-source {
      type string;
    }
    container proxy-itr {
      leaf ipv6-local-locator {
        type string;
      }
      leaf ipv4-local-locator {
        type string;
      }
    }
  }

  grouping ncs_template_router-lisp-af-common-grouping {
    leaf map-cache-limit {
      type string;
    }
    container map-cache-persistent {
      presence "true";
      leaf interval {
        type string;
      }
    }
    leaf proxy-etr {
      type empty;
    }
    list use-petr {
      // NCS patched for predictable order
      ordered-by user;
      key "address";
      leaf address {
        type string;
      }
      leaf priority {
        type string;
      }
      leaf weight {
        type string;
      }
    }
  }

  grouping ncs_template_router-lisp-af-grouping {
    leaf map-server {
      type empty;
    }
    leaf map-resolver {
      type empty;
    }
    container itr {
      presence "true";
      list map-resolver {
        // NCS patched for predictable order
        ordered-by user;
        key "address";
        leaf address {
          type string;
        }
      }
    }
    container etr {
      presence "true";
      list map-server {
        // NCS patched for predictable order
        ordered-by user;
        key "address";
        leaf address {
          type string;
        }
        container key {
          leaf encryption {
            type string;
          }
          leaf key {
            type string;
          }
        }
      }
    }
  }

  grouping ncs_template_router-lisp-eid-table-grouping {
    leaf instance-id {
      // NCS drop mandatory statement
      type string;
    }
    list map-cache {
      // NCS patched for predictable order
      ordered-by user;
      key "prefix";
      leaf prefix {
        type string;
      }
      choice map-cache-choice {
        case locator {
          leaf locator {
            type string;
          }
          leaf priority {
            type string;
          }
          leaf weight {
            type string;
          }
        }
        leaf map-request {
          type empty;
        }
        leaf native-forward {
          type empty;
        }
        leaf drop {
          type empty;
        }
      }
    }
    list database-mapping {
      // NCS patched for predictable order
      ordered-by user;
      key "prefix";
      // NCS drop max-elements statement
      leaf prefix {
        type string;
      }
      choice rloc-choice {
        leaf ipv4-address {
          type string;
        }
        container IPv4-interface {
          uses ncs_template_interface-name-grouping;
        }
        container IPv6-interface {
          uses ncs_template_interface-name-grouping;
        }
        leaf ipv6-address {
          type string;
        }
        leaf auto-discover-rlocs {
          type empty;
        }
        leaf locator-set {
          type string;
        }
      }
      leaf priority {
        type string;
      }
      leaf weight {
        type string;
      }
    }
    container loc-reach-algorithm {
      leaf lsb-reports {
        type string;
      }
      leaf rloc-probing {
        type empty;
      }
    }
    container ipv4 {
      uses ncs_template_router-lisp-af-common-grouping;
      uses ncs_template_router-lisp-af4-common-grouping;
    }
    container ipv6 {
      uses ncs_template_router-lisp-af-common-grouping;
      uses ncs_template_router-lisp-af6-common-grouping;
    }
  }

  grouping ncs_template_router-lisp-grouping {
    list locator-set {
      // NCS patched for predictable order
      ordered-by user;
      key "name";
      leaf name {
        type string;
      }
      list IPv4-address {
        // NCS patched for predictable order
        ordered-by user;
        key "name";
        leaf name {
          type string;
        }
        leaf priority {
          type string;
        }
        leaf weight {
          type string;
        }
      }
      list IPv6-address {
        // NCS patched for predictable order
        ordered-by user;
        key "name";
        leaf name {
          type string;
        }
        leaf priority {
          type string;
        }
        leaf weight {
          type string;
        }
      }
      list IPv4-interface {
        // NCS patched for predictable order
        ordered-by user;
        key "name";
        leaf name {
          type string;
        }
        leaf priority {
          type string;
        }
        leaf weight {
          type string;
        }
      }
      list IPv6-interface {
        // NCS patched for predictable order
        ordered-by user;
        key "name";
        leaf name {
          type string;
        }
        leaf priority {
          type string;
        }
        leaf weight {
          type string;
        }
      }
    }
    container map-request {
      leaf itr-rlocs {
        type string;
      }
    }
    container eid-table {
      list default-vrf {
        // NCS patched for predictable order
        ordered-by user;
        key "name";
        leaf name {
          type string;
        }
        uses ncs_template_router-lisp-eid-table-grouping;
      }
      list vrf {
        // NCS patched for predictable order
        ordered-by user;
        key "name";
        leaf name {
          type string;
        }
        uses ncs_template_router-lisp-eid-table-grouping;
      }
    }
    list site {
      // NCS patched for predictable order
      ordered-by user;
      key "name";
      leaf name {
        type string;
      }
      leaf description {
        type string;
      }
      container authentication-key {
        leaf encryption {
          type string;
        }
        leaf key {
          type string;
        }
      }
      list eid-prefix {
        // NCS patched for predictable order
        ordered-by user;
        key "prefix";
        leaf prefix {
          type string;
        }
      }
      container eid-prefix-instance {
        list eid-prefix {
          // NCS patched for predictable order
          ordered-by user;
          key "instance-id prefix";
          leaf instance-id {
            type string;
          }
          leaf prefix {
            type string;
          }
        }
      }
    }
    container ipv4 {
      uses ncs_template_router-lisp-af-grouping;
      uses ncs_template_router-lisp-af-common-grouping;
      uses ncs_template_router-lisp-af4-common-grouping;
    }
    container ipv6 {
      uses ncs_template_router-lisp-af-grouping;
      uses ncs_template_router-lisp-af-common-grouping;
      uses ncs_template_router-lisp-af6-common-grouping;
    }
  }

  grouping ncs_template_ip-nat-inside-souce-static-grouping {
    leaf extendable {
      type empty;
    }
    leaf no-alias {
      type empty;
    }
    leaf no-payload {
      type empty;
    }
    leaf route-map {
      type string;
    }
    leaf reversible {
      // NCS drop when statement
      type empty;
    }
    leaf redundancy {
      type string;
    }
    leaf mapping-id {
      // NCS drop when statement
      type string;
    }
    leaf vrf {
      // NCS drop tailf-common:cli-diff-dependency statement
      // NCS drop tailf-common:cli-diff-dependency statement
      type string;
    }
    leaf match-in-vrf {
      // NCS drop when statement
      type empty;
    }
    leaf forced {
      type empty;
    }
    leaf overload {
      type empty;
    }
  }

  grouping ncs_template_ip-nat-inside-grouping {
    choice pool-or-interface {
      case pool-choice {
        leaf pool {
          type string;
        }
        leaf redundancy {
          type string;
        }
        leaf mapping-id {
          type string;
        }
      }
      case interface-choice {
        container interface {
          uses ncs_template_interface-name-grouping;
        }
      }
    }
    leaf no-payload {
      type empty;
    }
    leaf reversible {
      type empty;
    }
    leaf vrf {
      // NCS drop tailf-common:cli-diff-dependency statement
      // NCS drop tailf-common:cli-diff-dependency statement
      type string;
    }
    leaf match-in-vrf {
      // NCS drop when statement
      type empty;
    }
    leaf overload {
      type empty;
    }
    leaf oer {
      type empty;
    }
  }

  grouping ncs_template_mobile-ip-spi-grouping {
    choice spi-type-choice {
      leaf hex {
        type string;
      }
      leaf decimal {
        type string;
      }
    }
  }

  grouping ncs_template_interface-xconnect-grouping {
    choice xconnect-choice {
      container xconnect {
        leaf address {
          type string;
        }
        leaf vcid {
          type string;
        }
        leaf encapsulation {
          type string;
        }
        leaf manual {
          type empty;
        }
        leaf pw-class {
          type string;
        }
        leaf pw-type {
          type string;
        }
        leaf sequencing {
          // NCS drop when statement
          type string;
        }
        container backup {
          container peer {
            leaf peer-router-ip-addr {
              type string;
            }
            leaf vcid {
              type string;
            }
            leaf pw-class {
              type string;
            }
            leaf priority {
              type string;
            }
          }
          container delay {
            leaf enable-delay {
              type string;
              // NCS drop default statement
            }
            leaf disable-delay {
              type string;
              // NCS drop default statement
            }
          }
        }
        leaf mtu {
          type string;
        }
        container remote {
          container link {
            container failure {
              leaf notification {
                type string;
                // NCS drop default statement
              }
            }
          }
        }
      }
      container xconnect-pw-class {
        container xconnect {
          leaf address {
            type string;
          }
          leaf vcid {
            type string;
          }
          leaf pw-class {
            type string;
          }
        }
      }
    }
  }

  grouping ncs_template_ip-pim-grouping {
    container ssm {
      choice ip-pim-ssm-choice {
        leaf default {
          type empty;
        }
        leaf range {
          type string;
        }
      }
    }
    list bsr-candidate {
      // NCS patched for predictable order
      ordered-by user;
      key "name";
      leaf name {
        type string;
      }
      leaf hash-mask-length {
        type string;
      }
      leaf priority {
        type string;
      }
    }
    container rp-address {
      leaf address {
        type string;
      }
      leaf access-list {
        type string;
      }
      leaf override {
        type empty;
      }
    }
    list rp-candidate {
      // NCS patched for predictable order
      ordered-by user;
      key "name";
      leaf name {
        type string;
      }
      leaf bidir {
        type empty;
      }
      leaf group-list {
        type string;
      }
      leaf interval {
        type string;
      }
      leaf priority {
        type string;
      }
    }
  }

  grouping ncs_template_event-manager-applet-event-grouping {
    container none {
      leaf maxrun {
        type string;
      }
    }
    container snmp-notification {
      leaf oid {
        type string;
      }
      leaf oid-val {
        type string;
      }
      leaf op {
        type string;
      }
      leaf src-ip-address {
        type string;
      }
      leaf dest-ip-address {
        type string;
      }
    }
    container syslog {
      leaf pattern {
        type string;
      }
    }
    container cli {
      container pattern {
        leaf regular-expression {
          type string;
        }
        leaf sync {
          type string;
        }
      }
    }
    container track {
      leaf object-number {
        type string;
      }
      leaf state {
        type string;
      }
      leaf maxrun {
        type string;
      }
    }
  }

  grouping ncs_template_vrf-route-target-grouping {
    list export {
      // NCS patched for predictable order
      ordered-by user;
      key "asn-ip";
      leaf asn-ip {
        type string;
      }
    }
    list import {
      // NCS patched for predictable order
      ordered-by user;
      key "asn-ip";
      leaf asn-ip {
        type string;
      }
    }
  }

  grouping ncs_template_vrf-definition-af-grouping {
    container export {
      leaf map {
        type string;
      }
    }
    container route-target {
      uses ncs_template_vrf-route-target-grouping;
    }
    container maximum {
      container routes {
        leaf limit {
          type string;
        }
        choice action {
          case a {
            leaf warning-only {
              type empty;
            }
          }
          case b {
            leaf warn-threshold {
              type string;
            }
            leaf reinstall {
              type string;
            }
          }
        }
      }
    }
  }

  grouping ncs_template_snmp-server-host-grouping {
    leaf message-type {
      type string;
      // NCS drop default statement
    }
    container version {
      leaf version {
        type string;
      }
      leaf security-level {
        // NCS drop when statement
        type string;
      }
    }
    leaf community-string {
      type string;
    }
    leaf-list allowed-traps {
      // NCS patched for predictable order
      ordered-by user;
      type string;
    }
  }

  grouping ncs_template_ip-sla-proto-grouping {
    leaf tos {
      type string;
    }
    leaf verify-data {
      type empty;
    }
    leaf data-pattern {
      type string;
    }
    leaf vrf {
      // NCS drop tailf-common:cli-diff-dependency statement
      // NCS drop tailf-common:cli-diff-dependency statement
      type string;
    }
    leaf owner {
      type string;
    }
    leaf tag {
      type string;
    }
    leaf frequency {
      type string;
      // NCS drop default statement
    }
    leaf timeout {
      type string;
    }
    leaf threshold {
      type string;
    }
    container history {
      leaf hours-of-statistics-kept {
        type string;
        // NCS drop default statement
      }
      leaf distributions-of-statistics-kept {
        type string;
        // NCS drop default statement
      }
      leaf statistics-distribution-interval {
        type string;
        // NCS drop default statement
      }
      leaf lives-kept {
        type string;
        // NCS drop default statement
      }
      leaf buckets-kept {
        type string;
        // NCS drop default statement
      }
      leaf filter {
        type string;
      }
      container enhanced {
        leaf interval {
          type string;
        }
        leaf buckets {
          type string;
        }
      }
    }
  }

  grouping ncs_template_aaa-authentication-method-grouping {
    leaf cache {
      type string;
    }
    leaf group {
      type string;
    }
    leaf krb5 {
      type empty;
    }
    leaf local {
      type empty;
    }
    leaf line {
      type empty;
    }
    leaf enable {
      type empty;
    }
    leaf none {
      type empty;
    }
  }

  grouping ncs_template_aaa-authorization-method-grouping {
    leaf cache {
      type string;
    }
    leaf group {
      type string;
    }
    leaf krb5-instance {
      type empty;
    }
    leaf if-authenticated {
      type empty;
    }
    leaf local {
      type empty;
    }
    leaf none {
      type empty;
    }
  }

  grouping ncs_template_aaa-accounting-method-grouping {
    leaf action-type {
      type string;
    }
    leaf broadcast {
      type empty;
    }
    leaf group {
      type string;
    }
  }

  grouping ncs_template_cable-modulation-profile-grouping {
    leaf fec-tbytes {
      type string;
    }
    leaf fec-len {
      type string;
    }
    leaf burst-len {
      type string;
    }
    leaf guard-t {
      type string;
    }
    leaf mod {
      type string;
    }
    leaf scrambler {
      type string;
    }
    leaf seed {
      // NCS drop when statement
      type string;
    }
    leaf diff {
      type string;
    }
    leaf pre-len {
      type string;
    }
    leaf last-cw {
      type string;
    }
    leaf preamble {
      type string;
    }
    leaf rs-interleave-depth {
      type string;
    }
    leaf rs-interleave-block {
      type string;
    }
  }

  grouping ncs_template_cable-load-balance-docsis-group-grouping {
    leaf restricted {
      type empty;
    }
    container downstream {
      leaf Modular-Cable {
        type string;
      }
      leaf rf-channel {
        type string;
      }
    }
    container upstream {
      leaf Cable {
        type string;
      }
      leaf upstream-list {
        type string;
      }
    }
    container method {
      container utilization {
        presence "true";
      }
    }
    container threshold {
      container load {
        leaf percentage {
          type string;
        }
        leaf minimum {
          type string;
        }
      }
      leaf stability {
        type string;
      }
    }
    leaf policy {
      type string;
    }
    leaf interval {
      type string;
    }
    container init-tech-list {
      leaf grouplist {
        type string;
      }
      leaf ucc {
        type empty;
      }
    }
    leaf docsis-policy {
      type string;
    }
    list tag {
      // NCS patched for predictable order
      ordered-by user;
      key "name";
      leaf name {
        type string;
      }
    }
  }

  grouping ncs_template_facility-alarm-grouping {
    container major {
      leaf temperature {
        type string;
      }
    }
    container minor {
      leaf temperature {
        type string;
      }
    }
    container critical {
      leaf exceed-action {
        type string;
      }
      leaf temperature {
        type string;
      }
    }
  }

  grouping ncs_template_process-cpu-threshold-grouping {
    leaf rising {
      type string;
    }
    leaf interval {
      type string;
    }
    leaf falling {
      type string;
    }
    container falling-interval {
      leaf interval {
        type string;
      }
    }
  }

  grouping ncs_template_cable-submgmt-default-filter-group-grouping {
    leaf upstream {
      type string;
    }
    leaf downstream {
      type string;
    }
  }

  grouping ncs_template_storm-control-level-bps-pps-grouping {
    container level-bps-pps {
      container level {
        choice level-choice {
          leaf bps {
            type string;
          }
          leaf pps {
            type string;
          }
        }
      }
    }
  }

  grouping ncs_template_service-policy-grouping {
    leaf input {
      type string;
    }
    leaf output {
      type string;
    }
  }

  grouping ncs_rpc_notif_redistribute-ospf-match-grouping {
    leaf internal {
      tailf:info
        "Redistribute OSPF internal routes";
      type empty;
    }
    container external-1 {
      tailf:cli-drop-node-name;
      tailf:cli-flatten-container;
      leaf external {
        tailf:info
          "Redistribute OSPF external routes";
        type enumeration {
          enum "1" {
            tailf:info
              "Redistribute external type 1 routes";
          }
        }
      }
    }
    container external-2 {
      tailf:cli-drop-node-name;
      tailf:cli-flatten-container;
      leaf external {
        tailf:info
          "Redistribute OSPF external routes";
        type enumeration {
          enum "2" {
            tailf:info
              "Redistribute external type 2 routes";
          }
        }
      }
    }
    container nssa-external-1 {
      tailf:cli-drop-node-name;
      tailf:cli-flatten-container;
      leaf nssa-external {
        tailf:info
          "Redistribute OSPF NSSA external routes";
        type enumeration {
          enum "1" {
            tailf:info
              "Redistribute NSSA external type 1 routes";
          }
        }
      }
    }
    container nssa-external-2 {
      tailf:cli-drop-node-name;
      tailf:cli-flatten-container;
      leaf nssa-external {
        tailf:info
          "Redistribute OSPF NSSA external routes";
        type enumeration {
          enum "2" {
            tailf:info
              "Redistribute NSSA external type 2 routes";
          }
        }
      }
    }
  }

  grouping ncs_rpc_notif_police-action-transmit-grouping {
    leaf transmit {
      tailf:info
        "transmit packet";
      type empty;
    }
  }

  grouping ncs_rpc_notif_police-action-drop-grouping {
    leaf drop {
      tailf:info
        "drop packet";
      type empty;
    }
  }

  grouping ncs_rpc_notif_police-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type cos_value-type;
        }
      }
    }
    container conform-set-cos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          type string {
            tailf:info
              "WORD;;table-map name";
          }
          // NCS drop tailf-common:non-strict-leafref statement
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type dscp-type;
        }
      }
    }
    container conform-set-dscp-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-dscp-transmit {
          tailf:info
            "set dscp and send it";
          type dscp-type;
        }
        leaf table {
          tailf:info
            "Specify table-map";
          type string {
            tailf:info
              "WORD;;table-map name";
          }
          // NCS drop tailf-common:non-strict-leafref statement
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-imposition-transmit {
          tailf:info
            "set exp at tag imposition and send it";
          type exp_value-type;
        }
        leaf table {
          tailf:info
            "Specify table-map";
          type string {
            tailf:info
              "WORD;;table-map name";
          }
          // NCS drop tailf-common:non-strict-leafref statement
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-topmost-transmit {
          tailf:info
            "set exp on topmost label and send it";
          type exp_value-type;
        }
        leaf table {
          tailf:info
            "Specify table-map";
          type string {
            tailf:info
              "WORD;;table-map name";
          }
          // NCS drop tailf-common:non-strict-leafref statement
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type prec_value-type;
        }
      }
    }
    container conform-set-prec-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-prec-transmit {
          tailf:info
            "rewrite packet precedence and send it";
          type prec_value-type;
        }
        leaf table {
          tailf:info
            "Specify table-map";
          type string {
            tailf:info
              "WORD;;table-map name";
          }
          // NCS drop tailf-common:non-strict-leafref statement
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type qos_value-type;
        }
      }
    }
    container conform-set-qos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-qos-transmit {
          tailf:info
            "set qos-group and send it";
          type qos_value-type;
        }
        leaf table {
          tailf:info
            "Specify table-map";
          type string {
            tailf:info
              "WORD;;table-map name";
          }
          // NCS drop tailf-common:non-strict-leafref statement
        }
      }
    }
    container conform-transmit {
      tailf:cli-no-keyword;
      tailf:cli-drop-node-name;
      tailf:cli-flatten-container;
      container conform-action {
        tailf:info
          "action when rate is less than conform burst";
        tailf:cli-flatten-container;
        uses ncs_rpc_notif_police-action-transmit-grouping;
      }
    }
    container conform-drop {
      tailf:cli-no-keyword;
      tailf:cli-drop-node-name;
      tailf:cli-flatten-container;
      container conform-action {
        tailf:info
          "action when rate is less than conform burst";
        tailf:cli-flatten-container;
        uses ncs_rpc_notif_police-action-drop-grouping;
      }
    }
  }

  grouping ncs_rpc_notif_police-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type cos_value-type;
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type qos_value-type;
        }
      }
    }
    container exceed-transmit {
      tailf:cli-no-keyword;
      tailf:cli-drop-node-name;
      tailf:cli-flatten-container;
      container exceed-action {
        tailf:info
          "action when rate is within conform and conform + exceed burst";
        tailf:cli-flatten-container;
        uses ncs_rpc_notif_police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses ncs_rpc_notif_police-action-drop-grouping;
      }
    }
  }

  grouping ncs_rpc_notif_police-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses ncs_rpc_notif_police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses ncs_rpc_notif_police-action-drop-grouping;
      }
    }
  }

  grouping ncs_rpc_notif_police-action-grouping {
    container actions {
      tailf:cli-break-sequence-commands;
      tailf:cli-no-keyword;
      tailf:cli-drop-node-name;
      tailf:cli-flatten-container;
      uses ncs_rpc_notif_police-conform-action-grouping;
      uses ncs_rpc_notif_police-exceed-action-grouping;
      uses ncs_rpc_notif_police-violate-action-grouping;
    }
  }

  grouping ncs_rpc_notif_password-grouping {
    container password-container {
      tailf:cli-drop-node-name;
      tailf:cli-flatten-container;
      tailf:cli-compact-syntax;
      tailf:cli-sequence-commands;
      leaf encryption {
        tailf:cli-drop-node-name;
        tailf:cli-optional-in-sequence;
        tailf:cli-incomplete-command;
        type uint8 {
          tailf:info
            "<0-7>;;Encryption type (0 to disable encryption, 7 for proprietary)";
          range "0..7";
        }
      }
      leaf password {
        tailf:cli-drop-node-name;
        type string {
          tailf:info
            "LINE;;The password";
          pattern '([1-680-9a-zA-Z].*)|(0.+)|(7.+)';
        }
      }
    }
  }

  grouping ncs_rpc_notif_crypto-key-grouping {
    leaf encryption {
      tailf:cli-drop-node-name;
      tailf:cli-incomplete-command;
      tailf:cli-optional-in-sequence;
      type enumeration {
        enum "0" {
          tailf:info
            "Specifies an UNENCRYPTED password will follow";
        }
        enum "6" {
          tailf:info
            "Specifies an ENCRYPTED password will follow";
        }
      }
    }
    leaf secret {
      tailf:cli-drop-node-name;
      tailf:cli-full-command;
      type string {
        tailf:info
          "LINE;;The UNENCRYPTED (cleartext) user password";
      }
    }
  }

  grouping ncs_rpc_notif_distribute-list-content-grouping {
    choice distribute-type {
      case access-list {
        leaf access-list-name {
          tailf:cli-drop-node-name;
          tailf:cli-prefix-key;
          type exp-ip-acl-type;
        }
      }
      case prefix-list-gateway {
        leaf prefix {
          tailf:info
            "Filter prefixes in routing updates";
          tailf:cli-prefix-key;
          tailf:cli-optional-in-sequence;
          type string {
            tailf:info
              "WORD;;Name of an IP prefix-list";
          }
        }
        leaf gateway {
          tailf:info
            "Filtering incoming updates based on gateway";
          tailf:cli-prefix-key;
          tailf:cli-optional-in-sequence;
          type string {
            tailf:info
              "WORD;;Name of an IP prefix-list";
          }
        }
      }
      case route-map {
        leaf routemap {
          tailf:info
            "Filter prefixes based on the route-map";
          tailf:cli-prefix-key;
          type string {
            tailf:info
              "WORD;;route-map name";
          }
        }
      }
    }
  }

  grouping ncs_rpc_notif_router-distribute-list-grouping {
    list distribute-list {
      tailf:info
        "Filter networks in routing updates";
      tailf:cli-suppress-mode;
      tailf:cli-delete-when-empty;
      tailf:cli-compact-syntax;
      tailf:cli-sequence-commands;
      tailf:cli-remove-before-change;
      key "direction";
      leaf direction {
        type enumeration {
          enum "in" {
            tailf:info
              "Filter incoming routing updates";
          }
          enum "out" {
            tailf:info
              "Filter outgoing routing updates";
          }
        }
      }
      uses ncs_rpc_notif_distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses ncs_rpc_notif_distribute-list-content-grouping;
      }
    }
  }

  grouping ncs_rpc_notif_passive-interface-grouping {
    container passive-interface {
      tailf:info
        "Suppress routing updates on an interface";
      choice passive-interface-choice {
        leaf default {
          tailf:info
            "Suppress routing updates on all interfaces";
          type empty;
        }
        list interface {
          tailf:cli-drop-node-name;
          tailf:cli-suppress-mode;
          tailf:cli-delete-when-empty;
          key "name";
          leaf name {
            type string {
              tailf:info
                "WORD;;Interface name";
            }
          }
        }
      }
    }
    container disable {
      tailf:info
        "Use with 'disable passive-interface' for 'no passive-interface' config";
      when '../passive-interface/default' {
        tailf:xpath-root 3;
      }
      list passive-interface {
        tailf:cli-suppress-mode;
        tailf:cli-delete-when-empty;
        tailf:cli-compact-syntax;
        key "interface";
        leaf interface {
          tailf:cli-multi-word-key;
          type string {
            tailf:info
              "WORD;;Interface name";
          }
        }
      }
    }
  }

  grouping ncs_rpc_notif_interface-name-grouping {
    choice interface-choice {
      leaf Null {
        tailf:info
          "Null interface";
        tailf:cli-allow-join-with-value {
          tailf:cli-display-joined;
        }
        type uint8 {
          tailf:info
            "<0-0>;;Null interface number";
          range "0";
        }
        // NCS drop tailf-common:non-strict-leafref statement
      }
      leaf Loopback {
        tailf:info
          "Loopback interface";
        tailf:cli-allow-join-with-value {
          tailf:cli-display-joined;
        }
        type string {
          tailf:info
            "<0-2147483647>;;Loopback interface number";
          pattern '([0-9.])+';
        }
        // NCS drop tailf-common:non-strict-leafref statement
      }
      leaf Embedded-Service-Engine {
        tailf:info
          "cisco embedded service engine module";
        tailf:cli-allow-join-with-value {
          tailf:cli-display-joined;
        }
        type string;
        // NCS drop tailf-common:non-strict-leafref statement
      }
      leaf Tunnel {
        tailf:info
          "Tunnel interface";
        tailf:cli-allow-join-with-value {
          tailf:cli-display-joined;
        }
        type uint32;
        // NCS drop tailf-common:non-strict-leafref statement
      }
      leaf Port-channel {
        tailf:info
          "Ethernet Channel of interfaces";
        tailf:cli-allow-join-with-value {
          tailf:cli-display-joined;
        }
        type uint32;
        // NCS drop tailf-common:non-strict-leafref statement
      }
      container Port-channel-subinterface {
        tailf:cli-drop-node-name;
        tailf:cli-flatten-container;
        tailf:cli-compact-syntax;
        leaf Port-channel {
          tailf:cli-allow-join-with-value {
            tailf:cli-display-joined;
          }
          type string {
            pattern '[0-9]+\.[0-9]+';
          }
          // NCS drop tailf-common:non-strict-leafref statement
        }
      }
      leaf Multilink {
        tailf:info
          "Multilink-group interface";
        tailf:cli-allow-join-with-value {
          tailf:cli-display-joined;
        }
        type uint16 {
          range "1..65535";
        }
        // NCS drop tailf-common:non-strict-leafref statement
      }
      leaf MFR {
        tailf:info
          "Multilink Frame Relay bundle interface";
        tailf:cli-allow-join-with-value {
          tailf:cli-display-joined;
        }
        type uint32;
        // NCS drop tailf-common:non-strict-leafref statement
      }
      container MFR-subinterface {
        tailf:cli-drop-node-name;
        tailf:cli-flatten-container;
        tailf:cli-compact-syntax;
        leaf MFR {
          tailf:cli-allow-join-with-value {
            tailf:cli-display-joined;
          }
          type string {
            pattern '[0-9]+\.[0-9]+';
          }
          // NCS drop tailf-common:non-strict-leafref statement
        }
      }
      leaf BRI {
        tailf:info
          "ISDN Basic Rate Interface";
        tailf:cli-allow-join-with-value {
          tailf:cli-display-joined;
        }
        type uint16;
        // NCS drop tailf-common:non-strict-leafref statement
      }
      leaf Ethernet {
        tailf:info
          "Ethernet";
        tailf:cli-allow-join-with-value {
          tailf:cli-display-joined;
        }
        type string {
          pattern '[0-9]+.*';
        }
        // NCS drop tailf-common:non-strict-leafref statement
      }
      leaf FastEthernet {
        tailf:info
          "FastEthernet IEEE 802.3";
        tailf:cli-allow-join-with-value {
          tailf:cli-display-joined;
        }
        type string;
        // NCS drop tailf-common:non-strict-leafref statement
      }
      leaf GigabitEthernet {
        tailf:info
          "GigabitEthernet IEEE 802.3z";
        tailf:cli-allow-join-with-value {
          tailf:cli-display-joined;
        }
        type string;
        // NCS drop tailf-common:non-strict-leafref statement
      }
      leaf TenGigabitEthernet {
        tailf:info
          "Ten Gigabit Ethernet";
        tailf:cli-allow-join-with-value {
          tailf:cli-display-joined;
        }
        type string;
        // NCS drop tailf-common:non-strict-leafref statement
      }
      leaf BDI {
        tailf:info
          "Bridge-Domain interface";
        tailf:cli-allow-join-with-value {
          tailf:cli-display-joined;
        }
        type uint16 {
          tailf:info
            "<1-4095>;;BDI interface number";
          range "1..4095";
        }
        // NCS drop tailf-common:non-strict-leafref statement
      }
      leaf Cable {
        tailf:info
          "CMTS interface";
        tailf:cli-allow-join-with-value {
          tailf:cli-display-joined;
        }
        type string;
        // NCS drop tailf-common:non-strict-leafref statement
      }
      leaf Modular-Cable {
        tailf:info
          "Modular Cable interface";
        tailf:cli-allow-join-with-value {
          tailf:cli-display-joined;
        }
        type string;
        // NCS drop tailf-common:non-strict-leafref statement
      }
      leaf Wideband-Cable {
        tailf:info
          "Wideband CMTS interface";
        tailf:cli-allow-join-with-value {
          tailf:cli-display-joined;
        }
        type string;
        // NCS drop tailf-common:non-strict-leafref statement
      }
      leaf Bundle {
        tailf:info
          "Virtual Bundle";
        tailf:cli-allow-join-with-value {
          tailf:cli-display-joined;
        }
        type uint8 {
          tailf:info
            "<1-255>;;Bundle interface number";
          range "1..255";
        }
        // NCS drop tailf-common:non-strict-leafref statement
      }
      leaf Cellular {
        tailf:info
          "Cellular";
        tailf:cli-allow-join-with-value {
          tailf:cli-display-joined;
        }
        type string;
        // NCS drop tailf-common:non-strict-leafref statement
      }
      leaf Vlan {
        tailf:info
          "Catalyst Vlans";
        tailf:cli-allow-join-with-value {
          tailf:cli-display-joined;
        }
        type uint16 {
          tailf:info
            "<1-4094>;;Vlan interface number";
          range "1..4094";
        }
        // NCS drop tailf-common:non-strict-leafref statement
      }
      leaf Async {
        tailf:info
          "Async interface";
        tailf:cli-allow-join-with-value {
          tailf:cli-display-joined;
        }
        type uint16;
        // NCS drop tailf-common:non-strict-leafref statement
      }
      leaf Group-Async {
        tailf:info
          "Async Group interface";
        tailf:cli-allow-join-with-value {
          tailf:cli-display-joined;
        }
        type uint16;
        // NCS drop tailf-common:non-strict-leafref statement
      }
      leaf Serial {
        tailf:info
          "Serial interface";
        tailf:cli-allow-join-with-value {
          tailf:cli-display-joined;
        }
        type string;
        // NCS drop tailf-common:non-strict-leafref statement
      }
      container Serial-subinterface {
        tailf:cli-drop-node-name;
        tailf:cli-flatten-container;
        tailf:cli-compact-syntax;
        leaf Serial {
          tailf:cli-allow-join-with-value {
            tailf:cli-display-joined;
          }
          type string {
            pattern '[0-9]+.*';
          }
          // NCS drop tailf-common:non-strict-leafref statement
        }
      }
      leaf Virtual-Template {
        tailf:info
          "Virtual Template interface";
        tailf:cli-allow-join-with-value {
          tailf:cli-display-joined;
        }
        type uint16 {
          tailf:info
            "<1-4095>;;Virtual-Template interface number";
          range "1..4095";
        }
        // NCS drop tailf-common:non-strict-leafref statement
      }
      leaf pseudowire {
        tailf:info
          "Pseudowire Interface";
        tailf:cli-allow-join-with-value {
          tailf:cli-display-joined;
        }
        type uint32 {
          tailf:info
            "<1-231072>;;pseudowire interface number";
          range "1..231072";
        }
        // NCS drop tailf-common:non-strict-leafref statement
      }
      leaf LISP {
        tailf:info
          "Locator/ID Separation Protocol Virtual Interface";
        tailf:cli-allow-join-with-value {
          tailf:cli-display-joined;
        }
        type uint16 {
          tailf:info
            "<0-1999>;;LISP interface number";
          range "0..1999";
        }
        // NCS drop tailf-common:non-strict-leafref statement
      }
      container LISP-subinterface {
        tailf:cli-drop-node-name;
        tailf:cli-flatten-container;
        tailf:cli-compact-syntax;
        leaf LISP {
          tailf:cli-allow-join-with-value {
            tailf:cli-display-joined;
          }
          type string {
            pattern '[0-9]+\.[0-9]+';
          }
          // NCS drop tailf-common:non-strict-leafref statement
        }
      }
    }
  }

  grouping ncs_rpc_notif_ip-community-list-standard-grouping {
    container deny {
      tailf:info
        "Specify community to reject";
      tailf:cli-delete-when-empty;
      presence "true";
      list deny-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local\-AS)|(no\-advertise)|(no\-export)|(\d+:\d+)|(\d+))( (internet)|(local\-AS)|(no\-advertise)|(no\-export)|(\d+:\d+)|(\d+))*';
          }
        }
      }
    }
    container permit {
      tailf:info
        "Specify community to accept";
      tailf:cli-delete-when-empty;
      presence "true";
      list permit-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local-AS)|(no-advertise)|(no-export)|(\d+:\d+)|(\d+))( (internet)|(local-AS)|(no-advertise)|(no-export)|(\d+:\d+)|(\d+))*';
          }
        }
      }
    }
  }

  grouping ncs_rpc_notif_ip-community-list-expanded-grouping {
    container deny {
      tailf:info
        "Specify community to reject";
      tailf:cli-delete-when-empty;
      presence "true";
      list deny-list {
        tailf:cli-drop-node-name;
        tailf:cli-suppress-mode;
        tailf:cli-delete-when-empty;
        key "expr";
        leaf expr {
          tailf:cli-multi-word-key {
            tailf:cli-max-words 10;
          }
          type string {
            tailf:info
              "LINE;;An ordered list as a regular-expression";
          }
        }
      }
    }
    container permit {
      tailf:info
        "Specify community to accept";
      tailf:cli-delete-when-empty;
      presence "true";
      list permit-list {
        tailf:cli-drop-node-name;
        tailf:cli-suppress-mode;
        tailf:cli-delete-when-empty;
        key "expr";
        leaf expr {
          tailf:cli-multi-word-key {
            tailf:cli-max-words 10;
          }
          type string {
            tailf:info
              "LINE;;An ordered list as a regular-expression";
          }
        }
      }
    }
  }

  grouping ncs_rpc_notif_ip-route-options-grouping {
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf dhcp {
      tailf:info
        "Default Gateway obtained from DHCP";
      tailf:cli-case-insensitive;
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-500>;;tracked object number";
        range "1..500";
      }
    }
  }

  grouping ncs_rpc_notif_ip-route-grouping {
    list ip-route-interface-forwarding-list {
      tailf:cli-drop-node-name;
      tailf:cli-suppress-mode;
      tailf:cli-delete-when-empty;
      tailf:cli-compact-syntax;
      tailf:cli-sequence-commands {
        tailf:cli-reset-all-siblings;
      }
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ncs_rpc_notif_ip-route-options-grouping;
    }
    list ip-route-forwarding-list {
      tailf:cli-drop-node-name;
      tailf:cli-suppress-mode;
      tailf:cli-delete-when-empty;
      tailf:cli-compact-syntax;
      tailf:cli-sequence-commands {
        tailf:cli-reset-all-siblings;
      }
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ncs_rpc_notif_ip-route-options-grouping;
    }
    list ip-route-interface-list {
      tailf:cli-drop-node-name;
      tailf:cli-suppress-mode;
      tailf:cli-delete-when-empty;
      tailf:cli-compact-syntax;
      tailf:cli-sequence-commands {
        tailf:cli-reset-all-siblings;
      }
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-case-insensitive;
        tailf:cli-diff-dependency "/ios:interface" {
          tailf:xpath-root 3;
        }
        type union {
          type string {
            tailf:info
              "WORD;;Interface name";
          }
          type enumeration {
            enum "dhcp" {
              tailf:info
                "Default Gateway obtained from DHCP";
            }
          }
        }
      }
      uses ncs_rpc_notif_ip-route-options-grouping;
    }
  }

  grouping ncs_rpc_notif_ipv6-route-options-grouping {
    leaf distance {
      tailf:cli-drop-node-name;
      tailf:cli-break-sequence-commands;
      type uint8 {
        tailf:info
          "<1-254>;;Administrative distance";
        range "1..254";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>;;Tag value";
      }
    }
  }

  grouping ncs_rpc_notif_ipv6-route-grouping {
    list ipv6-route-interface-destination-list {
      tailf:cli-drop-node-name;
      tailf:cli-suppress-mode;
      tailf:cli-delete-when-empty;
      tailf:cli-compact-syntax;
      tailf:cli-sequence-commands {
        tailf:cli-reset-all-siblings;
      }
      key "prefix interface destination";
      leaf prefix {
        tailf:cli-disallow-value "vrf";
        type ipv6-prefix {
          tailf:info
            "X:X:X:X::X/<0-128>;;IPv6 prefix x:x::y/<z>";
        }
      }
      leaf interface {
        tailf:cli-diff-dependency "/ios:interface" {
          tailf:xpath-root 3;
        }
        type string {
          tailf:info
            "WORD;;Interface name";
        }
      }
      leaf destination {
        type inet:ipv6-address {
          tailf:info
            "X:X:X:X::X;;IPv6 address of next-hop";
        }
      }
      uses ncs_rpc_notif_ipv6-route-options-grouping;
    }
    list ipv6-route-destination-list {
      tailf:cli-drop-node-name;
      tailf:cli-suppress-mode;
      tailf:cli-delete-when-empty;
      tailf:cli-compact-syntax;
      tailf:cli-sequence-commands {
        tailf:cli-reset-all-siblings;
      }
      key "prefix destination";
      leaf prefix {
        tailf:cli-disallow-value "vrf";
        type ipv6-prefix {
          tailf:info
            "X:X:X:X::X/<0-128>;;IPv6 prefix x:x::y/<z>";
        }
      }
      leaf destination {
        type inet:ipv6-address {
          tailf:info
            "X:X:X:X::X;;IPv6 address of next-hop";
        }
      }
      uses ncs_rpc_notif_ipv6-route-options-grouping;
    }
    list ipv6-route-interface-list {
      tailf:cli-drop-node-name;
      tailf:cli-suppress-mode;
      tailf:cli-delete-when-empty;
      tailf:cli-compact-syntax;
      tailf:cli-sequence-commands {
        tailf:cli-reset-all-siblings;
      }
      key "prefix interface";
      leaf prefix {
        tailf:cli-disallow-value "vrf";
        type ipv6-prefix {
          tailf:info
            "X:X:X:X::X/<0-128>;;IPv6 prefix x:x::y/<z>";
        }
      }
      leaf interface {
        tailf:cli-diff-dependency "/ios:interface" {
          tailf:xpath-root 3;
        }
        type string {
          tailf:info
            "WORD;;Interface name";
        }
      }
      uses ncs_rpc_notif_ipv6-route-options-grouping;
    }
  }

  grouping ncs_rpc_notif_random-detect-grouping {
    leaf min-threshold {
      tailf:cli-drop-node-name;
      tailf:cli-incomplete-command;
      type uint32 {
        tailf:info
          "<1-262143>;;minimum threshold (in packet by default)";
      }
    }
    leaf min-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf max-threshold {
      tailf:cli-drop-node-name;
      type uint32 {
        tailf:info
          "<1-262143>;;maximum threshold (number of packets)";
      }
    }
    leaf max-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf denominator {
      tailf:cli-drop-node-name;
      type uint32 {
        tailf:info
          "<1-65535>;;mark probability denominator";
      }
    }
  }

  grouping ncs_rpc_notif_class-map-match-grouping {
    container access-group {
      tailf:info
        "Access group";
      leaf index {
        tailf:cli-drop-node-name;
        type uint32 {
          tailf:info
            "<1-2799>;;Access list index";
          range "1..2699";
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      type string {
        tailf:info
          "WORD;;Match class-map name";
      }
      // NCS drop tailf-common:non-strict-leafref statement
    }
    leaf-list cos {
      tailf:info
        "IEEE 802.1Q/ISL class of service/user priority values";
      tailf:cli-flat-list-syntax;
      max-elements 4;
      type uint16 {
        range "0..7";
        tailf:info
          "<0-7>;;Enter up to 4 class-of-service values separated by white-spaces";
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint8 {
        tailf:info
          "<0-7>;;Discard Class value";
        range "0..7";
      }
    }
    leaf-list dscp {
      tailf:info
        "Match DSCP in IP(v4) and IPv6 packets";
      tailf:cli-flat-list-syntax;
      tailf:cli-full-command;
      type dscp-type;
    }
    leaf fr-de {
      tailf:info
        "Match on Frame-relay DE bit";
      type empty;
    }
    leaf-list fr-dlci {
      tailf:info
        "Match on fr-dlci";
      tailf:cli-list-syntax;
      type uint16 {
        tailf:info
          "<16-1007>;;frame-relay dlci number";
        range "16..1007";
      }
    }
    leaf-list input-interface {
      tailf:info
        "Select an input interface to match";
      tailf:cli-list-syntax;
      type string {
        tailf:info
          "WORD;;Interface name";
      }
    }
    container ip {
      tailf:info
        "IP specific values";
      leaf-list dscp {
        tailf:info
          "Match IP DSCP (DiffServ CodePoints)";
        tailf:cli-flat-list-syntax;
        type dscp-type;
      }
      leaf-list precedence {
        tailf:info
          "Match IP precedence";
        tailf:cli-flat-list-syntax;
        type precedence-type;
      }
      list rtp {
        tailf:info
          "Match RTP port nos";
        tailf:cli-suppress-mode;
        tailf:cli-delete-when-empty;
        key "port1 port2";
        leaf port1 {
          type uint16 {
            tailf:info
              "<2000-65535>;;Lower bound of UDP destination port";
            range "2000..65535";
          }
        }
        leaf port2 {
          type uint16 {
            tailf:info
              "<0-16383>;;Range of UDP ports";
            range "0..16383";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            range "0..7";
            tailf:info
              "<0-7>;;Enter up to 8 experimental values separated by white-spaces";
          }
        }
      }
    }
    container packet {
      tailf:info
        "Layer 3 Packet length";
      container length {
        tailf:info
          "Layer 3 Packet length";
        leaf max {
          tailf:info
            "Maximum length of packet";
          type uint16 {
            range "1..2000";
            tailf:info
              "<1-2000>;;Packet length in bytes";
          }
        }
        leaf min {
          tailf:info
            "Minimum length of packet";
          type uint16 {
            range "1..2000";
            tailf:info
              "<1-2000>;;Packet length in bytes";
          }
        }
      }
    }
    leaf-list precedence {
      tailf:info
        "Match Precedence in IP(v4) and IPv6 packets";
      tailf:cli-flat-list-syntax;
      type precedence-type;
    }
    container protocol {
      tailf:info
        "Protocol";
      leaf x802-11-iapp {
        tailf:info
          "IEEE 802.11 WLANs WG IAPP";
        tailf:alt-name "802-11-iapp";
        type empty;
      }
      leaf ace-svr {
        tailf:info
          "ACE Server/Propagation";
        type empty;
      }
      leaf aol {
        tailf:info
          "America-Online Instant Messenger";
        type empty;
      }
      leaf appleqtc {
        tailf:info
          "Apple QuickTime";
        type empty;
      }
      leaf biff {
        tailf:info
          "Bliff mail notification";
        type empty;
      }
      leaf bittorrent {
        tailf:info
          "bittorrent";
        type empty;
      }
      leaf bootpc {
        tailf:info
          "Bootstrap Protocol Client";
        type empty;
      }
      leaf bootps {
        tailf:info
          "Bootstrap Protocol Server";
        type empty;
      }
      leaf cddbp {
        tailf:info
          "CD Database Protocol";
        type empty;
      }
      leaf cifs {
        tailf:info
          "CIFS";
        type empty;
      }
      leaf cisco-fna {
        tailf:info
          "Cisco FNATIVE";
        type empty;
      }
      leaf cisco-net-mgmt {
        tailf:info
          "cisco-net-mgmt";
        type empty;
      }
      leaf cisco-svcs {
        tailf:info
          "cisco license/perf/GDP/X.25/ident svcs";
        type empty;
      }
      leaf cisco-sys {
        tailf:info
          "Cisco SYSMAINT";
        type empty;
      }
      leaf cisco-tdp {
        tailf:info
          "Cisco TDP";
        type empty;
      }
      leaf cisco-tna {
        tailf:info
          "Cisco TNATIVE";
        type empty;
      }
      leaf citriximaclient {
        tailf:info
          "Citrix IMA Client";
        type empty;
      }
      leaf clp {
        tailf:info
          "Cisco Line Protocol";
        type empty;
      }
      leaf creativepartnr {
        tailf:info
          "Creative Partnr";
        type empty;
      }
      leaf creativeserver {
        tailf:info
          "Creative Server";
        type empty;
      }
      leaf daytime {
        tailf:info
          "Daytime (RFC 867)";
        type empty;
      }
      leaf dbase {
        tailf:info
          "dBASE Unix";
        type empty;
      }
      leaf dbcontrol_agent {
        tailf:info
          "Oracle dbControl Agent po";
        type empty;
      }
      leaf ddns-v3 {
        tailf:info
          "Dynamic DNS Version 3";
        type empty;
      }
      leaf dhcp-failover {
        tailf:info
          "DHCP Failover";
        type empty;
      }
      leaf directconnect {
        tailf:info
          "Direct Connect Version 2.0";
        type empty;
      }
      leaf discard {
        tailf:info
          "Discard port";
        type empty;
      }
      leaf dnsix {
        tailf:info
          "DNSIX Securit Attribute Token Map";
        type empty;
      }
      leaf echo {
        tailf:info
          "Echo port";
        type empty;
      }
      leaf entrust-svc-hdlr {
        tailf:info
          "Entrust KM/Admin Service Handler";
        type empty;
      }
      leaf entrust-svcs {
        tailf:info
          "Entrust sps/aaas/aams";
        type empty;
      }
      leaf exec {
        tailf:info
          "Remote Process Execution";
        type empty;
      }
      leaf fcip-port {
        tailf:info
          "FCIP";
        type empty;
      }
      leaf ftps {
        tailf:info
          "FTP over TLS/SSL";
        type empty;
      }
      leaf gdoi {
        tailf:info
          "GDOI";
        type empty;
      }
      leaf giop {
        tailf:info
          "Oracle GIOP/SSL";
        type empty;
      }
      leaf gtpv0 {
        tailf:info
          "GPRS Tunneling Protocol Version 0";
        type empty;
      }
      leaf gtpv1 {
        tailf:info
          "GPRS Tunneling Protocol Version 1";
        type empty;
      }
      leaf h225ras {
        tailf:info
          "H225 RAS over Unicast";
        type empty;
      }
      leaf h323callsigalt {
        tailf:info
          "h323 Call Signal Alternate";
        type empty;
      }
      leaf hp-alarm-mgr {
        tailf:info
          "HP Performance data alarm manager";
        type empty;
      }
      leaf hp-collector {
        tailf:info
          "HP Performance data collector";
        type empty;
      }
      leaf hp-managed-node {
        tailf:info
          "HP Performance data managed node";
        type empty;
      }
      leaf hsrp {
        tailf:info
          "Hot Standby Router Protocol";
        type empty;
      }
      leaf https {
        tailf:info
          "Secure Hypertext Transfer Protocol";
        type empty;
      }
      leaf ica {
        tailf:info
          "ica (Citrix)";
        type empty;
      }
      leaf icabrowser {
        tailf:info
          "icabrowser (Citrix)";
        type empty;
      }
      leaf ident {
        tailf:info
          "Authentication Service";
        type empty;
      }
      leaf igmpv3lite {
        tailf:info
          "IGMP over UDP for SSM";
        type empty;
      }
      leaf imap3 {
        tailf:info
          "Interactive Mail Access Protocol 3";
        type empty;
      }
      leaf imaps {
        tailf:info
          "IMAP over TLS/SSL";
        type empty;
      }
      leaf ipass {
        tailf:info
          "IPASS";
        type empty;
      }
      leaf ipsec-msft {
        tailf:info
          "Microsoft IPsec NAT-T";
        type empty;
      }
      leaf irc-serv {
        tailf:info
          "IRC-SERV";
        type empty;
      }
      leaf ircs {
        tailf:info
          "IRC over TLS/SSL";
        type empty;
      }
      leaf ircu {
        tailf:info
          "IRCU";
        type empty;
      }
      leaf isakmp {
        tailf:info
          "ISAKMP";
        type empty;
      }
      leaf iscsi {
        tailf:info
          "iSCSI";
        type empty;
      }
      leaf iscsi-target {
        tailf:info
          "iSCSI port";
        type empty;
      }
      leaf kermit {
        tailf:info
          "kermit";
        type empty;
      }
      leaf ldap-admin {
        tailf:info
          "LDAP admin server port";
        type empty;
      }
      leaf ldaps {
        tailf:info
          "LDAP over TLS/SSL";
        type empty;
      }
      leaf login {
        tailf:info
          "Remote login";
        type empty;
      }
      leaf lotusmtap {
        tailf:info
          "Lotus Mail Tracking Agent Protocol";
        type empty;
      }
      leaf lotusnote {
        tailf:info
          "Lotus Note";
        type empty;
      }
      leaf microsoft-ds {
        tailf:info
          "Microsoft-DS";
        type empty;
      }
      leaf ms-cluster-net {
        tailf:info
          "MS Cluster Net";
        type empty;
      }
      leaf ms-dotnetster {
        tailf:info
          "Microsoft .NETster Port";
        type empty;
      }
      leaf ms-sna {
        tailf:info
          "Microsoft SNA Server/Base";
        type empty;
      }
      leaf ms-sql {
        tailf:info
          "Microsoft SQL";
        type empty;
      }
      leaf ms-sql-m {
        tailf:info
          "Microsoft SQL Monitor";
        type empty;
      }
      leaf msexch-routing {
        tailf:info
          "Microsoft Exchange Routing";
        type empty;
      }
      leaf msnmsgr {
        tailf:info
          "MSN Instant Messenger";
        type empty;
      }
      leaf msrpc {
        tailf:info
          "Microsoft Remote Procedure Call";
        type empty;
      }
      leaf mysql {
        tailf:info
          "MySQL";
        type empty;
      }
      leaf n2h2server {
        tailf:info
          "N2H2 Filter Service Port";
        type empty;
      }
      leaf ncp {
        tailf:info
          "NCP (Novell)";
        type empty;
      }
      leaf net8-cman {
        tailf:info
          "Oracle Net8 Cman/Admin";
        type empty;
      }
      leaf netbios-dgm {
        tailf:info
          "NETBIOS Datagram Service";
        type empty;
      }
      leaf netbios-ns {
        tailf:info
          "NETBIOS Name Service";
        type empty;
      }
      leaf netbios-ssn {
        tailf:info
          "NETBIOS Session Service";
        type empty;
      }
      leaf netstat {
        tailf:info
          "Variant of systat";
        type empty;
      }
      leaf oem-agent {
        tailf:info
          "OEM Agent (Oracle)";
        type empty;
      }
      leaf oracle {
        tailf:info
          "Oracle";
        type empty;
      }
      leaf oracle-em-vp {
        tailf:info
          "Oracle EM/VP";
        type empty;
      }
      leaf oraclenames {
        tailf:info
          "Oracle Names";
        type empty;
      }
      leaf orasrv {
        tailf:info
          "Oracle SQL*Net v1/v2";
        type empty;
      }
      leaf pcanywheredata {
        tailf:info
          "pcANYWHEREdata";
        type empty;
      }
      leaf pcanywherestat {
        tailf:info
          "pcANYWHEREstat";
        type empty;
      }
      leaf pop3s {
        tailf:info
          "POP3 over TLS/SSL";
        type empty;
      }
      leaf pwdgen {
        tailf:info
          "Password  Generator Protocol";
        type empty;
      }
      leaf qmtp {
        tailf:info
          "Quick Mail Transfer Protocol";
        type empty;
      }
      leaf r-winsock {
        tailf:info
          "remote-winsock";
        type empty;
      }
      leaf radius {
        tailf:info
          "RADIUS & Accounting";
        type empty;
      }
      leaf rdb-dbs-disp {
        tailf:info
          "Oracle RDB";
        type empty;
      }
      leaf realmedia {
        tailf:info
          "RealNetwork's Realmedia Protocol";
        type empty;
      }
      leaf realsecure {
        tailf:info
          "ISS Real Secure Console Service Port";
        type empty;
      }
      leaf router {
        tailf:info
          "Local Routing Process";
        type empty;
      }
      leaf rsvp-encap {
        tailf:info
          "RSVP ENCAPSULATION-1/2";
        type empty;
      }
      leaf rsvp_tunnel {
        tailf:info
          "RSVP Tunnel";
        type empty;
      }
      leaf rtc-pm-port {
        tailf:info
          "Oracle RTC-PM port";
        type empty;
      }
      leaf rtelnet {
        tailf:info
          "Remote Telnet Service";
        type empty;
      }
      leaf send {
        tailf:info
          "SEND";
        type empty;
      }
      leaf shell {
        tailf:info
          "Remote command";
        type empty;
      }
      leaf sip-tls {
        tailf:info
          "SIP-TLS";
        type empty;
      }
      leaf sms {
        tailf:info
          "SMS RCINFO/XFER/CHAT";
        type empty;
      }
      leaf snmptrap {
        tailf:info
          "SNMP Trap";
        type empty;
      }
      leaf sql-net {
        tailf:info
          "SQL-NET";
        type empty;
      }
      leaf sqlserv {
        tailf:info
          "SQL Services";
        type empty;
      }
      leaf sqlsrv {
        tailf:info
          "SQL Service";
        type empty;
      }
      leaf sshell {
        tailf:info
          "SSLshell";
        type empty;
      }
      leaf ssp {
        tailf:info
          "State Sync Protocol";
        type empty;
      }
      leaf syslog-conn {
        tailf:info
          "Reliable Syslog Service";
        type empty;
      }
      leaf tacacs {
        tailf:info
          "Login Host Protocol (TACACS)";
        type empty;
      }
      leaf tacacs-ds {
        tailf:info
          "TACACS-Database Service";
        type empty;
      }
      leaf tarantella {
        tailf:info
          "Tarantella";
        type empty;
      }
      leaf tcp {
        tailf:info
          "TCP";
        type empty;
      }
      leaf telnets {
        tailf:info
          "Telnet over TLS/SSL";
        type empty;
      }
      leaf time {
        tailf:info
          "Time";
        type empty;
      }
      leaf timed {
        tailf:info
          "Time server";
        type empty;
      }
      leaf tr-rsrb {
        tailf:info
          "cisco RSRB";
        type empty;
      }
      leaf ttc {
        tailf:info
          "Oracle TTC/SSL";
        type empty;
      }
      leaf udp {
        tailf:info
          "UDP";
        type empty;
      }
      leaf uucp {
        tailf:info
          "UUCPD/UUCP-RLOGIN";
        type empty;
      }
      leaf vqp {
        tailf:info
          "VQP";
        type empty;
      }
      leaf webster {
        tailf:info
          "Network Disctionary";
        type empty;
      }
      leaf who {
        tailf:info
          "Who's service";
        type empty;
      }
      leaf wins {
        tailf:info
          "Microsoft WINS";
        type empty;
      }
      leaf x11 {
        tailf:info
          "X Window System";
        type empty;
      }
      leaf xdmcp {
        tailf:info
          "XDM Control Protocol";
        type empty;
      }
      leaf ymsgr {
        tailf:info
          "Yahoo! Instant Messenger";
        type empty;
      }
      leaf aarp {
        tailf:info
          "AppleTalk ARP";
        type empty;
      }
      leaf appletalk {
        tailf:info
          "AppleTalk";
        type empty;
      }
      leaf arp {
        tailf:info
          "IP ARP";
        type empty;
      }
      leaf bgp {
        tailf:info
          "Border Gateway Protocol";
        type empty;
      }
      leaf bridge {
        tailf:info
          "Bridging";
        type empty;
      }
      leaf bstun {
        tailf:info
          "Block Serial Tunnel";
        type empty;
      }
      leaf cdp {
        tailf:info
          "Cisco Discovery Protocol";
        type empty;
      }
      container citrix {
        tailf:info
          "Citrix Systems ICA protocol";
        presence "enable citrix system protocol matching";
        leaf ica-tag {
          tailf:info
            "Citrix ICA tag 0-high 1-medium 2-low 3-background";
          type string {
            tailf:info
              "WORD;;Enter a string as the sub-protocol parameter";
          }
        }
      }
      leaf clns {
        tailf:info
          "ISO CLNS";
        type empty;
      }
      leaf clns_es {
        tailf:info
          "ISO CLNS End System";
        type empty;
      }
      leaf clns_is {
        tailf:info
          "ISO CLNS Intermediate System";
        type empty;
      }
      leaf cmns {
        tailf:info
          "ISO CMNS";
        type empty;
      }
      leaf compressedtcp {
        tailf:info
          "Compressed TCP (VJ";
        type empty;
      }
      leaf cuseeme {
        tailf:info
          "CU-SeeMe desktop video conference";
        type empty;
      }
      leaf decnet {
        tailf:info
          "DECnet";
        type empty;
      }
      leaf decnet_node {
        tailf:info
          "DECnet Node";
        type empty;
      }
      leaf decnet_router-l1 {
        tailf:info
          "DECnet Router L1";
        type empty;
      }
      leaf decnet_router-l2 {
        tailf:info
          "DECnet Router L2";
        type empty;
      }
      leaf dhcp {
        tailf:info
          "Dynamic Host Configuration";
        type empty;
      }
      leaf dlsw {
        type empty;
        tailf:info
          "Data Link Switching (Direct encapsulation only";
      }
      leaf dns {
        type empty;
        tailf:info
          "Domain Name Server lookup";
      }
      leaf edonkey {
        type empty;
        tailf:info
          "eDonkey";
      }
      leaf egp {
        type empty;
        tailf:info
          "Exterior Gateway Protocol";
      }
      leaf eigrp {
        type empty;
        tailf:info
          "Enhanced Interior Gateway Routing Protocol";
      }
      leaf exchange {
        type empty;
        tailf:info
          "MS-RPC for Exchange";
      }
      container fasttrack {
        tailf:info
          "FastTrack Traffic - KaZaA, Morpheus, Grokster";
        presence "enable fasttrack matching";
        leaf file-transfer {
          tailf:info
            "File transfer stream";
          type string {
            tailf:info
              "WORD;;Enter a string as the sub-protocol parameter";
          }
        }
      }
      leaf finger {
        type empty;
        tailf:info
          "Finger";
      }
      leaf ftp {
        type empty;
        tailf:info
          "File Transfer Protocol";
      }
      container gnutella {
        tailf:info
          "Gnutella Version2 Traffic - BearShare, Shareeza, Morpheus";
        presence "enable gnutella matching";
        leaf file-transfer {
          tailf:info
            "File transfer stream";
          type string {
            tailf:info
              "WORD;;Enter a string as the sub-protocol parameter";
          }
        }
      }
      leaf gopher {
        type empty;
        tailf:info
          "Gopher";
      }
      leaf gre {
        type empty;
        tailf:info
          "Generic Routing Encapsulation";
      }
      leaf h323 {
        type empty;
        tailf:info
          "H323 Protocol";
      }
      container http {
        tailf:info
          "World Wide Web traffic";
        presence "enable http traffic matching";
        leaf c-header-field {
          tailf:info
            "Client general Header Field";
          type string {
            tailf:info
              "WORD;;Enter a string as the sub-protocol parameter";
          }
        }
        leaf host {
          tailf:info
            "Server Host Name";
          type string {
            tailf:info
              "WORD;;Enter a string as the sub-protocol parameter";
          }
        }
        leaf mime {
          tailf:info
            "Match MIME Type";
          type string {
            tailf:info
              "WORD;;Enter a string as the sub-protocol parameter";
          }
        }
        leaf s-header-field {
          tailf:info
            "Server general Header Field";
          type string {
            tailf:info
              "WORD;;Enter a string as the sub-protocol parameter";
          }
        }
        leaf url {
          tailf:info
            "Match URL String";
          type string {
            tailf:info
              "WORD;;Enter a string as the sub-protocol parameter";
          }
        }
      }
      leaf icmp {
        tailf:info
          "Internet Control Message";
        type empty;
      }
      leaf imap {
        tailf:info
          "Internet Message Access Protocol";
        type empty;
      }
      leaf ip {
        tailf:info
          "IP";
        type empty;
      }
      leaf ipinip {
        tailf:info
          "IP in IP (encapsulation";
        type empty;
      }
      leaf ipsec {
        tailf:info
          "IP Security Protocol (ESP/AH";
        type empty;
      }
      leaf ipv6 {
        tailf:info
          "IPV6";
        type empty;
      }
      leaf ipx {
        tailf:info
          "Novell IPX";
        type empty;
      }
      leaf irc {
        type empty;
        tailf:info
          "Internet Relay Chat";
      }
      container kazaa2 {
        tailf:info
          "Kazaa Version 2";
        presence "enable kazaa version 2 matching";
        leaf file-transfer {
          tailf:info
            "File transfer stream";
          type string {
            tailf:info
              "WORD;;Enter a string as the sub-protocol parameter";
          }
        }
      }
      leaf kerberos {
        tailf:info
          "Kerberos";
        type empty;
      }
      leaf l2tp {
        tailf:info
          "L2F/L2TP tunnel";
        type empty;
      }
      leaf ldap {
        tailf:info
          "Lightweight Directory Access Protocol";
        type empty;
      }
      leaf llc2 {
        tailf:info
          "llc2";
        type empty;
      }
      leaf mgcp {
        tailf:info
          "Media Gateway Control Protocol";
        type empty;
      }
      container napster {
        tailf:info
          "Napster Traffic";
        presence "enable napster matching";
        leaf non-std {
          tailf:info
            "Non-standard port advertizements";
          type empty;
        }
      }
      leaf netbios {
        tailf:info
          "NetBIOS";
        type empty;
      }
      leaf netshow {
        tailf:info
          "Microsoft Netshow";
        type empty;
      }
      leaf nfs {
        tailf:info
          "Network File System";
        type empty;
      }
      leaf nntp {
        tailf:info
          "Network News Transfer Protocol";
        type empty;
      }
      leaf notes {
        tailf:info
          "Lotus Notes(R";
        type empty;
      }
      leaf novadigm {
        tailf:info
          "Novadigm EDM";
        type empty;
      }
      leaf ntp {
        tailf:info
          "Network Time Protocol";
        type empty;
      }
      leaf ospf {
        tailf:info
          "Open Shortest Path First";
        type empty;
      }
      leaf pad {
        tailf:info
          "PAD links";
        type empty;
      }
      leaf pcanywhere {
        tailf:info
          "Symantec pcANYWHERE";
        type empty;
      }
      leaf pop3 {
        tailf:info
          "Post Office Protocol";
        type empty;
      }
      leaf pppoe {
        tailf:info
          "PPP over Ethernet";
        type empty;
      }
      leaf pptp {
        tailf:info
          "Point-to-Point Tunneling Protocol";
        type empty;
      }
      leaf printer {
        tailf:info
          "print spooler/lpd";
        type empty;
      }
      leaf qllc {
        tailf:info
          "qllc protocol";
        type empty;
      }
      leaf rcmd {
        tailf:info
          "BSD r-commands (rsh, rlogin, rexec";
        type empty;
      }
      leaf rip {
        tailf:info
          "Routing Information Protocol";
        type empty;
      }
      leaf rsrb {
        tailf:info
          "Remote Source-Route Bridging";
        type empty;
      }
      leaf rsvp {
        tailf:info
          "Resource Reservation Protocol";
        type empty;
      }
      leaf rtcp {
        tailf:info
          "Real Time Control Protocol";
        type empty;
      }
      container rtp {
        tailf:info
          "Real Time Protocol";
        presence "enable rtp matching";
        leaf audio {
          tailf:info
            "Match voice packets";
          type empty;
        }
        leaf payload-type {
          tailf:info
            "Match an explicit PT";
          type string {
            tailf:info
              "WORD;;Enter a string as the sub-protocol parameter";
          }
        }
        leaf video {
          tailf:info
            "Match video packets";
          type empty;
        }
      }
      leaf rtsp {
        tailf:info
          "Real Time Streaming Protocol";
        type empty;
      }
      leaf secure-ftp {
        tailf:info
          "FTP over TLS/SSL";
        type empty;
      }
      leaf secure-http {
        tailf:info
          "Secured HTTP";
        type empty;
      }
      leaf secure-imap {
        tailf:info
          "Internet Message Access Protocol over TLS/SSL";
        type empty;
      }
      leaf secure-irc {
        tailf:info
          "Internet Relay Chat over TLS/SSL";
        type empty;
      }
      leaf secure-ldap {
        tailf:info
          "Lightweight Directory Access Protocol over TLS/SSL";
        type empty;
      }
      leaf secure-nntp {
        tailf:info
          "Network News Transfer Protocol over TLS/SSL";
        type empty;
      }
      leaf secure-pop3 {
        tailf:info
          "Post Office Protocol over TLS/SSL";
        type empty;
      }
      leaf secure-telnet {
        tailf:info
          "Telnet over TLS/SSL";
        type empty;
      }
      leaf sip {
        tailf:info
          "Session Initiation Protocol";
        type empty;
      }
      leaf skinny {
        tailf:info
          "Skinny Protocol";
        type empty;
      }
      leaf smtp {
        tailf:info
          "Simple Mail Transfer Protocol";
        type empty;
      }
      leaf snapshot {
        tailf:info
          "Snapshot routing support";
        type empty;
      }
      leaf snmp {
        tailf:info
          "Simple Network Management Protocol";
        type empty;
      }
      leaf socks {
        tailf:info
          "SOCKS";
        type empty;
      }
      leaf sqlnet {
        tailf:info
          "SQL*NET for Oracle";
        type empty;
      }
      leaf sqlserver {
        tailf:info
          "MS SQL Server";
        type empty;
      }
      leaf ssh {
        tailf:info
          "Secured Shell";
        type empty;
      }
      leaf streamwork {
        tailf:info
          "Xing Technology StreamWorks player";
        type empty;
      }
      leaf stun {
        tailf:info
          "Serial Tunnel";
        type empty;
      }
      leaf sunrpc {
        tailf:info
          "Sun RPC";
        type empty;
      }
      leaf syslog {
        tailf:info
          "System Logging Utility";
        type empty;
      }
      leaf telnet {
        tailf:info
          "Telnet";
        type empty;
      }
      leaf tftp {
        tailf:info
          "Trivial File Transfer Protocol";
        type empty;
      }
      leaf vdolive {
        tailf:info
          "VDOLive streaming video";
        type empty;
      }
      leaf vofr {
        tailf:info
          "voice over Frame Relay packets";
        type empty;
      }
      leaf winmx {
        tailf:info
          "WinMx file-sharing application";
        type empty;
      }
      leaf xwindows {
        tailf:info
          "X-Windows remote access";
        type empty;
      }
      container attribute {
        tailf:info
          "Attribute based protocol match";
        list category {
          tailf:info
            "Category attribute";
          tailf:cli-suppress-mode;
          tailf:cli-delete-when-empty;
          key "category-type";
          leaf category-type {
            type enumeration {
              enum "voice-and-video" {
                tailf:info
                  "Filter incoming connections";
              }
              enum "database" {
                tailf:info
                  "Filter outgoing connections";
              }
              enum "email" {
                tailf:info
                  "Email related applications";
              }
              enum "browsing" {
                tailf:info
                  "Browsing related applications";
              }
              enum "trojan" {
                tailf:info
                  "Trojan related applications";
              }
              enum "gaming" {
                tailf:info
                  "Gaming related applications";
              }
              enum "anonymizers" {
                tailf:info
                  "Anonymizers applications";
              }
              enum "backup-and-storage" {
                tailf:info
                  "Backup and storage related applications";
              }
              enum "business-and-productivity-tools" {
                tailf:info
                  "Business-and-productivity-tools related applications";
              }
              enum "epayement" {
                tailf:info
                  "Epayement related applications";
              }
              enum "file-sharing" {
                tailf:info
                  "File-sharing related applications";
              }
              enum "industrial-protocols" {
                tailf:info
                  "Industrial-protocols related applications";
              }
              enum "instant-messaging" {
                tailf:info
                  "Instant-messaging related applications";
              }
              enum "inter-process-rpc" {
                tailf:info
                  "Inter-process-rpc related applications";
              }
              enum "internet-security" {
                tailf:info
                  "Internet security related applications";
              }
              enum "layer3-over-ip" {
                tailf:info
                  "Layer3-over-IP related applications";
              }
              enum "location-based-services" {
                tailf:info
                  "Location-based-services related applications";
              }
              enum "net-admin" {
                tailf:info
                  "Net-admin related applications";
              }
              enum "newsgroup" {
                tailf:info
                  "Newsgroup related applications";
              }
              enum "other" {
                tailf:info
                  "Other related applications";
              }
              enum "social-networking" {
                tailf:info
                  "Social-networking related applications";
              }
              enum "software-updates" {
                tailf:info
                  "Software updates and downloads related applications";
              }
            }
          }
        }
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-range-list-syntax;
      type uint16 {
        tailf:info
          "<1-4094>;;VLAN id";
        range "1..4094";
      }
    }
  }

  grouping ncs_rpc_notif_ip-name-server-grouping {
    list name-server-list {
      tailf:cli-drop-node-name;
      tailf:cli-suppress-mode;
      tailf:cli-delete-when-empty;
      max-elements 6;
      key "address";
      leaf address {
        type union {
          type inet:ipv4-address {
            tailf:info
              "A.B.C.D;;Domain server IP address (maximum of 6)";
          }
          type inet:ipv6-address {
            tailf:info
              "X:X:X:X::X;;Domain server IPv6 address (maximum of 6)";
          }
        }
      }
    }
  }

  grouping ncs_rpc_notif_ip-host-grouping {
    list host-list {
      tailf:cli-drop-node-name;
      tailf:cli-suppress-mode;
      tailf:cli-delete-when-empty;
      tailf:cli-compact-syntax;
      tailf:cli-sequence-commands;
      tailf:cli-incomplete-command;
      key "hostname";
      leaf hostname {
        tailf:cli-disallow-value "vrf";
        type string {
          tailf:info
            "WORD;;Name of host";
        }
      }
      leaf tcp-port-number {
        tailf:cli-drop-node-name;
        tailf:cli-optional-in-sequence;
        tailf:cli-incomplete-command;
        type uint16 {
          tailf:info
            "<0-65535>;;Default telnet port number";
        }
      }
      leaf-list ip-address1 {
        tailf:cli-drop-node-name;
        tailf:cli-flat-list-syntax;
        type inet:ipv4-address {
          tailf:info
            "A.B.C.D;;Host IP address";
        }
      }
    }
  }

  grouping ncs_rpc_notif_ip-dhcp-excluded-address-grouping {
    list low-list {
      tailf:cli-drop-node-name;
      tailf:cli-suppress-mode;
      tailf:cli-delete-when-empty;
      key "low";
      leaf low {
        tailf:cli-disallow-value "vrf";
        type inet:ipv4-address {
          tailf:info
            "A.B.C.D;;Low IP address";
        }
      }
    }
    list low-high-list {
      tailf:cli-drop-node-name;
      tailf:cli-suppress-mode;
      tailf:cli-delete-when-empty;
      key "low high";
      leaf low {
        tailf:cli-disallow-value "vrf";
        type inet:ipv4-address {
          tailf:info
            "A.B.C.D;;Low IP address";
        }
      }
      leaf high {
        tailf:cli-disallow-value "vrf";
        type inet:ipv4-address {
          tailf:info
            "A.B.C.D;;High IP address";
        }
      }
    }
  }

  grouping ncs_rpc_notif_ntp-peer-grouping {
    list peer-list {
      tailf:cli-drop-node-name;
      tailf:cli-suppress-mode;
      tailf:cli-delete-when-empty;
      tailf:cli-compact-syntax;
      tailf:cli-reset-container;
      key "name";
      leaf name {
        tailf:cli-disallow-value "vrf";
        tailf:cli-case-sensitive;
        type union {
          type inet:ipv4-address {
            tailf:info
              "A.B.C.D;;IP address of peer";
          }
          type string {
            tailf:info
              "WORD;;Hostname of peer";
          }
          type inet:ipv6-address {
            tailf:info
              "X:X:X:X::X;;IPv6 address of peer";
          }
        }
      }
      leaf burst {
        tailf:info
          "Send a burst when peer is reachable (Default)";
        type empty;
      }
      leaf iburst {
        tailf:info
          "Send a burst when peer is unreachable (Default)";
        type empty;
      }
      leaf key {
        tailf:info
          "Configure peer authentication key";
        type uint32 {
          tailf:info
            "<1-4294967295>;;Peer key number";
          range "1..4294967295";
        }
      }
      leaf maxpoll {
        tailf:info
          "Maximum poll interval";
        type uint8 {
          tailf:info
            "<4-17>;;Poll value in Log2";
          range "4..17";
        }
      }
      leaf minpoll {
        tailf:info
          "Minimum poll interval";
        type uint8 {
          tailf:info
            "<4-17>;;Poll value in Log2";
          range "4..17";
        }
      }
      leaf normal-sync {
        tailf:info
          "Disable rapid sync at startup";
        type empty;
      }
      leaf prefer {
        tailf:info
          "Prefer this peer when possible";
        type empty;
      }
      container source {
        tailf:info
          "Interface for source address";
        tailf:cli-flatten-container;
        tailf:cli-compact-syntax;
        uses ncs_rpc_notif_interface-name-grouping;
      }
      leaf version {
        tailf:info
          "Configure NTP version";
        type uint8 {
          tailf:info
            "<1-4>;;NTP version number";
        }
      }
    }
  }

  grouping ncs_rpc_notif_sntp-server-grouping {
    list server-list {
      tailf:cli-drop-node-name;
      tailf:cli-suppress-mode;
      tailf:cli-delete-when-empty;
      tailf:cli-compact-syntax;
      tailf:cli-reset-container;
      key "name";
      leaf name {
        tailf:cli-disallow-value "vrf";
        type union {
          type inet:ipv4-address {
            tailf:info
              "A.B.C.D;;IP address of server";
          }
          type string {
            tailf:info
              "WORD;;Hostname of peer";
          }
          type inet:ipv6-address {
            tailf:info
              "X:X:X:X::X;;IPv6 address of server";
          }
        }
      }
      leaf key {
        tailf:info
          "Configure server authentication key";
        type uint32 {
          tailf:info
            "<1-4294967295>;;Server key number";
          range "1..4294967295";
        }
      }
      leaf version {
        tailf:info
          "Configure NTP version";
        type uint8 {
          tailf:info
            "<1-4>;;NTP version number";
        }
      }
    }
  }

  grouping ncs_rpc_notif_line-grouping {
    leaf absolute-timeout {
      tailf:info
        "Set absolute timeout for line disconnection";
      tailf:cli-full-command;
      type uint32 {
        tailf:info
          "<0-10000>;;Absolute timeout interval in minutes";
      }
    }
    container access-class {
      tailf:info
        "Filter connections based on an IP access list";
      tailf:cli-flatten-container;
      tailf:cli-compact-syntax;
      tailf:cli-sequence-commands {
        tailf:cli-reset-all-siblings;
      }
      list access-list {
        tailf:cli-drop-node-name;
        tailf:cli-suppress-mode;
        tailf:cli-delete-when-empty;
        tailf:cli-compact-syntax;
        tailf:cli-reset-container;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
          mandatory true;
        }
        leaf vrf-also {
          tailf:info
            "Same access list is applied for all VRFs";
          type empty;
        }
      }
    }
    container activation-character-choice {
      tailf:cli-drop-node-name;
      choice activation-character-choice {
        leaf activation-character {
          tailf:info
            "Define the activation character";
          tailf:cli-boolean-no;
          type boolean;
          default "true";
        }
        container activation-character-conf {
          tailf:cli-drop-node-name;
          tailf:cli-incomplete-command;
          tailf:cli-incomplete-no;
          leaf activation-character {
            type string {
              tailf:info
                "CHAR or <0-127>;;Activation character or its decimal equivalent";
            }
          }
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    container script {
      tailf:info
        "specify event related chat scripts to run on the line";
      leaf dialer {
        tailf:info
          "chat script to run whenever dialer makes an outgoing call";
        type string {
          tailf:info
            "WORD;;chat script name";
        }
        // NCS drop tailf-common:non-strict-leafref statement
      }
    }
    container modem {
      tailf:info
        "Configure the Modem Control Lines";
      leaf enable {
        tailf:info
          "Console port is used for connecting modem";
        tailf:cli-boolean-no;
        type boolean;
      }
      leaf InOut {
        tailf:info
          "Configure line for incoming AND outgoing use of modem";
        type empty;
      }
      container autoconfigure {
        tailf:info
          "Automatically configure modem on line";
        leaf discovery {
          tailf:info
            "Attempt to determine modem type automatically";
          type empty;
        }
      }
    }
    container exec-choice {
      tailf:cli-drop-node-name;
      choice exec-choice {
        leaf exec {
          tailf:info
            "Configure EXEC";
          tailf:cli-boolean-no;
          type boolean;
          default "true";
        }
        container exec-conf {
          tailf:cli-drop-node-name;
          tailf:cli-incomplete-command;
          tailf:cli-incomplete-no;
          container exec {
            tailf:cli-incomplete-command;
            tailf:cli-incomplete-no;
            container prompt {
              tailf:info
                "EXEC prompt";
              leaf timestamp {
                tailf:info
                  "Print timestamps for show commands";
                type empty;
              }
            }
          }
        }
      }
    }
    container exec-timeout {
      tailf:info
        "Set the EXEC timeout";
      tailf:cli-compact-syntax;
      tailf:cli-sequence-commands;
      leaf minutes {
        tailf:info
          "<0-35791>;;Timeout in minutes";
        tailf:cli-drop-node-name;
        type uint32;
      }
      leaf seconds {
        tailf:info
          "<0-2147483>;;Timeout in seconds";
        tailf:cli-drop-node-name;
        type uint32;
      }
    }
    container session-disconnect-warning {
      tailf:info
        "Set warning countdown for session-timeout";
      tailf:cli-compact-syntax;
      tailf:cli-sequence-commands {
        tailf:cli-reset-siblings;
      }
      leaf seconds {
        tailf:cli-drop-node-name;
        type uint32 {
          tailf:info
            "<0-4294967295>;;Session timeout warning in seconds";
        }
      }
      leaf message {
        tailf:info
          "Optional warning message";
        tailf:cli-multi-value;
        type string {
          tailf:info
            "LINE;;One text line optional warning message";
        }
      }
    }
    container logging {
      tailf:info
        "Modify message logging facilities";
      container synchronous {
        tailf:info
          "Synchronized message output";
        presence "true";
      }
    }
    container login {
      tailf:info
        "Enable password checking";
      tailf:cli-delete-when-empty;
      presence "true";
      leaf local {
        type empty;
      }
      leaf authentication {
        type string;
      }
    }
    leaf logout-warning {
      tailf:info
        "Set Warning countdown for absolute timeout of line";
      tailf:cli-full-command;
      type uint32 {
        tailf:info
          "<0-4294967295>;;Warning time in seconds";
      }
    }
    container ipv6 {
      tailf:info
        "IPv6 options";
      list access-class {
        tailf:info
          "Filter connections based on an IPv6 access list";
        tailf:cli-suppress-mode;
        tailf:cli-delete-when-empty;
        tailf:cli-compact-syntax;
        tailf:cli-sequence-commands;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
      }
    }
    container history {
      tailf:info
        "Enable and control the command history function";
      leaf size {
        tailf:info
          "Set history buffer size";
        type uint16 {
          tailf:info
            "<0-256>;;Size of history buffer";
          range "0..256";
        }
      }
    }
    container password {
      tailf:info
        "Set a password";
      tailf:cli-compact-syntax;
      tailf:cli-sequence-commands {
        tailf:cli-reset-siblings;
      }
      uses ncs_rpc_notif_password-07-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf-list output {
        tailf:info
          "Define which protocols to use for outgoing connections";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
    leaf rxspeed {
      tailf:info
        "Set the receive speed";
      type uint32 {
        tailf:info
          "<0-4294967295>;;Receive speed";
      }
    }
    leaf txspeed {
      tailf:info
        "Set the transmit speed";
      type uint32 {
        tailf:info
          "<0-4294967295>;;Transmit speed";
      }
    }
    leaf length {
      tailf:info
        "Set number of lines on a screen";
      tailf:cli-full-command;
      type uint16 {
        tailf:info
          "<0-512>;;Number of lines on screen (0 for no pausing)";
        range "0..512";
      }
    }
    leaf width {
      tailf:info
        "Set width of the display terminal";
      tailf:cli-full-command;
      type uint16 {
        tailf:info
          "Number of characters on a screen line";
        range "0..512";
      }
    }
  }

  grouping ncs_rpc_notif_queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping ncs_rpc_notif_interface-common-pre-grouping {
    leaf description {
      tailf:info
        "Interface specific description";
      tailf:cli-multi-value;
      tailf:cli-full-command;
      type string {
        length "0..240";
      }
    }
    leaf mac-address {
      tailf:info
        "Manually set interface MAC address";
      type string {
        tailf:info
          "H.H.H;;MAC address";
      }
    }
  }

  grouping ncs_rpc_notif_interface-common-grouping {
    container authentication {
      tailf:info
        "set the port-control value";
      leaf port-control {
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
    }
    container mab {
      presence "true";
      leaf eap {
        type empty;
      }
    }
    container l2protocol-tunnel {
      tailf:info
        "Tunnel Layer2 protocols";
      tailf:cli-delete-when-empty;
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
        leaf lldp {
          tailf:info
            "Link Layer Discovery Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
      leaf lldp {
        tailf:info
          "Link Layer Discovery Protocol";
        type empty;
      }
      container point-to-point {
        tailf:info
          "point-to-point L2 Protocol";
        leaf lacp {
          tailf:info
            "Link Aggregation Control Protocol";
          type empty;
        }
        leaf pagp {
          tailf:info
            "Port Aggregation Protocol";
          type empty;
        }
        leaf udld {
          tailf:info
            "Unidirectional Link Detection";
          type empty;
        }
      }
    }
    container encapsulation {
      tailf:info
        "Set encapsulation type for an interface";
      container dot1Q {
        tailf:info
          "IEEE 802.1Q Virtual LAN";
        tailf:cli-compact-syntax;
        tailf:cli-sequence-commands;
        leaf vlan-id {
          tailf:cli-drop-node-name;
          type uint16 {
            tailf:info
              "<1-4094>;;IEEE 802.1Q VLAN ID required";
            range "1..4094";
          }
        }
        leaf second-dot1q {
          tailf:info
            "Configure this subinterface as a 1Q-in-1Q subinterface";
          tailf:cli-optional-in-sequence;
          tailf:cli-full-command;
          type union {
            type enumeration {
              enum "any" {
                tailf:info
                  "All Inner VLAN IDs not configured on another subinterface";
              }
            }
            type string {
              tailf:info
                "Second (inner) VLAN IDs e.g. 100,200-300,400,500-600";
            }
          }
        }
        leaf native {
          tailf:info
            "Make this as native vlan";
          type empty;
        }
      }
      container isl {
        tailf:info
          "Inter Switch Link - Virtual LAN encapsulation";
        tailf:cli-compact-syntax;
        tailf:cli-sequence-commands;
        leaf vlan-id {
          tailf:cli-drop-node-name;
          type uint16 {
            tailf:info
              "<1-4095>;;Virtual LAN Identifier.";
            range "1..4095";
          }
        }
      }
      container ppp {
        tailf:info
          "Point-to-Point protocol";
        presence "true";
      }
      container slip {
        tailf:info
          "Serial Line IP";
        presence "true";
      }
      container frame-relay {
        tailf:info
          "Frame Relay networks";
        tailf:cli-delete-when-empty;
        presence "true";
        leaf IETF {
          tailf:info
            "Use RFC1490/RFC2427 encapsulation";
          tailf:cli-full-command;
          type empty;
        }
        leaf MFR {
          tailf:info
            "Multilink Frame Relay bundle interface";
          tailf:cli-allow-join-with-value {
            tailf:cli-display-joined;
          }
          tailf:cli-full-command;
          type uint32;
          // NCS drop tailf-common:non-strict-leafref statement
        }
      }
      container hdlc {
        tailf:cli-delete-when-empty;
        presence "true";
      }
    }
    container frame-relay {
      leaf lmi-type {
        tailf:cli-full-command;
        type enumeration {
          enum "ansi";
          enum "cisco";
          enum "q933a";
        }
      }
      leaf intf-type {
        type enumeration {
          enum "dce";
          enum "dte";
          enum "nni";
        }
      }
      container interface-dlci {
        tailf:info
          "Define a DLCI on an interface/subinterface";
        tailf:cli-add-mode;
        tailf:cli-mode-name "config-fr-dlci";
        tailf:cli-compact-syntax;
        tailf:cli-sequence-commands {
          tailf:cli-reset-siblings;
        }
        leaf dlci {
          tailf:cli-drop-node-name;
          tailf:cli-hide-in-submode;
          type uint16 {
            tailf:info
              "<16-1007>;;Define a switched or locally terminated DLCI";
          }
        }
        leaf encapsulation {
          tailf:cli-drop-node-name;
          tailf:cli-hide-in-submode;
          type enumeration {
            enum "cisco" {
              tailf:info
                "Use CISCO Encapsulation";
            }
            enum "IETF" {
              tailf:info
                "Use RFC1490/RFC2427 Encapsulation";
            }
          }
        }
      }
    }
    container fair-queue {
      tailf:info
        "Enable Fair Queuing on an Interface";
      tailf:cli-compact-syntax;
      tailf:cli-sequence-commands;
      tailf:cli-reset-container;
      tailf:cli-delete-when-empty;
      presence "true";
      leaf congestive-discard-threshold {
        tailf:cli-drop-node-name;
        type uint16 {
          tailf:info
            "<1-4096>;;Congestive Discard Threshold";
        }
      }
      leaf dynamic-queues {
        tailf:cli-drop-node-name;
        type uint16 {
          tailf:info
            "<16-4096>;;Number Dynamic Conversation Queues";
        }
      }
      leaf reservable-queues {
        tailf:cli-drop-node-name;
        type uint16 {
          tailf:info
            "<0-1000>;;Number Reservable Conversation Queues";
        }
      }
    }
    container flowcontrol {
      tailf:info
        "Configure flow operation.";
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    choice keepalive-choice {
      leaf keepalive {
        tailf:info
          "Enable keepalive";
        tailf:cli-boolean-no;
        tailf:cli-full-command;
        type boolean;
        default "true";
      }
      container keepalive-period {
        tailf:cli-drop-node-name;
        leaf keepalive {
          tailf:info
            "Enable keepalive";
          type uint16 {
            tailf:info
              "<0-32767>;;Keepalive period (default 10 seconds)";
            range "0..32767";
          }
          default "10";
        }
      }
      container keepalive-period-retries {
        tailf:cli-drop-node-name;
        container keepalive {
          tailf:cli-compact-syntax;
          tailf:cli-sequence-commands {
            tailf:cli-reset-siblings;
          }
          leaf period {
            tailf:cli-drop-node-name;
            type uint16 {
              tailf:info
                "<0-32767>;;Keepalive period (default 10 seconds)";
              range "0..32767";
            }
          }
          leaf retries {
            tailf:cli-drop-node-name;
            type uint8 {
              range "1..255";
            }
          }
        }
      }
    }
    container snmp {
      tailf:info
        "Modify SNMP interface parameters";
      container ifindex {
        tailf:info
          "Persist ifindex for the interface";
        leaf persist {
          tailf:info
            "Enable/Disable ifIndex persistence ";
          type empty;
        }
      }
      container trap {
        tailf:info
          "Allow a specific SNMP trap";
        leaf link-status {
          tailf:info
            "Allow SNMP LINKUP and LINKDOWN traps";
          tailf:cli-boolean-no;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
      }
    }
    container flow-sampler {
      tailf:info
        "Attach flow sampler to the interface";
      leaf name {
        tailf:cli-drop-node-name;
        type string {
          tailf:info
            "WORD;;Name of the flow sampler";
        }
        // NCS drop tailf-common:non-strict-leafref statement
      }
      container egress {
        tailf:cli-drop-node-name;
        tailf:cli-compact-syntax;
        tailf:cli-sequence-commands;
        leaf name {
          tailf:cli-drop-node-name;
          tailf:cli-incomplete-command;
          type string {
            tailf:info
              "WORD;;Name of the flow sampler";
          }
          // NCS drop tailf-common:non-strict-leafref statement
        }
        leaf egress {
          tailf:info
            "Egress flow sampler";
          type empty;
        }
      }
    }
    container bfd {
      tailf:info
        "BFD interface configuration commands";
      leaf echo {
        tailf:info
          "Use echo adjunct as bfd detection mechanism";
        type empty;
      }
      container interval {
        tailf:info
          "Transmit interval between BFD packets";
        tailf:cli-compact-syntax;
        tailf:cli-sequence-commands {
          tailf:cli-reset-all-siblings;
        }
        leaf msecs {
          tailf:cli-drop-node-name;
          tailf:cli-incomplete-command;
          type uint16 {
            tailf:info
              "<50-999>;;Milliseconds";
            range "50..999";
          }
        }
        leaf min_rx {
          tailf:info
            "Minimum receive interval capability";
          tailf:cli-incomplete-command;
          type uint16 {
            tailf:info
              "<50-999>;;Milliseconds";
            range "50..999";
          }
        }
        leaf multiplier {
          tailf:info
            "Multiplier value used to compute holddown";
          type uint8 {
            tailf:info
              "<3-50>;;value used to multiply the interval";
            range "3..50";
          }
        }
      }
    }
    container bandwidth {
      tailf:info
        "Set bandwidth informational parameter";
      tailf:cli-compact-syntax;
      tailf:cli-sequence-commands {
        tailf:cli-reset-siblings;
      }
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container mop {
      tailf:info
        "DEC MOP server commands";
      leaf xenabled {
        tailf:alt-name "enabled";
        tailf:info
          "Enable MOP for interface";
        tailf:cli-boolean-no;
        tailf:cli-full-command;
        type boolean;
        default "true";
      }
    }
    container dampening {
      tailf:info
        "Enable event dampening";
      presence "true";
      leaf dampening-time {
        tailf:cli-drop-node-name;
        tailf:cli-delete-container-on-delete;
        tailf:info
          "<1-30>;;Half-life time for penalty";
        type uint16 {
          range "1..30";
        }
      }
    }
    list hold-queue {
      tailf:info
        "Set hold queue depth";
      tailf:cli-suppress-mode;
      tailf:cli-delete-when-empty;
      tailf:cli-compact-syntax;
      tailf:cli-sequence-commands;
      key "direction";
      leaf direction {
        type enumeration {
          enum "in" {
            tailf:info
              "Input queue";
          }
          enum "out" {
            tailf:info
              "Output queue";
          }
        }
      }
      leaf queue-length {
        tailf:cli-drop-node-name;
        tailf:cli-prefix-key;
        type uint16 {
          tailf:info
            "<0-4096>;;Queue length";
          range "0..4096";
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:info
                "Use LDP (default)";
            }
            enum "tdp" {
              tailf:info
                "Use TDP";
            }
          }
        }
      }
      container ldp {
        tailf:info
          "Configure Label Distribution Protocol (LDP) parameters";
        container discovery {
          tailf:info
            "Configure interface LDP Discovery parameters";
          leaf transport-address {
            tailf:info
              "Specify interface LDP transport address";
            type ldp-discovery-address-type;
          }
        }
      }
      leaf mtu {
        tailf:info
          "Set MPLS Maximum Transmission Unit";
        tailf:cli-full-command;
        type union {
          type uint16 {
            tailf:info
              "<1501-1524>;;MTU (baby giants bytes)";
            range "1501..1524";
          }
          type uint16 {
            tailf:info
              "<64-1500>;;MTU (bytes)";
            range "64..1500";
          }
          type uint16 {
            tailf:info
              "<64-9216>;;MTU size in bytes";
            range "64..9216";
          }
        }
        default "1500";
      }
      container traffic-eng {
        tailf:info
          "Configure Traffic Engineering parameters";
        leaf administrative-weight {
          tailf:info
            "Set the administrative weight for the interface";
          tailf:cli-full-command;
          type uint32 {
            tailf:info
              "<0-4294967295>;;Weight";
            range "0..4294967295";
          }
        }
        leaf backup-path {
          tailf:info
            "Configure an MPLS TE backup for this interface";
          type string {
            tailf:info
              "Tunnel;;Tunnel interface";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                tailf:info
                  "<0-100>;;decreased bandwidth usage (percent)";
                range "0..100";
              }
            }
            leaf-list up {
              tailf:info
                "Set the thresholds for increased resource availability";
              tailf:cli-flat-list-syntax;
              type uint8 {
                tailf:info
                  "<0-100>;;increased bandwidth usage (percent)";
                range "0..100";
              }
            }
          }
        }
        leaf tunnels {
          tailf:info
            "enable MPLS Traffic Engineering tunnels";
          tailf:cli-full-command;
          type empty;
        }
      }
      leaf ip {
        tailf:info
          "Configure dynamic MPLS forwarding for IP";
        tailf:cli-full-command;
        type empty;
      }
    }
    container isis {
      tailf:info
        "IS-IS commands";
      container bfd {
        tailf:info
          "Bidirectional Forwarding Protocol";
        presence "true";
      }
      leaf circuit-type {
        tailf:info
          "Configure circuit type for interface";
        type enumeration {
          enum "level-1" {
            tailf:info
              "Level-1 only adjacencies are formed";
          }
          enum "level-1-2" {
            tailf:info
              "Level-1-2 adjacencies are formed";
          }
          enum "level-2-only" {
            tailf:info
              "Level-2 only adjacencies are formed";
          }
        }
        default "level-1-2";
      }
      leaf network {
        tailf:info
          "Network type";
        tailf:cli-full-command;
        type enumeration {
          enum "point-to-point" {
            tailf:info
              "Specify ISIS point-to-point network";
          }
        }
      }
      choice metric-choice {
        case default-case {
          leaf metric {
            tailf:info
              "Configure the metric for interface";
            type uint32 {
              tailf:info
                "<1-16777214>;;Default metric";
              range "1..16777214";
            }
          }
        }
        case level-case {
          container metric-level {
            tailf:cli-drop-node-name;
            list metric {
              tailf:cli-suppress-mode;
              tailf:cli-delete-when-empty;
              tailf:cli-compact-syntax;
              key "level";
              leaf level {
                type enumeration {
                  enum "level-1" {
                    tailf:info
                      "Apply metric to level-1 links";
                  }
                  enum "level-2" {
                    tailf:info
                      "Apply metric to level-2 links";
                  }
                }
              }
              leaf default {
                tailf:cli-drop-node-name;
                tailf:cli-prefix-key;
                type uint32 {
                  tailf:info
                    "<1-16777214>;;Default metric";
                  range "1..16777214";
                }
              }
            }
          }
        }
      }
      uses ncs_rpc_notif_router-isis-interface-grouping;
      container ipv6 {
        tailf:info
          "IPv6 interface configuration";
        container metric-level {
          tailf:cli-drop-node-name;
          list metric {
            tailf:info
              "Configure the metric for interface";
            tailf:cli-suppress-mode;
            tailf:cli-delete-when-empty;
            tailf:cli-compact-syntax;
            tailf:cli-sequence-commands;
            key "level";
            leaf level {
              type enumeration {
                enum "level-1" {
                  tailf:info
                    "Apply metric to level-1 links";
                }
                enum "level-2" {
                  tailf:info
                    "Apply metric to level-2 links";
                }
              }
            }
            leaf value {
              tailf:cli-drop-node-name;
              tailf:cli-prefix-key;
              type union {
                type uint32 {
                  tailf:info
                    "<1-16777214>;;Default metric";
                  range "1..16777214";
                }
                type enumeration {
                  enum "maximum" {
                    tailf:info
                      "Maximum metric. All routers will exclude this link from their SPF";
                  }
                }
              }
            }
          }
        }
      }
    }
    choice vrf-choice {
      container ip-vrf {
        tailf:cli-drop-node-name;
        container ip {
          container vrf {
            leaf forwarding {
              tailf:info
                "Configure forwarding table";
              tailf:callpoint interface-vrf-hook {
                tailf:set-hook node;
              }
              type string {
                tailf:info
                  "WORD;;VRF name";
              }
              // NCS drop tailf-common:non-strict-leafref statement
            }
          }
        }
      }
      container vrf {
        tailf:info
          "VPN Routing/Forwarding parameters on the interface";
        leaf forwarding {
          tailf:info
            "Configure forwarding table";
          tailf:callpoint interface-vrf-hook {
            tailf:set-hook node;
          }
          type string {
            tailf:info
              "WORD;;VRF name";
          }
          // NCS drop tailf-common:non-strict-leafref statement
        }
      }
    }
    container ip {
      tailf:info
        "Interface Internet Protocol config commands";
      list access-group {
        tailf:info
          "Specify access control for packets";
        tailf:cli-suppress-mode;
        tailf:cli-delete-when-empty;
        tailf:cli-compact-syntax;
        tailf:cli-sequence-commands;
        key "direction";
        leaf direction {
          type enumeration {
            enum "in" {
              tailf:code-name "access_group_direction_in";
              tailf:info
                "inbound packets";
            }
            enum "out" {
              tailf:code-name "access_group_direction_out";
              tailf:info
                "outbound packets";
            }
          }
        }
        leaf access-list {
          tailf:cli-drop-node-name;
          tailf:cli-prefix-key;
          type exp-ip-acl-type;
        }
      }
      container accounting {
        tailf:info
          "Enable IP accounting on this interface";
        tailf:cli-delete-when-empty;
        presence "true";
        leaf access-violations {
          tailf:info
            "Account for IP packets violating access lists on this interface";
          tailf:cli-full-command;
          type empty;
        }
        leaf output-packets {
          tailf:info
            "Account for IP packets output on this interface";
          tailf:cli-full-command;
          type empty;
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      choice address-choice {
        leaf unnumbered {
          tailf:info
            "Enable IP processing without an explicit address";
          type string;
        }
        container no-address {
          tailf:cli-drop-node-name;
          leaf address {
            tailf:cli-boolean-no;
            tailf:cli-full-command;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-compact-syntax;
                tailf:cli-sequence-commands;
                tailf:cli-incomplete-command;
                tailf:cli-incomplete-no;
                leaf address {
                  tailf:cli-drop-node-name;
                  tailf:cli-incomplete-command;
                  tailf:cli-incomplete-no;
                  tailf:cli-diff-dependency "/ios:vrf/definition" {
                    tailf:xpath-root 3;
                  }
                  tailf:cli-diff-dependency "../../../../vrf/forwarding" {
                    tailf:xpath-root 3;
                  }
                  mandatory true;
                  type inet:ipv4-address {
                    tailf:info
                      "A.B.C.D;;IP address";
                  }
                }
                leaf mask {
                  tailf:cli-drop-node-name;
                  mandatory true;
                  type inet:ipv4-address {
                    tailf:info
                      "A.B.C.D;;IP subnet mask";
                  }
                }
              }
              list secondary {
                tailf:cli-drop-node-name;
                tailf:cli-suppress-mode;
                tailf:cli-delete-when-empty;
                tailf:cli-compact-syntax;
                tailf:cli-incomplete-command;
                tailf:cli-incomplete-no;
                tailf:cli-diff-dependency "../primary/address" {
                  tailf:xpath-root 3;
                }
                key "address mask";
                leaf address {
                  tailf:cli-incomplete-no;
                  type inet:ipv4-address {
                    tailf:info
                      "A.B.C.D;;IP address";
                  }
                }
                leaf mask {
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                tailf:cli-sequence-commands;
                presence "true";
                container client-id {
                  tailf:info
                    "Specify client-id to use";
                  tailf:cli-optional-in-sequence;
                  tailf:cli-flatten-container;
                  tailf:cli-compact-syntax;
                  uses ncs_rpc_notif_interface-name-grouping;
                }
                leaf hostname {
                  tailf:info
                    "Specify value for hostname option";
                  type string {
                    tailf:info
                      "WORD;;hostname string";
                  }
                }
              }
            }
            case negotiated-case {
              container negotiated {
                tailf:info
                  "IP Address negotiated over PPP";
                tailf:cli-reset-container;
                tailf:cli-delete-when-empty;
                presence "true";
                leaf previous {
                  tailf:info
                    "IPCP attempts to negotiate previous address assigned";
                  type empty;
                }
              }
            }
          }
        }
      }
      container directed-broadcast {
        tailf:info
          "Enable forwarding of directed broadcasts";
        tailf:cli-delete-when-empty;
        presence "true";
        leaf access-list {
          tailf:cli-drop-node-name;
          type union {
            type uint16 {
              tailf:info
                "<1-199>;;A standard IP access list number";
              range "1..199";
            }
            type uint16 {
              tailf:info
                "<1300-2699>;;A standard IP expanded access list number";
              range "1300..2699";
            }
          }
        }
      }
      container router {
        tailf:info
          "IP router interface commands";
        container isis {
          tailf:info
            "IS-IS Routing for IP";
          tailf:cli-delete-when-empty;
          presence "true";
          leaf tag {
            tailf:cli-drop-node-name;
            type string {
              tailf:info
                "WORD;;Routing process tag";
            }
          }
        }
      }
      container flow {
        tailf:info
          "NetFlow related commands";
        leaf ingress {
          tailf:info
            "Enable inbound NetFlow";
          type empty;
        }
        leaf egress {
          tailf:info
            "Enable outbound NetFlow";
          type empty;
        }
      }
      container helper-address {
        tailf:info
          "Specify a destination address for UDP broadcasts";
        tailf:cli-compact-syntax;
        tailf:cli-sequence-commands {
          tailf:cli-reset-siblings;
        }
        choice helper-choice {
          leaf global {
            tailf:info
              "Helper-address is global";
            tailf:cli-optional-in-sequence;
            type empty;
          }
          leaf vrf {
            tailf:info
              "VRF name for helper-address (if different from interface VRF)";
            tailf:cli-optional-in-sequence;
            tailf:cli-diff-dependency "/ios:ip/vrf" {
              tailf:xpath-root 3;
            }
            tailf:cli-diff-dependency "/ios:vrf/definition" {
              tailf:xpath-root 3;
            }
            type string {
              tailf:info
                "WORD;;VPN Routing/Forwarding instance name";
            }
          }
        }
        leaf address {
          tailf:cli-drop-node-name;
          type inet:ipv4-address {
            tailf:info
              "A.B.C.D;;IP destination address";
          }
        }
      }
      container ospf {
        tailf:info
          "OSPF interface commands";
        list process-id {
          tailf:cli-drop-node-name;
          tailf:cli-suppress-mode;
          tailf:cli-delete-when-empty;
          tailf:cli-compact-syntax;
          tailf:cli-sequence-commands {
            tailf:cli-reset-all-siblings;
          }
          tailf:cli-incomplete-command;
          key "id";
          leaf id {
            type uint16 {
              tailf:info
                "<1-65535>;;Process ID";
            }
          }
          leaf area {
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        container authentication {
          tailf:info
            "Enable authentication";
          tailf:cli-delete-when-empty;
          presence "true";
          leaf option {
            tailf:cli-drop-node-name;
            type enumeration {
              enum "message-digest" {
                tailf:info
                  "Use message-digest authentication";
              }
              enum "null" {
                tailf:info
                  "Use no authentication";
              }
            }
          }
        }
        list message-digest-key {
          tailf:info
            "Message digest authentication password (key)";
          tailf:cli-suppress-mode;
          tailf:cli-delete-when-empty;
          tailf:cli-compact-syntax;
          tailf:cli-sequence-commands {
            tailf:cli-reset-siblings;
          }
          key "id";
          leaf id {
            type uint8 {
              tailf:info
                "<1-255>;;Key ID";
              range "1..255";
            }
          }
          leaf md5 {
            tailf:info
              "Use MD5 algorithm";
            type empty;
          }
          leaf enc-type {
            tailf:cli-drop-node-name;
            tailf:cli-incomplete-command;
            tailf:cli-optional-in-sequence;
            type uint8 {
              tailf:info
                "<0-7>;;Encryption type (0 for not yet encrypted, 7 for proprietary)";
              range "0..7";
            }
          }
          leaf password {
            tailf:cli-drop-node-name;
            type string {
              tailf:info
                "LINE;;The OSPF password (key) (maximum 16 characters)";
            }
          }
        }
        leaf network {
          tailf:info
            "Network type";
          tailf:cli-full-command;
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        leaf hello-interval {
          tailf:info
            "Time between HELLO packets";
          type uint16 {
            tailf:info
              "<1-65535>;;Seconds";
            range "1..65535";
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf cost {
          tailf:info
            "Interface cost";
          tailf:cli-full-command;
          type uint16 {
            tailf:info
              "<1-65535>;;Cost";
            range "1..65535";
          }
        }
        leaf priority {
          tailf:info
            "Router priority";
          tailf:cli-full-command;
          type uint8 {
            tailf:info
              "<0-255>;;Priority";
          }
        }
      }
      container pim {
        tailf:info
          "PIM interface commands";
        leaf query-interval {
          tailf:info
            "PIM router query interval";
          type uint16 {
            tailf:info
              "<1-65535>;;Query interval in seconds or milliseconds";
            range "1..65535";
          }
        }
        leaf sparse-mode {
          tailf:info
            "Enable PIM sparse-mode operation";
          tailf:cli-diff-dependency "/ios:ip/multicast-routing" {
            tailf:xpath-root 3;
          }
          type empty;
        }
        leaf dr-priority {
          tailf:info
            "PIM router DR priority";
          type uint32 {
            tailf:info
              "<0-4294967294>;;DR priority, preference given to larger value";
          }
        }
        leaf snooping {
          tailf:info
            "PIM Snooping enable for Catalyst Vlan";
          type empty;
        }
      }
      container multicast {
        tailf:info
          "IP multicast interface commands";
        list boundary {
          tailf:info
            "Boundary for administratively scoped multicast addresses";
          tailf:cli-compact-syntax;
          tailf:cli-sequence-commands {
            tailf:cli-reset-siblings;
          }
          key "access-list";
          leaf access-list {
            type exp-ip-acl-type;
          }
        }
      }
      container policy {
        tailf:info
          "Enable policy routing";
        leaf route-map {
          tailf:info
            "Policy route-map";
          type string {
            tailf:info
              "WORD;;Route map name";
          }
        }
      }
      leaf unreachables {
        tailf:info
          "Enable sending ICMP Unreachable messages";
        tailf:cli-boolean-no;
        type boolean;
        default "true";
      }
      leaf proxy-arp {
        tailf:info
          "Enable proxy ARP";
        tailf:cli-boolean-no;
        type boolean;
        default "true";
      }
      container route-cache-conf {
        tailf:cli-drop-node-name;
        leaf route-cache {
          tailf:cli-boolean-no;
          tailf:cli-full-command;
          type boolean;
          default "true";
        }
      }
      container route-cache {
        tailf:info
          "Enable fast-switching cache for outgoing packets";
        tailf:cli-incomplete-no;
        tailf:cli-incomplete-command;
        leaf cef {
          tailf:info
            "Enable Cisco Express Forwarding";
          tailf:cli-boolean-no;
          type boolean;
          default "true";
        }
        leaf flow {
          tailf:info
            "Enable Flow fast-switching cache";
          tailf:cli-boolean-no;
          type boolean;
          default "false";
        }
        leaf policy {
          tailf:info
            "Enable fast-switching policy cache for outgoing packets";
          tailf:cli-boolean-no;
          type boolean;
          default "false";
        }
        leaf same-interface {
          tailf:info
            "Enable fast-switching on the same interface";
          tailf:cli-boolean-no;
          type boolean;
          default "false";
        }
      }
      container igmp {
        tailf:info
          "IGMP interface commands";
        list join-group {
          tailf:info
            "IGMP join multicast group";
          tailf:cli-suppress-mode;
          tailf:cli-delete-when-empty;
          tailf:cli-compact-syntax;
          key "address";
          leaf address {
            type inet:ipv4-address {
              tailf:info
                "A.B.C.D;;IP group address";
            }
          }
          leaf source {
            tailf:info
              "Include SSM source";
            type inet:ipv4-address {
              tailf:info
                "A.B.C.D;;IP source address";
            }
          }
        }
        container static-group {
          tailf:info
            "IGMP static multicast group";
          list groups {
            tailf:cli-suppress-mode;
            tailf:cli-delete-when-empty;
            tailf:cli-drop-node-name;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            key "id";
            leaf id {
              type string {
                tailf:info
                  "WORD;;Name of class-map of type multicast-flows";
              }
              // NCS drop tailf-common:non-strict-leafref statement
            }
          }
        }
        leaf version {
          tailf:info
            "IGMP version";
          type uint8 {
            tailf:info
              "<1-3>;;version number";
            range "1..3";
          }
        }
        leaf access-group {
          tailf:info
            "IGMP group access group";
          type exp-ip-acl-type;
        }
      }
      leaf redirects {
        tailf:info
          "Enable sending ICMP Redirect messages";
        type empty;
      }
      container nhrp {
        tailf:info
          "NHRP interface subcommands";
        leaf network-id {
          tailf:info
            "NBMA network identifier";
          type uint32 {
            tailf:info
              "<1-4294967295>;;Network identifier";
          }
        }
        container shortcut {
          tailf:info
            "Enable shortcut switching";
          tailf:cli-delete-when-empty;
          presence "true";
          leaf virtual-template {
            type uint16;
          }
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container tcp {
        tailf:info
          "TCP header compression and other parameters";
        leaf adjust-mss {
          tailf:info
            "Adjust the mss of transit packets";
          type uint16 {
            tailf:info
              "<500-1460>;;Maximum segment size in bytes";
            range "500..1460";
          }
        }
        container header-compression {
          tailf:info
            "Enable TCP header compression";
          tailf:cli-delete-when-empty;
          presence "true";
          leaf type {
            tailf:cli-drop-node-name;
            type enumeration {
              enum "ietf-format" {
                tailf:info
                  "Compressing using IETF format";
              }
              enum "iphc-format" {
                tailf:info
                  "Using PPP  IPHC compression for TCP/UDP/RTP";
              }
              enum "passive" {
                tailf:info
                  "Compress only for destinations which send compressed headers";
              }
            }
          }
        }
      }
      container rtp {
        tailf:info
          "RTP parameters";
        container header-compression {
          tailf:info
            "Enable RTP header compression";
          tailf:cli-compact-syntax;
          tailf:cli-sequence-commands {
            tailf:cli-reset-siblings;
          }
          leaf type {
            tailf:cli-drop-node-name;
            tailf:cli-optional-in-sequence;
            type enumeration {
              enum "ietf-format" {
                tailf:info
                  "Compressing using IETF format";
              }
              enum "iphc-format" {
                tailf:info
                  "Compress using IPHC format";
              }
              enum "passive" {
                tailf:info
                  "Compress only for destinations which send compressed headers";
              }
            }
          }
          leaf periodic-refresh {
            tailf:info
              "Periodic context refresh";
            type empty;
          }
        }
        leaf compression-connections {
          tailf:info
            "Maximum number of compressed connections";
          type uint16 {
            tailf:info
              "<1-1000>;;Number of connections";
            range "1..1000";
          }
        }
      }
      container mobile {
        tailf:info
          "Mobile IP support";
        container router-service {
          tailf:info
            "Mobile router support";
          container roam {
            tailf:info
              "Roaming interface";
            tailf:cli-diff-dependency "/ios:router/mobile" {
              tailf:xpath-root 3;
            }
            presence "true";
            leaf priority {
              tailf:info
                "Priority level";
              type uint8 {
                tailf:info
                  "<0-255>;;Priority level";
              }
            }
          }
          leaf description {
            tailf:info
              "roaming interface description";
            tailf:cli-multi-value;
            tailf:cli-full-command;
            type string {
              tailf:info
                "LINE;;roaming interface description";
            }
          }
          leaf link-type {
            tailf:info
              "Link type of the roaming interface";
            type string;
          }
          container tunnel {
            tailf:info
              "Tunnel parameters";
            leaf mode {
              tailf:info
                "Tunnel encapsulation mode";
              type enumeration {
                enum "gre" {
                  tailf:info
                    "Generic Routing Encapsulation";
                }
                enum "ipip" {
                  tailf:info
                    "IP-in-IP Encapsulation";
                }
              }
            }
          }
          container collocated {
            tailf:info
              "Collocated care-of address options";
            tailf:cli-compact-syntax;
            tailf:cli-sequence-commands;
            leaf gateway {
              tailf:info
                "Default gateway for static collocated care-of address";
              tailf:cli-optional-in-sequence;
              type inet:ipv4-address {
                tailf:info
                  "A.B.C.D;;IP address to use as the default gateway";
              }
            }
            leaf ccoa-only {
              tailf:info
                "Only register a collocated CoA";
              tailf:cli-optional-in-sequence;
              type empty;
            }
            container registration {
              tailf:info
                "Registration options";
              tailf:cli-break-sequence-commands;
              leaf retry {
                tailf:info
                  "Retry interval in seconds (1-65535)";
                type uint16 {
                  tailf:info
                    "<1-65535>;;Seconds (default 60; 65535 = never)";
                  range "1..65535";
                }
                default "60";
              }
              container nat {
                tailf:info
                  "NAT traversal settings";
                container traversal {
                  tailf:info
                    "Enable NAT traversal support";
                  tailf:cli-compact-syntax;
                  presence "true";
                  leaf keepalive {
                    tailf:info
                      "Keepalive message frequency (sec)";
                    type uint16 {
                      tailf:info
                        "<0-65535>;;keepalive value";
                    }
                  }
                  leaf force {
                    tailf:info
                      "Force home agent to use UDP encapsulation for the tunnel";
                    type empty;
                  }
                }
              }
            }
            leaf encapsulation {
              type enumeration {
                enum "slip";
                enum "ppp";
              }
            }
          }
        }
      }
      container virtual-reassembly {
        tailf:info
          "Enable Virtual Fragment Reassembly";
        tailf:cli-compact-syntax;
        leaf max-reassemblies {
          type uint32;
        }
        leaf max-fragments {
          tailf:info
            "<1-64>;;Number of fragments per datagram";
          type uint8 {
            tailf:info
              "<1-64>;;Number of fragments per datagram";
            range "1..64";
          }
        }
        leaf timeout {
          type uint32;
        }
        leaf drop-fragments {
          tailf:info
            "Drop all the incoming fragments";
          type empty;
        }
        leaf in {
          type empty;
        }
        leaf out {
          type empty;
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            tailf:cli-suppress-mode;
            tailf:cli-delete-when-empty;
            tailf:cli-compact-syntax;
            key "id";
            leaf id {
              type uint16 {
                tailf:info
                  "<1-4094>;;DHCP Snooping vlan";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
          list bridge-domain {
            tailf:info
              "DHCP Snooping bridge-domain";
            tailf:cli-suppress-mode;
            tailf:cli-delete-when-empty;
            tailf:cli-compact-syntax;
            key "id";
            leaf id {
              type uint16 {
                tailf:info
                  "<1-4094>;;DHCP Snooping bridge-domain number";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id";
                      }
                    }
                  }
                }
              }
            }
          }
        }
      }
      leaf mtu {
        tailf:info
          "Set IP Maximum Transmission Unit";
        type uint16 {
          tailf:info
            "<68-9198>;;MTU (bytes)";
          range "68..9198";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
      container rsvp {
        tailf:info
          "RSVP Interface Commands";
        container bandwidth {
          tailf:info
            "RSVP Reservable Bandwidth (kbps)";
          tailf:cli-reset-container;
          presence "true";
        }
        container signalling {
          tailf:info
            "RSVP signalling";
          container hello {
            tailf:info
              "Enable neighbor-down detection";
            presence "true";
            container graceful-restart {
              tailf:info
                "Configure RSVP Graceful Restart";
              presence "true";
            }
          }
        }
        container resource-provider {
          tailf:info
            "RSVP resource provider";
          choice resource-provider-choice {
            leaf none {
              tailf:info
                "Associates NO resources with reservations";
              type empty;
            }
            leaf wfq {
              tailf:info
                "Associates WFQ resources with reservations";
              type enumeration {
                enum "interface" {
                  tailf:info
                    "Associates WFQ queues and bandwidth at the interface level with reservations";
                }
                enum "pvc" {
                  tailf:info
                    "Associates WFQ queues and bandwidth at the PVC level with reservations";
                }
              }
            }
          }
        }
      }
      container verify {
        tailf:info
          "Enable per packet validation";
        container unicast {
          tailf:info
            "Enable per packet validation for unicast";
          container reverse-path {
            tailf:info
              "Reverse path validation of source address (old command format)";
            presence "true";
          }
          container source {
            tailf:info
              "Validation of source address";
            tailf:cli-compact-syntax;
            tailf:cli-sequence-commands {
              tailf:cli-reset-all-siblings;
            }
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
            leaf allow-self-ping {
              tailf:cli-break-sequence-commands;
              tailf:info
                "Allow router to ping itself (opens vulnerability in verification)";
              type empty;
            }
            leaf allow-default {
              tailf:info
                "Allow default route to match when checking source address";
              type empty;
            }
          }
        }
      }
      container rip {
        tailf:info
          "Router Information Protocol";
        container receive {
          tailf:info
            "advertisement reception";
          leaf version {
            tailf:info
              "version control";
            type enumeration {
              enum "1" {
                tailf:info
                  "RIP version 1";
              }
              enum "2" {
                tailf:info
                  "RIP version 2";
              }
            }
          }
        }
        container authentication {
          tailf:info
            "Authentication control";
          leaf mode {
            tailf:info
              "Authentication mode";
            type enumeration {
              enum "md5" {
                tailf:info
                  "Keyed message digest";
              }
              enum "text" {
                tailf:info
                  "Clear text authentication";
              }
            }
          }
          leaf key-chain {
            tailf:info
              "Authentication key-chain";
            type string {
              tailf:info
                "LINE;;name of key-chain";
            }
            // NCS drop tailf-common:non-strict-leafref statement
          }
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case manual-case {
            list prefix-list {
              tailf:cli-drop-node-name;
              tailf:cli-suppress-mode;
              tailf:cli-delete-when-empty;
              key "prefix";
              leaf prefix {
                type ios:ipv6-prefix {
                  tailf:info
                    "X:X:X:X::X/<0-128>;;IPv6 prefix";
                }
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      list traffic-filter {
        tailf:info
          "Access control list for packets";
        tailf:cli-suppress-mode;
        tailf:cli-delete-when-empty;
        tailf:cli-compact-syntax;
        tailf:cli-sequence-commands;
        key "direction";
        leaf direction {
          type enumeration {
            enum "in" {
              tailf:info
                "inbound packets";
            }
            enum "out" {
              tailf:info
                "outbound packets";
            }
          }
        }
        leaf access-list {
          tailf:cli-drop-node-name;
          tailf:cli-prefix-key;
          type string {
            tailf:info
              "WORD;;Access-list name";
          }
        }
      }
      container nd {
        tailf:info
          "IPv6 interface Neighbor Discovery subcommands";
        container dad {
          tailf:info
            "Duplicate Address Detection";
          leaf attempts {
            tailf:info
              "Set IPv6 Duplicate Address Detection Transmits";
            type uint16 {
              tailf:info
                "<0-600>;;Number of attempts";
              range "0..600";
            }
          }
        }
        container prefix {
          tailf:info
            "Configure IPv6 Routing Prefix Advertisement";
          list prefix-list {
            tailf:cli-drop-node-name;
            tailf:cli-suppress-mode;
            tailf:cli-delete-when-empty;
            tailf:cli-compact-syntax;
            tailf:cli-sequence-commands {
              tailf:cli-reset-all-siblings;
            }
            tailf:cli-incomplete-command;
            key "ipv6-prefix";
            leaf ipv6-prefix {
              type union {
                type inet:ipv6-prefix {
                  tailf:info
                    "X:X:X:X::X/<0-128>;;IPv6 prefix x:x::y/<z>";
                }
                type enumeration {
                  enum "default" {
                    tailf:info
                      "Specify prefix default parameters";
                  }
                }
              }
            }
            choice advertise-choice {
              case no-advertise {
                leaf no-advertise {
                  tailf:info
                    "Do not advertise prefix";
                  tailf:cli-full-command;
                  type empty;
                }
              }
              case advertise {
                leaf valid-lifetime {
                  tailf:cli-drop-node-name;
                  tailf:cli-incomplete-command;
                  type union {
                    type enumeration {
                      enum "infinite" {
                        tailf:info
                          "Infinite Valid Lifetime";
                      }
                    }
                    type uint32 {
                      tailf:info
                        "<0-4294967295>;;Valid Lifetime (secs)";
                    }
                  }
                }
                leaf preferred-lifetime {
                  tailf:cli-drop-node-name;
                  type union {
                    type enumeration {
                      enum "infinite" {
                        tailf:info
                          "Infinite Preferred Lifetime";
                      }
                    }
                    type uint32 {
                      tailf:info
                        "<0-4294967295>;;Preferred Lifetime (secs)";
                    }
                  }
                }
                leaf off-link {
                  tailf:cli-break-sequence-commands;
                  tailf:info
                    "Prefix is offlink";
                  type empty;
                }
                leaf no-autoconfig {
                  tailf:info
                    "Do not use prefix for autoconfiguration";
                  type empty;
                }
                leaf no-rtr-address {
                  tailf:info
                    "Do not send full router address in prefix advert";
                  type empty;
                }
                leaf no-onlink {
                  tailf:info
                    "Do not use prefix for onlink determination";
                  type empty;
                }
              }
            }
          }
        }
        leaf managed-config-flag {
          tailf:info
            "Hosts should use DHCP for address config";
          type empty;
        }
        leaf other-config-flag {
          tailf:info
            "Hosts should use DHCP for non-address config";
          type empty;
        }
        container ra {
          tailf:info
            "Router Advertisement control";
          container suppress {
            tailf:info
              "Suppress IPv6 Router Advertisements";
            tailf:cli-delete-when-empty;
            presence "true";
            leaf all {
              tailf:info
                "Suppress all ipv6 Router advertisements";
              type empty;
            }
          }
          container interval {
            choice interval-choice {
              leaf seconds {
                tailf:cli-drop-node-name;
                type uint16 {
                  tailf:info
                    "<4-1800>;;RA Interval (sec)";
                  range "4..1800";
                }
              }
              leaf msec {
                tailf:info
                  "Interval in milliseconds";
                type uint32 {
                  tailf:info
                    "<70-1800000>;;RA Interval (msec)";
                  range "70..1800000";
                }
              }
            }
          }
        }
      }
      container mld {
        tailf:info
          "interface commands";
        leaf access-group {
          tailf:info
            "source, group membership access";
          type string {
            tailf:info
              "WORD;;Named access list specifying access group range";
          }
        }
      }
      leaf redirects {
        tailf:info
          "Enable sending of ICMP Redirect messages";
        tailf:cli-boolean-no;
        tailf:cli-full-command;
        type boolean;
        default "true";
      }
      leaf unreachables {
        tailf:info
          "Enable sending of ICMP Unreachable messages";
        tailf:cli-boolean-no;
        tailf:cli-full-command;
        type boolean;
        default "true";
      }
      container router {
        tailf:info
          "IPv6 Router interface commands";
        container isis {
          tailf:info
            "isis  IS-IS Routing for IPv6";
          tailf:cli-delete-when-empty;
          presence "true";
          leaf tag {
            tailf:cli-drop-node-name;
            type string {
              tailf:info
                "WORD;;Routing process tag";
            }
          }
        }
      }
      container ospf {
        tailf:info
          "OSPF interface commands";
        list process {
          tailf:cli-drop-node-name;
          tailf:cli-suppress-mode;
          tailf:cli-delete-when-empty;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf mtu {
        tailf:info
          "Set IPv6 Maximum Transmission Unit";
        type uint16 {
          tailf:info
            "<1280-9198>;;MTU (bytes)";
          range "1280..9198";
        }
      }
      container crypto {
        tailf:info
          "Encryption/Decryption commands";
        container map {
          tailf:info
            "Assign a Crypto Map";
          tailf:cli-compact-syntax;
          tailf:cli-sequence-commands {
            tailf:cli-reset-siblings;
          }
          leaf map-name {
            tailf:cli-drop-node-name;
            type string {
              tailf:info
                "WORD;;Crypto Map tag";
            }
            // NCS drop tailf-common:non-strict-leafref statement
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
      }
      container verify {
        tailf:info
          "Enable per packet validation";
        container unicast {
          tailf:info
            "Enable per packet validation for unicast";
          container reverse-path {
            tailf:info
              "Reverse path validation of source address (old command format)";
            tailf:cli-delete-when-empty;
            presence "true";
            leaf access-list {
              tailf:cli-drop-node-name;
              type string {
                tailf:info
                  "WORD;;Access-list name";
              }
            }
          }
        }
      }
      container dhcp {
        tailf:info
          "IPv6 DHCP interface subcommands";
        container relay {
          tailf:info
            "Act as an IPv6 DHCP relay agent";
          list destination {
            tailf:info
              "Configure relay destination";
            tailf:cli-suppress-mode;
            tailf:cli-delete-when-empty;
            tailf:cli-compact-syntax;
            tailf:cli-sequence-commands {
              tailf:cli-reset-siblings;
            }
            key "ipv6-address";
            leaf ipv6-address {
              type inet:ipv6-address {
                tailf:info
                  "X:X:X:X::X;;IPv6 address";
              }
            }
            leaf source-address {
              tailf:info
                "Configure source address to use for relay-forward";
              type inet:ipv6-address {
                tailf:info
                  "X:X:X:X::X;;IPv6 src address";
              }
            }
            leaf link-address {
              tailf:info
                "Configure link-address to use for relay-forward";
              type inet:ipv6-address {
                tailf:info
                  "X:X:X:X::X;;IPv6 link address";
              }
            }
          }
        }
      }
    }
    leaf delay {
      tailf:info
        "Specify interface throughput delay";
      type uint32 {
        tailf:info
          "<1-16777215>;;Throughput delay (tens of microseconds)";
      }
    }
    leaf load-interval {
      tailf:info
        "Specify interval for load calculation for an interface";
      type uint16 {
        tailf:info
          "<30-600>;;Load interval delay in seconds";
        range "0..600";
      }
    }
    container logging {
      tailf:info
        "Configure logging for interface";
      container event {
        tailf:info
          "Interface events";
        leaf link-status {
          tailf:info
            "UPDOWN and CHANGE messages";
          tailf:cli-full-command;
          type empty;
        }
        leaf subif-link-status {
          tailf:info
            "Sub-interface UPDOWN and CHANGE messages";
          tailf:cli-full-command;
          type empty;
        }
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container qos {
        tailf:info
          "qos command keyword";
        leaf channel-consistency {
          tailf:info
            "enable or disable qos consistency checks";
          tailf:cli-boolean-no;
          tailf:cli-full-command;
          type boolean;
          default "true";
        }
        leaf trust {
          tailf:info
            "trust keyword";
          tailf:cli-full-command;
          type enumeration {
            enum "cos" {
              tailf:info
                "cos keyword";
            }
            enum "dscp" {
              tailf:info
                "dscp keyword";
            }
            enum "ip-precedence" {
              tailf:info
                "ip-precedence keyword";
            }
          }
        }
        leaf vlan-based {
          tailf:info
            "vlan-based keyword";
          tailf:cli-full-command;
          type empty;
        }
      }
    }
    leaf mtu {
      tailf:info
        "Set the interface Maximum Transmission Unit (MTU)";
      tailf:cli-full-command;
      type uint16 {
        tailf:info
          "<64-18000>;;MTU size in bytes";
        range "64..18000";
      }
    }
    container ntp {
      tailf:info
        "Configure NTP";
      container broadcast {
        tailf:info
          "Configure NTP broadcast service";
        presence "true";
        container client {
          tailf:info
            "Listen to NTP broadcasts";
          tailf:cli-full-command;
          presence "true";
        }
        list destination {
          tailf:info
            "Configure broadcast destination address";
          tailf:cli-suppress-mode;
          tailf:cli-delete-when-empty;
          tailf:cli-compact-syntax;
          tailf:cli-reset-container;
          key "address";
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
          leaf address {
            type inet:ipv4-address {
              tailf:info
                "A.B.C.D;;Destination broadcast IP address";
            }
          }
        }
        container version-key {
          tailf:cli-drop-node-name;
          tailf:cli-compact-syntax;
          tailf:cli-reset-container;
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
        }
      }
      leaf disable {
        tailf:info
          "Disable NTP traffic (both IP and IPv6)";
        tailf:cli-full-command;
        type empty;
      }
      container multicast {
        tailf:info
          "Configure NTP multicast service";
        tailf:cli-display-separated;
        tailf:cli-compact-syntax;
        presence "true";
        list address-list {
          tailf:cli-drop-node-name;
          tailf:cli-suppress-mode;
          tailf:cli-delete-when-empty;
          tailf:cli-compact-syntax;
          key "group-address";
          leaf group-address {
            type union {
              type inet:ipv4-address {
                tailf:info
                  "A.B.C.D;;Multicast group IP address";
              }
              type inet:ipv6-address {
                tailf:info
                  "X:X:X:X::X;;Multicast group IPv6 address";
              }
            }
          }
          leaf version {
            tailf:info
              "Configure NTP version";
            type uint8 {
              tailf:info
                "<1-4>;;NTP version number";
              range "1..4";
            }
          }
          leaf key {
            tailf:info
              "Configure multicast authentication key";
            type uint32 {
              tailf:info
                "<0-4294967295>;;Multicast key number";
            }
          }
          leaf ttl {
            tailf:info
              "TTL of the multicast packet";
            type uint8 {
              tailf:info
                "<1-255>;;TTL";
              range "1..255";
            }
          }
        }
        leaf version {
          tailf:info
            "Configure NTP version";
          type uint8 {
            tailf:info
              "<1-4>;;NTP version number";
            range "1..4";
          }
        }
        leaf key {
          tailf:info
            "Configure multicast authentication key";
          type uint32 {
            tailf:info
              "<0-4294967295>;;Multicast key number";
          }
        }
        leaf ttl {
          tailf:info
            "TTL of the multicast packet";
          type uint8 {
            tailf:info
              "<1-255>;;TTL";
            range "1..255";
          }
        }
        container client-list {
          tailf:cli-drop-node-name;
          leaf-list client {
            tailf:info
              "Listen to NTP multicasts";
            tailf:cli-list-syntax;
            tailf:cli-suppress-list-no;
            tailf:cli-incomplete-no;
            type union {
              type inet:ipv4-address {
                tailf:info
                  "A.B.C.D;;Multicast client IP address";
              }
              type inet:ipv6-address {
                tailf:info
                  "X:X:X:X::X;;Multicast client IPv6 address";
              }
            }
          }
        }
        leaf client {
          tailf:info
            "Listen to NTP multicasts";
          tailf:cli-full-command;
          type empty;
        }
      }
    }
    container power {
      container inline {
        leaf consumption {
          tailf:cli-full-command;
          type uint16 {
            range "4000..15400";
          }
        }
      }
    }
    list rate-limit {
      tailf:info
        "Rate Limit";
      tailf:cli-suppress-mode;
      tailf:cli-delete-when-empty;
      tailf:cli-compact-syntax;
      key "dir bps bc be conform-action exceed-action";
      leaf dir {
        type enumeration {
          enum "input" {
            tailf:info
              "Rate limit on input";
          }
          enum "output" {
            tailf:info
              "Rate limit on output";
          }
        }
      }
      leaf dscp {
        tailf:info
          "Match dscp value";
        type uint8 {
          tailf:info
            "<0-63>;;dscp";
          range "0..63";
        }
      }
      leaf bps {
        tailf:info
          "<8000-2000000000>;;Bits per second";
        type police-bps-type;
      }
      leaf bc {
        type uint32 {
          tailf:info
            "<1000-512000000>;;Normal burst bytes";
          range "1000..512000000";
        }
      }
      leaf be {
        type uint32 {
          tailf:info
            "<2000-1024000000>;;Maximum burst bytes";
          range "2000..1024000000";
        }
      }
      leaf conform-action {
        tailf:cli-expose-key-name;
        type enumeration {
          enum "transmit";
        }
      }
      leaf exceed-action {
        tailf:cli-expose-key-name;
        type enumeration {
          enum "drop";
        }
      }
    }
    container service-policy {
      tailf:info
        "Configure QoS Service Policy";
      leaf history {
        tailf:cli-full-command;
        tailf:info
          "Keep history of QoS metrics";
        type empty;
      }
      uses ncs_rpc_notif_service-policy-grouping;
      container type {
        tailf:info
          "Configure CPL Service Policy";
        container performance-monitor {
          tailf:info
            "Configure media monitor service-policy type";
          tailf:cli-sequence-commands;
          tailf:cli-compact-syntax;
          leaf direction {
            tailf:cli-drop-node-name;
            type enumeration {
              enum "input" {
                tailf:info
                  "Assign policy-map to the input of an interfcae";
              }
              enum "output" {
                tailf:info
                  "Assign policy-map to the output of an interfcae";
              }
            }
          }
          leaf name {
            tailf:cli-drop-node-name;
            type string {
              tailf:info
                "WORD;;policy-map name";
            }
            // NCS drop tailf-common:non-strict-leafref statement
          }
        }
      }
    }
    leaf shutdown {
      tailf:info
        "Shutdown the selected interface";
      tailf:cli-full-command;
      tailf:cli-show-no;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        type empty;
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        key "group-number";
        leaf group-number {
          tailf:cli-suppress-range;
          type uint16 {
            tailf:info
              "<0-255>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-compact-syntax;
                tailf:cli-sequence-commands {
                  tailf:cli-reset-siblings;
                }
                leaf encrypt {
                  tailf:cli-drop-node-name;
                  type enumeration {
                    enum "0" {
                      tailf:info
                        "Specifies an UNENCRYPTED key string will follow";
                    }
                    enum "7" {
                      tailf:info
                        "Specifies a HIDDEN key string will follow";
                    }
                  }
                }
                leaf string {
                  tailf:cli-drop-node-name;
                  type string {
                    tailf:info
                      "WORD;;Key string (64 chars max)";
                  }
                }
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-sequence-commands;
          tailf:cli-compact-syntax;
          tailf:cli-delete-when-empty;
          presence "true";
          leaf address {
            tailf:cli-drop-node-name;
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container preempt {
          tailf:info
            "Overthrow lower priority Active routers";
          tailf:cli-delete-when-empty;
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        leaf priority {
          tailf:info
            "Priority level";
          tailf:cli-full-command;
          type uint8 {
            tailf:info
              "<0-255>;;Priority value";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-compact-syntax;
                  tailf:cli-sequence-commands {
                    tailf:cli-reset-siblings;
                  }
                  leaf encrypt {
                    tailf:cli-drop-node-name;
                    type enumeration {
                      enum "0" {
                        tailf:info
                          "Specifies an UNENCRYPTED key string will follow";
                      }
                      enum "7" {
                        tailf:info
                          "Specifies a HIDDEN key string will follow";
                      }
                    }
                  }
                  leaf string {
                    tailf:cli-drop-node-name;
                    type string {
                      tailf:info
                        "WORD;;Key string (64 chars max)";
                    }
                  }
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
        list track {
          tailf:info
            "Priority tracking";
          tailf:cli-suppress-mode;
          tailf:cli-delete-when-empty;
          tailf:cli-incomplete-command;
          tailf:cli-compact-syntax;
          key "name";
          leaf name {
            tailf:cli-suppress-range;
            type union {
              type uint16 {
                tailf:info
                  "<0-500>;;Tracked object number";
              }
              type string {
                tailf:info
                  "WORD;;Interface name";
              }
            }
          }
          choice options {
            case interface {
              leaf priority-decrement {
                tailf:cli-drop-node-name;
                type uint16 {
                  tailf:info
                    "<1-255>;;Decrement value";
                }
              }
            }
            case group-number {
              leaf decrement {
                tailf:info
                  "Priority decrement";
                tailf:cli-full-command;
                type uint16 {
                  tailf:info
                    "<1-255>;;Decrement value";
                }
              }
              leaf shutdown {
                tailf:info
                  "Shutdown group";
                tailf:cli-full-command;
                type empty;
              }
            }
          }
        }
      }
    }
    container storm-control {
      tailf:info
        "storm configuration";
      container action {
        tailf:info
          "Action to take for storm-control";
        leaf shutdown {
          tailf:info
            "Shutdown this interface if a storm occurs";
          tailf:cli-full-command;
          type empty;
        }
        leaf trap {
          tailf:info
            "Send SNMP trap if a storm occurs";
          tailf:cli-full-command;
          type empty;
        }
        leaf level {
          tailf:info
            "Set storm suppression level on this interface";
          tailf:cli-full-command;
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
        container include {
          tailf:info
            "include other traffic types";
          leaf multicast {
            tailf:info
              "Suppress broadcast and multicast traffic";
            type empty;
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list dscp-map {
        tailf:info
          "Configure dscp-map for a queue threshold";
        tailf:cli-suppress-mode;
        tailf:cli-delete-when-empty;
        tailf:cli-compact-syntax;
        key "queue threshold";
        leaf queue {
          type uint8 {
            tailf:info
              "<1-7>;;enter dscp-map queue id";
          }
        }
        leaf threshold {
          type uint8 {
            tailf:info
              "<1-4>;;enter dscp-map threshold id";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
        leaf weight-d {
          tailf:cli-drop-node-name;
          type uint8 {
            tailf:info
              "<0-100>;;enter queue size weight";
            range "0..100";
          }
        }
        leaf weight-e {
          tailf:cli-drop-node-name;
          type uint8 {
            tailf:info
              "<0-100>;;enter queue size weight";
            range "0..100";
          }
        }
        leaf weight-f {
          tailf:cli-drop-node-name;
          type uint8 {
            tailf:info
              "<0-100>;;enter queue size weight";
            range "0..100";
          }
        }
        leaf weight-g {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses ncs_rpc_notif_queue-size-grouping;
      }
    }
    container priority-queue {
      tailf:info
        "Configure priority scheduling";
      leaf queue-limit {
        tailf:info
          "configure priority queue limit";
        tailf:cli-full-command;
        type uint8 {
          tailf:info
            "<0-100>;;enter queue size weight";
          range "0..100";
        }
      }
      list dscp-map {
        tailf:info
          "Configure dscp-map for a queue threshold";
        tailf:cli-suppress-mode;
        tailf:cli-delete-when-empty;
        tailf:cli-compact-syntax;
        tailf:cli-incomplete-command;
        key "id";
        leaf id {
          type uint8 {
            tailf:info
              "<1-1>;;enter priority queue id";
            range "1";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      container cos-map {
        tailf:info
          "Configure cos-map for a queue";
        tailf:cli-compact-syntax;
        tailf:cli-sequence-commands;
        leaf id {
          tailf:cli-drop-node-name;
          tailf:cli-incomplete-command;
          type uint8 {
            tailf:info
              "<1-1>;;enter cos-map queue id";
            range "1";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf primary {
          tailf:info
            "Primary Edge Port";
          tailf:cli-optional-in-sequence;
          when '../edge' {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
    container clns {
      tailf:info
        "CLNS interface subcommands";
      leaf route-cache {
        tailf:cli-boolean-no;
        tailf:cli-full-command;
        type boolean;
        default "true";
      }
    }
    container dsu {
      leaf bandwidth {
        tailf:cli-full-command;
        type uint32;
      }
    }
    container isdn {
      tailf:info
        "ISDN Interface configuration commands";
      leaf switch-type {
        tailf:info
          "Select the Interface ISDN switch type";
        tailf:cli-full-command;
        type string {
          pattern 'primary.*';
        }
      }
      leaf protocol-emulate {
        tailf:info
          "Protocol (L2/L3) emulation network/user side";
        tailf:cli-full-command;
        type enumeration {
          enum "network" {
            tailf:info
              "ISDN protocol emulation network side";
          }
          enum "user" {
            tailf:info
              "ISDN protocol emulation user side (default)";
          }
        }
      }
      container incoming-voice {
        tailf:info
          "Specify options for incoming calls.";
        choice incoming-voice-choice {
          leaf voice {
            tailf:info
              "Incoming voice calls will be handled as voice.";
            type empty;
          }
          container data {
            tailf:info
              "Incoming voice calls will be handled as data.";
            tailf:cli-delete-when-empty;
            presence "true";
            leaf kbps {
              tailf:cli-drop-node-name;
              type enumeration {
                enum "56" {
                  tailf:info
                    "56  B Channel Bandwidth of 56Kb/s";
                }
                enum "64" {
                  tailf:info
                    "64  B Channel Bandwidth of 64Kb/s";
                }
              }
            }
          }
          container modem {
            tailf:info
              "Incoming voice calls will be handled as modems.";
            tailf:cli-delete-when-empty;
            presence "true";
            leaf kbps {
              tailf:cli-drop-node-name;
              type enumeration {
                enum "56" {
                  tailf:info
                    "56  B Channel Bandwidth of 56Kb/s  ";
                }
                enum "64" {
                  tailf:info
                    "64  B Channel Bandwidth of 64Kb/s";
                }
              }
            }
          }
        }
      }
      container supp-service {
        tailf:info
          "Specify the subscribed supplementary service";
        container name {
          tailf:info
            "Specify the subscribed name service";
          container calling {
            tailf:info
              "calling name service";
            tailf:cli-delete-when-empty;
            presence "true";
          }
        }
      }
    }
    leaf trunk-group {
      tailf:info
        "Configure interface to be in a trunk group";
      type string {
        tailf:info
          "WORD;;Trunk group label";
      }
      // NCS drop tailf-common:non-strict-leafref statement
    }
    container crypto {
      tailf:info
        "Encryption/Decryption commands";
      container map {
        tailf:info
          "Assign a Crypto Map";
        container ipv4 {
          tailf:cli-drop-node-name;
          tailf:cli-compact-syntax;
          tailf:cli-sequence-commands {
            tailf:cli-reset-siblings;
          }
          leaf map-name {
            tailf:cli-drop-node-name;
            tailf:cli-disallow-value "ipv6";
            type string {
              tailf:info
                "WORD;;Crypto Map tag";
            }
            // NCS drop tailf-common:non-strict-leafref statement
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
        container ipv6 {
          tailf:cli-compact-syntax;
          tailf:cli-sequence-commands {
            tailf:cli-reset-siblings;
          }
          leaf map-name {
            tailf:cli-drop-node-name;
            type string {
              tailf:info
                "WORD;;Crypto Map tag";
            }
            // NCS drop tailf-common:non-strict-leafref statement
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
      }
    }
    container routing {
      tailf:info
        "Per-interface routing configuration";
      leaf dynamic {
        tailf:info
          "participates in routing protocols";
        tailf:cli-boolean-no;
        tailf:cli-full-command;
        type boolean;
        default "true";
      }
    }
  }

  grouping ncs_rpc_notif_interface-tunnel-grouping {
    container tunnel {
      tailf:info
        "protocol-over-protocol tunneling";
      leaf source {
        tailf:info
          "source of tunnel packets";
        type string;
      }
      leaf destination {
        tailf:info
          "destination of tunnel";
        type host-v4v6-type;
      }
      container mode {
        tailf:info
          "tunnel encapsulation method";
        choice mode-choice {
          container ipsec {
            tailf:info
              "IPSec tunnel encapsulation";
            container ipv4 {
              tailf:info
                "over IPv4";
              tailf:cli-delete-when-empty;
              presence "true";
            }
          }
          container mpls {
            container traffic-eng {
              tailf:cli-delete-when-empty;
              presence "true";
              leaf gre-ip {
                type empty;
              }
            }
          }
        }
      }
      container path-mtu-discovery {
        tailf:info
          "Enable Path MTU Discovery on tunnel";
        presence "true";
      }
      container protection {
        tailf:info
          "Enable tunnel protection";
        container ipsec {
          tailf:info
            "Use ipsec to protect this tunnel interface";
          leaf profile {
            tailf:info
              "Determine the ipsec policy profile to use.";
            type string {
              tailf:info
                "WORD;;IPSec policy profile";
            }
            // NCS drop tailf-common:non-strict-leafref statement
          }
        }
      }
      container mpls {
        container traffic-eng {
          container affinity {
            tailf:cli-sequence-commands {
              tailf:cli-reset-siblings;
            }
            tailf:cli-compact-syntax;
            leaf attributes {
              tailf:cli-drop-node-name;
              type string;
            }
            leaf mask {
              type string;
            }
          }
          container autoroute {
            leaf announce {
              tailf:cli-full-command;
              type empty;
            }
          }
          container priority {
            tailf:cli-sequence-commands {
              tailf:cli-reset-siblings;
            }
            tailf:cli-compact-syntax;
            leaf setup-priority {
              tailf:cli-drop-node-name;
              type uint8 {
                range "0..7";
              }
            }
            leaf hold-priority {
              tailf:cli-drop-node-name;
              type uint8 {
                range "0..7";
              }
            }
          }
          leaf bandwidth {
            tailf:cli-full-command;
            type uint32;
          }
          list path-option {
            tailf:cli-suppress-mode;
            tailf:cli-delete-when-empty;
            tailf:cli-sequence-commands {
              tailf:cli-reset-siblings;
            }
            tailf:cli-compact-syntax;
            key "id";
            leaf id {
              type uint32;
            }
            choice path-option-choice {
              container dynamic {
                presence "true";
              }
              container explicit {
                tailf:cli-compact-syntax;
                choice explicit-choice {
                  leaf name {
                    type string;
                  }
                  leaf identifier {
                    type uint32;
                  }
                }
              }
            }
            container lockdown {
              presence "true";
            }
          }
          container fast-reroute {
            presence "true";
          }
        }
      }
    }
  }

  grouping ncs_rpc_notif_interface-ethernet-pre-grouping {
    leaf port-type {
      tailf:info
        "Set port type";
      type enumeration {
        enum "eni" {
          tailf:info
            "Set port-type to ENI";
        }
        enum "nni" {
          tailf:info
            "Set port-type to NNI";
        }
        enum "uni" {
          tailf:info
            "Set port-type to UNI";
        }
      }
    }
  }

  grouping ncs_rpc_notif_interface-ethernet-grouping {
    leaf media-type {
      tailf:info
        "Media type";
      tailf:cli-full-command;
      type enumeration {
        enum "rj45" {
          tailf:info
            "Copper";
        }
        enum "sfp" {
          tailf:info
            "Fiber";
        }
        enum "auto-select" {
          tailf:info
            "Auto Select";
        }
      }
    }
    container carrier-delay {
      tailf:info
        "Specify delay for interface transitions";
      choice delay-choice {
        leaf seconds {
          tailf:cli-drop-node-name;
          type uint8 {
            tailf:info
              "<0-60>;;Carrier Transitions delay seconds";
            range "0..60";
          }
        }
        leaf msec {
          tailf:info
            "delay specified in milliseconds";
          type uint16 {
            tailf:info
              "<0-1000>;;Carrier Transitions delay milliseconds";
            range "0..1000";
          }
        }
      }
    }
    container channel-group {
      tailf:info
        "Add this interface to an Etherchannel group";
      tailf:cli-sequence-commands {
        tailf:cli-reset-siblings;
      }
      tailf:cli-compact-syntax;
      leaf number {
        tailf:cli-drop-node-name;
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container ethernet {
      tailf:info
        "Ethernet interface parameters";
      container oam {
        tailf:info
          "To enable Ethernet Link OAM";
        presence "true";
        leaf max-rate {
          type uint8 {
            tailf:info
              "Maximum number of OAM PDUs sent per second";
            range "1..10";
          }
        }
        leaf min-rate {
          type uint8 {
            tailf:info
              "Minimum transmission rate in seconds";
            range "1..10";
          }
        }
        leaf mode {
          type enumeration {
            enum "active" {
              tailf:info
                "Active OAM client mode";
            }
            enum "passive" {
              tailf:info
                "Passive OAM client mode";
            }
          }
        }
        leaf timeout {
          type uint8 {
            tailf:info
              "OAM client timeout in seconds";
            range "2..30";
          }
        }
      }
      container dot1ad {
        tailf:info
          "dot1ad port";
        choice dot1ad-choice {
          leaf nni {
            tailf:info
              "dot1ad nni port";
            type empty;
          }
          container uni {
            tailf:info
              "dot1ad uni";
            choice uni-choice {
              container c-port {
                tailf:info
                  "dot1ad uni customer bridge port";
                tailf:cli-delete-when-empty;
                presence "true";
                leaf isolate {
                  tailf:info
                    "split horizon";
                  type empty;
                }
              }
              container s-port {
                tailf:info
                  "dot1ad uni s bridge port";
                tailf:cli-delete-when-empty;
                presence "true";
                leaf isolate {
                  tailf:info
                    "split horizon";
                  type empty;
                }
              }
            }
          }
        }
      }
      container cfm {
        tailf:info
          "Ethernet CFM interface commands";
        container mep {
          tailf:info
            "Maintenance End Point";
          list mep-list {
            tailf:cli-drop-node-name;
            tailf:cli-suppress-mode;
            tailf:cli-delete-when-empty;
            tailf:cli-compact-syntax;
            tailf:cli-sequence-commands;
            key "mpid";
            leaf mpid {
              tailf:info
                "Maintenance End Point Identifier";
              tailf:cli-expose-key-name;
              type uint16 {
                tailf:info
                  "<1-8191>;;Maintenance End Point Identifier";
                range "1..8191";
              }
            }
            leaf domain {
              tailf:info
                "maintenance domain";
              tailf:cli-prefix-key;
              type string {
                tailf:info
                  "WORD;;maintenance domain name";
              }
            }
            container service {
              tailf:info
                "Maintenance Association within Domain";
              tailf:cli-flatten-container;
              tailf:cli-compact-syntax;
              choice service-choice {
                leaf short-ma-name {
                  tailf:cli-drop-node-name;
                  type string {
                    tailf:info
                      "WORD;;service instance id - short MA name";
                  }
                }
                leaf number {
                  tailf:info
                    "Maintenance Association number value";
                  type uint16 {
                    tailf:info
                      "<0-65535>;;Maintenance Association number";
                  }
                }
              }
            }
          }
        }
      }
    }
    container negotiation {
      tailf:info
        "Select autonegotiation mode";
      leaf auto {
        tailf:info
          "Enable link autonegotiation";
        tailf:cli-boolean-no;
        type boolean;
      }
    }
    container synchronous {
      tailf:info
        "Synchronous";
      leaf mode {
        tailf:info
          "Mode";
        type empty;
      }
    }
    leaf duplex {
      tailf:info
        "Configure duplex operation.";
      tailf:cli-no-value-on-delete;
      tailf:cli-diff-dependency "../media-type" {
        tailf:xpath-root 3;
      }
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
    }
    leaf full-duplex {
      tailf:info
        "Configure full-duplex operational mode";
      tailf:cli-full-command;
      type empty;
    }
    leaf speed {
      tailf:info
        "Configure speed operation.";
      tailf:cli-diff-dependency "../media-type" {
        tailf:xpath-root 3;
      }
      type enumeration {
        enum "10" {
          tailf:info
            "Force 10 Mbps operation";
        }
        enum "100" {
          tailf:info
            "Force 100 Mbps operation";
        }
        enum "1000" {
          tailf:info
            "Force 1000 Mbps operation";
        }
        enum "auto" {
          tailf:info
            "Enable AUTO speed configuration";
        }
        enum "nonegotiate";
      }
    }
    uses ncs_rpc_notif_interface-xconnect-grouping;
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
    container service {
      tailf:info
        "Configure Ether Service";
      tailf:cli-diff-dependency "../switchport" {
        tailf:xpath-root 3;
      }
      list instance {
        tailf:info
          "Configure Ether Service Instance";
        tailf:cli-mode-name "config-if-srv";
        tailf:cli-compact-syntax;
        tailf:cli-sequence-commands;
        tailf:cli-incomplete-command;
        tailf:cli-diff-dependency "../../switchport" {
          tailf:xpath-root 3;
        }
        key "id";
        leaf id {
          type uint32 {
            tailf:info
              "<1-4294967295>;;Service Instance Identifier";
            range "1..4294967295";
          }
        }
        leaf trunk {
          tailf:cli-optional-in-sequence;
          tailf:cli-prefix-key;
          type empty;
        }
        leaf ethernet {
          tailf:info
            "Configure an Ethernet Instance";
          tailf:cli-hide-in-submode;
          type empty;
        }
        leaf ethernet-evc-name {
          tailf:cli-drop-node-name;
          tailf:cli-hide-in-submode;
          type string {
            tailf:info
              "WORD;;Attach an EVC to the service instance";
          }
          // NCS drop tailf-common:non-strict-leafref statement
        }
        leaf description {
          tailf:cli-break-sequence-commands;
          tailf:info
            "Service instance specific description";
          tailf:cli-multi-value;
          tailf:cli-full-command;
          type string {
            tailf:info
              "LINE;;Up to 240 characters describing this service instance";
            length "0..240";
          }
        }
        leaf evc-name {
          tailf:cli-drop-node-name;
          tailf:cli-hide-in-submode;
          type string {
            tailf:info
              "WORD;;Attach an EVC to the service instance";
            length "1..100";
          }
        }
        container encapsulation {
          tailf:info
            "Configure ethernet frame match criteria";
          container dot1q {
            tailf:info
              "IEEE 802.1Q Virtual LAN or S-VLAN";
            tailf:cli-compact-syntax;
            tailf:cli-sequence-commands {
              tailf:cli-reset-siblings;
            }
            leaf-list id {
              tailf:cli-drop-node-name;
              tailf:cli-replace-all;
              tailf:cli-range-list-syntax;
              type union {
                type uint16 {
                  tailf:info
                    "<1-4094>;;VLAN id";
                  range "1..4094";
                }
                type enumeration {
                  enum "any" {
                    tailf:info
                      "For all VLANS [1-4094]";
                  }
                }
              }
            }
            leaf second-dot1q {
              tailf:cli-break-sequence-commands;
              tailf:info
                "inner 802.1Q Virtual LAN or C-VLAN";
              type union {
                type uint16 {
                  tailf:info
                    "<1-4094>;;VLAN id";
                  range "1..4094";
                }
                type enumeration {
                  enum "any" {
                    tailf:info
                      "For all VLANS [1-4094]";
                  }
                }
              }
            }
            leaf cos {
              tailf:info
                "cos Vlan";
              type uint8 {
                tailf:info
                  "<0-7>;;cos values";
                range "0..7";
              }
            }
            leaf etype {
              tailf:info
                "payload ethertype after Vlan Field";
              type enumeration {
                enum "ipv4" {
                  tailf:info
                    "IPv4";
                }
                enum "ipv6" {
                  tailf:info
                    "IPv6";
                }
                enum "pppoe-all" {
                  tailf:info
                    "PPPoE ALL";
                }
                enum "pppoe-discovery" {
                  tailf:info
                    "PPPoE Discovery Stage";
                }
                enum "pppoe-session" {
                  tailf:info
                    "PPPoE Session Stage";
                }
              }
            }
          }
          container dot1ad {
            tailf:cli-compact-syntax;
            tailf:cli-sequence-commands {
              tailf:cli-reset-siblings;
            }
            leaf-list id {
              tailf:cli-drop-node-name;
              tailf:cli-replace-all;
              tailf:cli-range-list-syntax;
              type union {
                type uint16 {
                  tailf:info
                    "<1-4094>;;VLAN id";
                  range "1..4094";
                }
              }
            }
          }
          container untagged {
            tailf:info
              "Untagged encapsulation";
            presence "true";
          }
          container default {
            tailf:info
              "catch-all unconfigured encapsulation";
            presence "true";
          }
        }
        container rewrite {
          tailf:info
            "Configure ethernet rewrite criteria";
          container ingress {
            tailf:info
              "Ingress Rewrite";
            container tag {
              tailf:info
                "Configure Rewrite Tag";
              tailf:cli-compact-syntax;
              tailf:cli-sequence-commands {
                tailf:cli-reset-siblings;
              }
              choice tag-choice {
                leaf pop {
                  tailf:info
                    "Pop the tag";
                  type enumeration {
                    enum "1" {
                      tailf:info
                        "Pop the outermost tag";
                    }
                    enum "2" {
                      tailf:info
                        "Pop two outermost tags";
                    }
                  }
                }
                case push {
                  leaf push {
                    tailf:info
                      "Rewrite Operation of push";
                    type enumeration {
                      enum "dot1ad" {
                        tailf:info
                          "Push dot1ad tag";
                      }
                      enum "dot1q" {
                        tailf:info
                          "Push dot1q tag";
                      }
                    }
                  }
                  leaf vlan-id {
                    tailf:cli-drop-node-name;
                    type uint16 {
                      tailf:info
                        "<1-4094>;;VLAN id";
                      range "1..4094";
                    }
                  }
                }
              }
              leaf mode {
                tailf:cli-drop-node-name;
                type enumeration {
                  enum "symmetric" {
                    tailf:info
                      "Tag egress packets as specified in encapsulation";
                  }
                }
              }
            }
          }
        }
        leaf group {
          tailf:info
            "Join a service group";
          tailf:cli-full-command;
          type uint16 {
            tailf:info
              "<1-65532>;;Service group ID number";
            range "1..65532";
          }
        }
        container errdisable {
          tailf:info
            "Configure error disable";
          container recovery {
            tailf:info
              "enable auto recovery";
            container cause {
              tailf:info
                "error disable cause";
              leaf mac-security {
                tailf:info
                  "mac-security violation";
                type uint32 {
                  tailf:info
                    "<30-86400>;;timer interval(sec)";
                  range "30..86400";
                }
              }
            }
          }
        }
        container snmp {
          tailf:info
            "Modify SNMP service instance parameters";
          container trap {
            tailf:info
              "Allow a specific SNMP trap";
            leaf link-status {
              tailf:info
                "Allow SNMP LINKUP and LINKDOWN traps";
              type empty;
            }
          }
          container ifindex {
            tailf:info
              "Persist ifindex for the service instance";
            leaf persist {
              tailf:info
                "Enable/Disable ifIndex persistence";
              type empty;
            }
          }
        }
        leaf shutdown {
          tailf:info
            "Take the Service Instance out of Service";
          type empty;
        }
        container bridge-domain {
          tailf:info
            "Bridge-domain";
          tailf:cli-compact-syntax;
          tailf:cli-sequence-commands {
            tailf:cli-reset-all-siblings;
          }
          leaf from-encapsulation {
            tailf:info
              "Derive bridge domains from encapsulation vlan list,";
            tailf:cli-optional-in-sequence;
            tailf:cli-full-command;
            type empty;
          }
          leaf bridge-id {
            tailf:cli-drop-node-name;
            type uint16 {
              tailf:info
                "<1-16384>;;Bridge-domain number";
            }
          }
          container split-horizon {
            tailf:info
              "Configure this port as a member of a split horizon group";
            tailf:cli-flatten-container;
            leaf group {
              tailf:info
                "Split-horizon group";
              type uint8 {
                tailf:info
                  "<0-2>;;Split-horizon group number";
                range "0..2";
              }
            }
          }
        }
        container mac {
          tailf:info
            "Commands for MAC Address-based features";
          container security {
            tailf:info
              "MAC Security commands";
            tailf:cli-display-separated;
            tailf:cli-delete-when-empty;
            presence "true";
            list address {
              tailf:info
                "MAC Address";
              tailf:cli-suppress-mode;
              tailf:cli-delete-when-empty;
              key "operation mac-address";
              leaf operation {
                type enumeration {
                  enum "deny" {
                    tailf:info
                      "Specify an address that must not be learnt";
                  }
                  enum "permit" {
                    tailf:info
                      "Specify an address to statically configure in the MAC table";
                  }
                }
              }
              leaf mac-address {
                type string {
                  tailf:info
                    "H.H.H;;Specify the 48-bit MAC Address to deny/permit";
                }
              }
            }
            container maximum {
              tailf:info
                "Configure an upper bound";
              leaf addresses {
                tailf:info
                  "Maximum addresses that can be learnt on this service instance";
                type uint16 {
                  tailf:info
                    "<1-1000>;;Address count";
                  range "1..1000";
                }
              }
            }
            leaf violation {
              tailf:info
                "Configure the response when a MAC security policy is violated";
              tailf:cli-full-command;
              type enumeration {
                enum "protect" {
                  tailf:info
                    "Protect mode - don't report violations, drop violating frames";
                }
                enum "restrict" {
                  tailf:info
                    "Restrict mode - report violations, drop violating frames";
                }
              }
            }
          }
          container static {
            tailf:info
              "static MAC address";
            list address {
              tailf:info
                "MAC Address";
              tailf:cli-suppress-mode;
              tailf:cli-delete-when-empty;
              key "mac-addr";
              leaf mac-addr {
                type string {
                  tailf:info
                    "H.H.H;;Specify the 48-bit Static MAC Address";
                }
              }
            }
          }
          list access-group {
            tailf:info
              "Specify access control for packets";
            tailf:cli-suppress-mode;
            tailf:cli-delete-when-empty;
            tailf:cli-compact-syntax;
            tailf:cli-sequence-commands;
            key "direction";
            leaf direction {
              type enumeration {
                enum "in" {
                  tailf:info
                    "Apply to Ingress";
                }
                enum "out" {
                  tailf:info
                    "Apply to Egress";
                }
              }
            }
            leaf access-list {
              tailf:cli-drop-node-name;
              tailf:cli-prefix-key;
              type string {
                tailf:info
                  "WORD;;ACL name";
              }
            }
          }
        }
        container l2protocol {
          tailf:info
            "Configure l2 control protocol processing";
          container peer {
            tailf:info
              "peer L2 control protocol packets as data";
            presence "true";
            leaf-list protocol {
              tailf:cli-drop-node-name;
              tailf:cli-flat-list-syntax;
              type enumeration {
                enum "cdp" {
                  tailf:info
                    "Cisco Discovery Protocol";
                }
                enum "dtp" {
                  tailf:info
                    "Dynamic Trunking Protocol";
                }
                enum "lacp" {
                  tailf:info
                    "LACP Protocol";
                }
                enum "lldp" {
                  tailf:info
                    "Link Layer Discovery Protocol";
                }
                enum "pagp" {
                  tailf:info
                    "Port Aggregation Protocol";
                }
                enum "stp" {
                  tailf:info
                    "Spanning Tree Protocol";
                }
                enum "udld" {
                  tailf:info
                    "UDLD Protocol";
                }
                enum "vtp" {
                  tailf:info
                    "Vlan Trunking Protocol";
                }
              }
            }
          }
          container forward {
            tailf:info
              "forward L2 control protocol packets as data";
            presence "true";
            leaf-list protocol {
              tailf:cli-drop-node-name;
              tailf:cli-flat-list-syntax;
              type enumeration {
                enum "cdp" {
                  tailf:info
                    "Cisco Discovery Protocol";
                }
                enum "dtp" {
                  tailf:info
                    "Dynamic Trunking Protocol";
                }
                enum "lacp" {
                  tailf:info
                    "LACP Protocol";
                }
                enum "lldp" {
                  tailf:info
                    "Link Layer Discovery Protocol";
                }
                enum "pagp" {
                  tailf:info
                    "Port Aggregation Protocol";
                }
                enum "stp" {
                  tailf:info
                    "Spanning Tree Protocol";
                }
                enum "udld" {
                  tailf:info
                    "UDLD Protocol";
                }
                enum "vtp" {
                  tailf:info
                    "Vlan Trunking Protocol";
                }
              }
            }
          }
          container tunnel {
            tailf:info
              "tunnel L2 control protocol packets as data";
            presence "true";
          }
        }
        container service-policy {
          tailf:info
            "Attach a policy-map to an EFP";
          tailf:cli-diff-dependency "/ios:policy-map" {
            tailf:xpath-root 3;
          }
          list input {
            tailf:info
              "service policy input";
            tailf:cli-suppress-mode;
            tailf:cli-delete-when-empty;
            max-elements 1;
            key "name";
            leaf name {
              type string {
                tailf:info
                  "WORD;;input Policy-map name";
              }
              // NCS drop tailf-common:non-strict-leafref statement
            }
          }
          list output {
            tailf:info
              "service policy output";
            tailf:cli-suppress-mode;
            tailf:cli-delete-when-empty;
            max-elements 1;
            key "name";
            leaf name {
              type string {
                tailf:info
                  "WORD;;output Policy-map name";
              }
              // NCS drop tailf-common:non-strict-leafref statement
            }
          }
        }
        uses ncs_rpc_notif_interface-xconnect-grouping;
        container cfm {
          tailf:info
            "Ethernet CFM EFP subcommands";
          container mep {
            tailf:info
              "Maintenance End Point";
            tailf:cli-add-mode;
            tailf:cli-mode-name "config-if-srv-ecfm-mep";
            tailf:cli-compact-syntax;
            tailf:cli-sequence-commands;
            leaf domain {
              tailf:info
                "Configure a domain for this mep";
              tailf:cli-hide-in-submode;
              tailf:cli-incomplete-command;
              type string {
                tailf:info
                  "WORD;;maintenance domain name";
              }
            }
            leaf mpid {
              tailf:info
                "Maintenance End Point Identifier";
              tailf:cli-hide-in-submode;
              type uint16 {
                tailf:info
                  "<1-8191>;;Maintenance End Point Identifier";
                range "1..8191";
              }
            }
            container continuity-check {
              tailf:info
                "Enable Continuity Check for this local MEP";
              tailf:cli-break-sequence-commands;
              container static {
                tailf:info
                  "Verify MEP in received CCM is valid";
                leaf rmep {
                  tailf:info
                    "MEP defined using rmep mpid";
                  type empty;
                }
              }
            }
            container rmep {
              tailf:info
                "Static Remote MEP associated with this DOWN MEP";
              leaf mpid {
                tailf:info
                  "Maintenance End Point Identifier";
                type uint16 {
                  tailf:info
                    "<1-8191>;;Identifier value";
                  range "1..8191";
                }
              }
            }
            leaf cos {
              tailf:info
                "Specify Class of Service sent in CFM mssages for EFP MEP";
              type uint8 {
                tailf:info
                  "<0-7>;;CoS value";
                range "0..7";
              }
            }
          }
        }
        container ethernet-if-srv {
          tailf:cli-drop-node-name;
          container ethernet {
            tailf:info
              "ethernet";
            container lmi {
              tailf:info
                "Configure ether lmi parameters";
              container ce-vlan {
                tailf:info
                  "Configure ether lmi customer vlans";
                leaf-list map {
                  tailf:info
                    "Configure ether lmi ce-vlan/evc map";
                  tailf:cli-replace-all;
                  tailf:cli-range-list-syntax;
                  type union {
                    type uint16 {
                      tailf:info
                        "<1-4094>;;VLAN id";
                      range "1..4094";
                    }
                    type enumeration {
                      enum "default" {
                        tailf:info
                          "Default EFP";
                      }
                      enum "untagged" {
                        tailf:info
                          "Untagged frames";
                      }
                    }
                  }
                }
              }
            }
            container loopback {
              tailf:info
                "Ethernet Dataplane Loopback";
              container permit {
                tailf:info
                  "Allow data plane loopback to be activated";
                leaf external {
                  tailf:info
                    "Allow to loopback the traffic from the wire";
                  type empty;
                }
                leaf internal {
                  tailf:info
                    "Allow to loopback the traffic from the relay";
                  type empty;
                }
              }
            }
          }
        }
      }
    }
  }

  grouping ncs_rpc_notif_interface-zone-member-grouping {
    container zone-member {
      tailf:info
        "Apply zone name";
      leaf security {
        tailf:info
          "Security zone";
        type string;
        // NCS drop tailf-common:non-strict-leafref statement
      }
    }
  }

  grouping ncs_rpc_notif_interface-pointtopoint-grouping {
    container ppp {
      tailf:info
        "Point-to-Point Protocol";
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container ipcp {
        tailf:info
          "Set IPCP negotiation options";
        container dns {
          tailf:info
            "Specify DNS negotiation options";
          tailf:cli-compact-syntax;
          tailf:cli-sequence-commands;
          leaf primary {
            tailf:cli-drop-node-name;
            type inet:ipv4-address {
              tailf:info
                "A.B.C.D;;Primary DNS IP address";
            }
          }
        }
      }
      container multilink {
        tailf:info
          "Make interface multilink capable";
        tailf:cli-display-separated;
        presence "true";
        leaf interleave {
          tailf:info
            "Allow interleaving of small packets with fragments";
          type empty;
        }
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          leaf disable {
            tailf:info
              "Suppress multilink fragmentation when possible";
            tailf:cli-full-command;
            type empty;
          }
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
        container queue {
          tailf:info
            "Specify link queuing parameters";
          container depth {
            tailf:info
              "Specify maximum depth for link transmit queues";
            leaf fifo {
              tailf:info
                "Set max depth for link queues when bundle has FIFO queuing";
              type uint8 {
                tailf:info
                  "<2-255>;;Max queue depth for link";
                range "2..255";
              }
            }
            leaf qos {
              tailf:info
                "Set max depth for link queues when bundle has non-FIFO queuing";
              type uint8 {
                tailf:info
                  "<2-255>;;Max queue depth for link";
                range "2..255";
              }
            }
          }
        }
      }
    }
    container dialer {
      tailf:info
        "Dial-on-demand routing (DDR) commands";
      container in-band {
        tailf:info
          "Set v.25bis dialing for interface";
        tailf:cli-delete-when-empty;
        presence "true";
        leaf parity {
          tailf:cli-drop-node-name;
          type enumeration {
            enum "no-parity" {
              tailf:info
                "No parity";
            }
            enum "odd-parity" {
              tailf:info
                "Odd parity";
            }
          }
        }
      }
      container idle-timeout {
        tailf:info
          "Specify idle timeout before disconnecting line";
        tailf:cli-compact-syntax;
        tailf:cli-sequence-commands {
          tailf:cli-reset-siblings;
        }
        leaf seconds {
          tailf:cli-drop-node-name;
          type uint32 {
            tailf:info
              "<0-2147483>;;Idle timeout before disconnecting a call";
          }
        }
        leaf direction {
          tailf:cli-drop-node-name;
          type enumeration {
            enum "either" {
              tailf:info
                "Reset idle timer based on both inbound and outbound traffic";
            }
            enum "inbound" {
              tailf:info
                "Reset idle timer based on inbound traffic only";
            }
          }
        }
      }
      leaf enable-timeout {
        tailf:info
          "Set length of time an interface stays down before it is available for dialing";
        type uint32 {
          tailf:info
            "<1-2147483>;;Enable timeout in seconds";
          range "1..2147483";
        }
      }
      leaf string {
        tailf:info
          "Specify telephone number to be passed to DCE device";
        type string {
          tailf:info
            "WORD;;Dialer string (quote strings containing #)";
        }
      }
      leaf watch-group {
        tailf:info
          "Assign interface to dialer-watch-list";
        type uint16 {
          tailf:info
            "<1-255>;;Dialer watch group number";
          range "1..255";
        }
        // NCS drop tailf-common:non-strict-leafref statement
      }
    }
    leaf physical-layer {
      tailf:info
        "Configure sync or async physical layer on serial interface";
      type enumeration {
        enum "async" {
          tailf:info
            "Configure asynchronous physical layer on serial interface";
        }
        enum "sync" {
          tailf:info
            "Configure synchronous physical layer on serial interface";
        }
      }
    }
    container async {
      tailf:info
        "Async interface parameters";
      container mode {
        tailf:info
          "Specify line mode (interactive or dedicated interface use)";
        leaf dedicated {
          tailf:info
            "Line is dedicated as an async interface";
          type empty;
        }
        leaf interactive {
          tailf:info
            "Line may be switched between interactive use and async interface";
          type empty;
        }
      }
    }
    container pulse-time {
      tailf:info
        "Force DTR low during resets";
      choice pulse-time-choice {
        leaf seconds {
          tailf:cli-drop-node-name;
          type uint8 {
            tailf:info
              "<0-60>;;DTR low time in seconds";
            range "0..60";
          }
        }
        leaf msec {
          tailf:info
            "millisecond (resolution)";
          type uint16 {
            tailf:info
              "<1-59999>;;DTR low time in milliseconds";
            range "1..59999";
          }
        }
      }
    }
  }

  grouping ncs_rpc_notif_crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping ncs_rpc_notif_router-bgp-max-path-grouping {
    container paths {
      tailf:cli-drop-node-name;
      tailf:cli-compact-syntax;
      tailf:cli-sequence-commands {
        tailf:cli-reset-siblings;
      }
      leaf number-of-paths {
        tailf:cli-drop-node-name;
        type uint16 {
          tailf:info
            "<1-16>;;Number of paths";
          range "1..16";
        }
        default "1";
      }
      leaf import {
        tailf:info
          "Maximum import paths";
        type uint16 {
          tailf:info
            "<1-16>;;Number of import paths";
          range "1..16";
        }
      }
    }
  }

  grouping ncs_rpc_notif_router-bgp-redistribute-grouping {
    leaf metric {
      tailf:cli-break-sequence-commands;
      tailf:info
        "Metric for redistributed routes";
      type uint32 {
        tailf:info
          "<0-4294967295>;;Default metric";
        range "0..4294967295";
      }
    }
    leaf route-map {
      tailf:info
        "Route map reference";
      type string {
        tailf:info
          "WORD;;Pointer to route-map entries";
      }
    }
  }

  grouping ncs_rpc_notif_route-map-metric-grouping {
    leaf route-map {
      tailf:info
        "Route map reference";
      type string {
        tailf:info
          "WORD;;Pointer to route-map entries";
      }
    }
    leaf metric {
      tailf:info
        "Metric for redistributed routes";
      type uint32 {
        tailf:info
          "<0-4294967295>;;Default metric";
        range "0..4294967295";
      }
    }
  }

  grouping ncs_rpc_notif_redistribute-isis-grouping {
    choice osi-ip-choice {
      leaf ip {
        tailf:info
          "Redistribution of IP dynamic routes";
        type empty;
      }
      leaf clns {
        tailf:info
          "Redistribution of OSI dynamic routes";
        type empty;
      }
    }
    leaf level {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    uses ncs_rpc_notif_router-bgp-redistribute-grouping;
  }

  grouping ncs_rpc_notif_router-bgp-grouping {
    container bgp-top {
      tailf:cli-drop-node-name;
      container bgp {
        container bestpath {
          tailf:info
            "Change the default bestpath selection";
          container as-path {
            leaf multipath-relax {
              type empty;
            }
          }
        }
      }
    }
    container timers {
      tailf:info
        "Adjust routing timers";
      container bgp {
        tailf:info
          "BGP timers";
        tailf:cli-compact-syntax;
        tailf:cli-sequence-commands {
          tailf:cli-reset-siblings;
        }
        leaf keepalive {
          tailf:cli-drop-node-name;
          tailf:cli-incomplete-command;
          type uint16 {
            tailf:info
              "<0-65535>;;Keepalive interval";
            range "0..65535";
          }
        }
        leaf holdtime {
          tailf:cli-drop-node-name;
          type uint16 {
            tailf:info
              "<0-65535>;;Holdtime";
            range "0..65535";
          }
        }
        leaf min-holdtime {
          tailf:cli-drop-node-name;
          type uint16 {
            tailf:info
              "<0-65535>;;Minimum hold time from neighbor";
            range "0..65535";
          }
        }
      }
    }
  }

  grouping ncs_rpc_notif_router-bgp-peer-policy-grouping {
    leaf advertisement-interval {
      tailf:info
        "Minimum interval between sending BGP routing updates";
      tailf:cli-full-command;
      type uint16 {
        tailf:info
          "<0-600>;;time in seconds";
        range "0..600";
      }
    }
    container send-community {
      tailf:info
        "Send Community attribute to this neighbor";
      tailf:cli-delete-when-empty;
      presence "true";
      leaf send-community-where {
        tailf:cli-drop-node-name;
        type enumeration {
          enum "both" {
            tailf:info
              "Send Standard and Extended Community attributes";
          }
          enum "extended" {
            tailf:info
              "Send Extended Community attribute";
          }
          enum "standard" {
            tailf:code-name "send_standard";
            tailf:info
              "Send Standard Community attribute";
          }
        }
      }
    }
    container maximum-prefix {
      tailf:info
        "Maximum number of prefixes accepted from this peer";
      tailf:cli-compact-syntax;
      tailf:cli-sequence-commands {
        tailf:cli-reset-all-siblings;
      }
      leaf max-prefix-no {
        tailf:cli-drop-node-name;
        type uint32 {
          tailf:info
            "<1-2147483647>;;maximum no. of prefix limit";
          range "1..2147483647";
        }
      }
      leaf threshold {
        tailf:cli-drop-node-name;
        tailf:cli-break-sequence-commands;
        type uint8 {
          tailf:info
            "<1-100>;;Threshold value (%) at which to generate a warning msg";
          range "1..100";
        }
      }
      leaf restart {
        tailf:cli-full-command;
        tailf:info
          "Restart bgp connection after limit is exceeded";
        type uint16 {
          tailf:info
            "<1-65535>;;Restart interval in minutes";
          range "1..65535";
        }
      }
      leaf warning-only {
        tailf:cli-full-command;
        tailf:info
          "Only give warning message when limit is exceeded";
        type empty;
      }
    }
    container allowas-in {
      tailf:info
        "Accept as-path with my AS present in it";
      tailf:cli-delete-when-empty;
      presence "accept as-paths";
      leaf as-number {
        tailf:cli-drop-node-name;
        type uint8 {
          tailf:info
            "<1-10>;;Number of occurances of AS number";
          range "1..10";
        }
      }
    }
    container as-override {
      tailf:info
        "Override matching AS-number while sending update";
      tailf:cli-delete-when-empty;
      presence "true";
      leaf disable {
        type empty;
      }
    }
  }

  grouping ncs_rpc_notif_router-bgp-peer-session-grouping {
    leaf remote-as {
      tailf:info
        "Specify a BGP neighbor";
      tailf:cli-delete-container-on-delete;
      tailf:cli-full-command;
      type string {
        tailf:info
          "AS of remote neighbor";
      }
    }
    container password {
      tailf:info
        "Set a password";
      tailf:cli-compact-syntax;
      tailf:cli-sequence-commands {
        tailf:cli-reset-siblings;
      }
      leaf enctype {
        tailf:cli-optional-in-sequence;
        tailf:cli-drop-node-name;
        tailf:cli-incomplete-command;
        type uint8 {
          tailf:info
            "<0-7>;;Encryption type (0 to disable encryption, 7 for proprietary)";
          range "0..7";
        }
      }
      leaf text {
        tailf:cli-drop-node-name;
        tailf:cli-multi-value;
        tailf:cli-full-command;
        tailf:cli-disallow-value "0|1|2|3|4|5|6|7";
        type string {
          tailf:info
            "LINE;;The password";
        }
      }
    }
    container ttl-security {
      tailf:info
        "BGP ttl security check";
      leaf hops {
        tailf:info
          "IP hops";
        type uint8 {
          tailf:info
            "<1-254>;;maximum number of hops";
          range "1..254";
        }
      }
    }
    container timers {
      tailf:info
        "BGP per neighbor timers";
      tailf:cli-compact-syntax;
      tailf:cli-sequence-commands {
        tailf:cli-reset-siblings;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          range "0..65535";
          tailf:info
            "<0-65535>;;Holdtime";
        }
      }
      leaf minimum-neighbor-hold {
        tailf:cli-drop-node-name;
        type uint16 {
          tailf:info
            "<0-65535>;;Minimum hold time from neighbor";
          range "0..65535";
        }
      }
    }
    container fall-over {
      tailf:info
        "session fall on peer route lost";
      presence "true";
      leaf bfd {
        tailf:info
          "Use BFD to detect failure";
        tailf:cli-full-command;
        type empty;
      }
      leaf route-map {
        tailf:info
          "Route map for peer route";
        tailf:cli-full-command;
        type string {
          tailf:info
            "WORD;;Name of the route map";
        }
      }
    }
  }

  grouping ncs_rpc_notif_router-bgp-neighbor-grouping {
    container peer-group {
      tailf:info
        "Member of the peer-group";
      tailf:cli-delete-when-empty;
      presence "true";
      leaf peer-group-name {
        tailf:info
          "WORD;;peer-group name";
        tailf:cli-drop-node-name;
        tailf:cli-delete-container-on-delete;
        tailf:cli-full-command;
        type string;
      }
    }
    container local-as {
      tailf:info
        "Specify a local-as number";
      tailf:cli-compact-syntax;
      tailf:cli-sequence-commands {
        tailf:cli-reset-siblings;
      }
      tailf:cli-delete-when-empty;
      presence "Specify a local-as number";
      leaf as-no {
        tailf:cli-drop-node-name;
        type uint16 {
          range "1..65535";
          tailf:info
            "<1-65535>;;AS number used as local AS";
        }
      }
      leaf no-prepend {
        tailf:info
          "Do not prepend local-as to updates from ebgp peers";
        type empty;
      }
      leaf replace-as {
        tailf:info
          "Replace real AS with local AS in the EBGP updates";
        type empty;
      }
      leaf dual-as {
        tailf:info
          "Accept either real AS or local AS from the ebgp peer";
        type empty;
      }
    }
    uses ncs_rpc_notif_router-bgp-peer-session-grouping;
    leaf activate {
      tailf:info
        "Enable the Address Family for this Neighbor";
      tailf:cli-full-command;
      type empty;
    }
    uses ncs_rpc_notif_router-bgp-peer-policy-grouping;
    leaf soo {
      tailf:info
        "Site-of-Origin extended community";
      tailf:cli-full-command;
      type string {
        tailf:info
          "ASN:nn or IP-address:nn;;VPN extended community";
      }
    }
    container capability {
      tailf:info
        "Advertise capability to the peer";
      container orf {
        tailf:info
          "Advertise ORF capability to the peer";
        leaf-list prefix-list {
          tailf:cli-flat-list-syntax;
          tailf:info
            "Advertise prefixlist ORF capability to this neighbor";
          max-elements 1;
          type enumeration {
            enum "both" {
              tailf:info
                "Capability to SEND and RECEIVE the ORF to/from this neighbor";
            }
            enum "receive" {
              tailf:info
                "Capability to RECEIVE the ORF from this neighbor";
            }
            enum "send" {
              tailf:info
                "Capability to SEND the ORF to this neighbor";
            }
          }
        }
      }
    }
    container default-originate {
      tailf:info
        "Originate default route to this neighbour";
      tailf:cli-delete-when-empty;
      presence "enable originate default route to this neighbour";
      leaf route-map {
        tailf:info
          "Route-map to specify criteria to originate default";
        type string {
          tailf:info
            "WORD;;route-map name";
        }
      }
    }
    leaf description {
      tailf:info
        "Neighbor specific description";
      tailf:cli-full-command;
      tailf:cli-multi-value;
      type string {
        tailf:info
          "LINE;;Up to 80 characters describing this neighbor";
      }
    }
    leaf disable-connected-check {
      tailf:info
        "One-hop away EBGP peer using loopback address";
      tailf:cli-full-command;
      type empty;
    }
    uses ncs_rpc_notif_router-distribute-list-grouping;
    leaf dmzlink-bw {
      tailf:info
        "Propagate the DMZ link bandwidth";
      tailf:cli-full-command;
      type empty;
    }
    container ebgp-multihop {
      tailf:info
        "Allow EBGP neighbors not on directly connected networks";
      tailf:cli-delete-when-empty;
      presence "Allow EBGP neighbors not on directly connected networks";
      leaf max-hop {
        tailf:cli-drop-node-name;
        type uint8 {
          range "1..255";
          tailf:info
            "<1-255>;;maximum hop count";
        }
      }
    }
    list filter-list {
      tailf:info
        "Establish BGP filters";
      tailf:cli-suppress-mode;
      tailf:cli-delete-when-empty;
      key "inout";
      leaf inout {
        type enumeration {
          enum "in" {
            tailf:code-name "filter_in";
            tailf:info
              "Filter incoming routes";
          }
          enum "out" {
            tailf:code-name "filter_out";
            tailf:info
              "Filter outgoing routes";
          }
        }
      }
      leaf as-path-list {
        tailf:cli-drop-node-name;
        tailf:cli-prefix-key;
        type uint16 {
          range "1..500";
          tailf:info
            "<1-500>;;AS path access list";
        }
        mandatory true;
      }
    }
    container inherit {
      tailf:info
        "Inherit a template";
      leaf peer-policy {
        tailf:info
          "Inherit a peer-policy template";
        tailf:cli-full-command;
        type string {
          tailf:info
            "WORD;;Template name";
        }
      }
      leaf peer-session {
        tailf:info
          "Inherit a peer-session template";
        tailf:cli-full-command;
        type string {
          tailf:info
            "WORD;;Template name";
        }
      }
    }
    leaf next-hop-self {
      tailf:cli-full-command;
      tailf:info
        "Disable the next hop calculation for this neighbor";
      type empty;
    }
    container next-hop-self-arg {
      tailf:cli-drop-node-name;
      leaf next-hop-self {
        type string;
      }
    }
    leaf next-hop-unchanged {
      tailf:cli-full-command;
      tailf:info
        "Propagate the iBGP paths's next hop unchanged for this neighbor";
      type empty;
    }
    list prefix-list {
      tailf:info
        "Filter updates to/from this neighbor";
      tailf:cli-suppress-mode;
      tailf:cli-delete-when-empty;
      key "direction";
      leaf direction {
        type enumeration {
          enum "in" {
            tailf:info
              "Filter incoming updates";
          }
          enum "out" {
            tailf:info
              "Filter outgoing updates";
          }
        }
      }
      leaf prefix-list-name {
        tailf:cli-drop-node-name;
        tailf:cli-prefix-key;
        type string {
          tailf:info
            "WORD;;Name of a prefix list";
        }
        mandatory true;
      }
    }
    leaf remove-private-as {
      tailf:info
        "Remove private AS number from outbound updates";
      tailf:cli-full-command;
      type empty;
    }
    list route-map {
      tailf:info
        "Apply route map to neighbor";
      tailf:cli-suppress-mode;
      tailf:cli-delete-when-empty;
      key "direction";
      leaf direction {
        type enumeration {
          enum "in" {
            tailf:info
              "Apply map to incoming routes";
          }
          enum "out" {
            tailf:info
              "Apply map to outbound routes";
          }
        }
      }
      leaf route-map-name {
        tailf:cli-drop-node-name;
        tailf:cli-prefix-key;
        type string {
          tailf:info
            "WORD;;Name of route map";
        }
        mandatory true;
      }
    }
    leaf route-reflector-client {
      tailf:cli-full-command;
      tailf:info
        "Configure a neighbor as Route Reflector client";
      type empty;
    }
    container send-label {
      tailf:info
        "Send NLRI + MPLS Label to this peer";
      tailf:cli-delete-when-empty;
      presence "true";
      leaf explicit-null {
        tailf:info
          "Advertise Explicit Null label in place of Implicit Null";
        type empty;
      }
    }
    leaf shutdown {
      tailf:cli-full-command;
      tailf:info
        "Administratively shut down this neighbor";
      type empty;
    }
    leaf soft-reconfiguration {
      tailf:cli-full-command;
      tailf:info
        "Per neighbor soft reconfiguration";
      type enumeration {
        enum "inbound" {
          tailf:info
            "Allow inbound soft reconfiguration for this neighbor";
        }
      }
    }
    container translate-update {
      tailf:info
        "Translate Update to MBGP format";
      container ipv4 {
        tailf:info
          "Address Family";
        container multicast {
          tailf:info
            "Address Family modifier";
          tailf:cli-delete-when-empty;
          presence "Address Family modifier";
          leaf unicast {
            tailf:info
              "Address Family modifier";
            type empty;
          }
        }
      }
    }
    container transport {
      tailf:info
        "Transport options";
      leaf connection-mode {
        tailf:info
          "Specify passive or active connection";
        type enumeration {
          enum "active" {
            tailf:info
              "Actively establish the TCP session";
          }
          enum "passive" {
            tailf:info
              "Passively establish the TCP session";
          }
        }
      }
    }
    leaf unsuppress-map {
      tailf:info
        "Route-map to selectively unsuppress suppressed routes";
      tailf:cli-full-command;
      type string {
        tailf:info
          "WORD;;Name of route map";
      }
    }
    container update-source {
      tailf:info
        "Source of routing updates";
      uses ncs_rpc_notif_interface-name-grouping;
    }
    leaf version {
      tailf:cli-full-command;
      tailf:info
        "Set the BGP version to match a neighbor";
      type uint16 {
        range "4";
        tailf:info
          "<4-4>;;Neighbor's BGP version";
      }
    }
    leaf weight {
      tailf:info
        "Set default weight for routes from this neighbor";
      tailf:cli-full-command;
      type uint16 {
        tailf:info
          "<0-65535>;;default weight";
        range "0..65535";
      }
    }
    container ha-mode {
      tailf:info
        "high availability mode";
      container graceful-restart {
        tailf:info
          "graceful-restart for this peer";
        presence "true";
        leaf disable {
          tailf:info
            "disable graceful-restart";
          type empty;
        }
      }
      container sso {
        tailf:info
          "stateful-switchover support for this peer";
        presence "true";
        leaf disable {
          tailf:info
            "disable stateful-switchover";
          type empty;
        }
      }
    }
    container suppress-signaling-protocol {
      tailf:info
        "suppress VPLS signaling protocol";
      leaf ldp {
        tailf:info
          "suppress ldp signaling, enable bgp signaling";
        tailf:cli-full-command;
        type empty;
      }
    }
    leaf prefix-length-size {
      tailf:info
        "Packet Level storage size for Prefixes";
      type uint8 {
        tailf:info
          "<1-2>;;Storage size in bytes";
        range "1..2";
      }
    }
  }

  grouping ncs_rpc_notif_router-bgp-af-grouping {
    container aggregate-address {
      tailf:info
        "Configure BGP aggregate entries";
      tailf:cli-compact-syntax;
      tailf:cli-sequence-commands {
        tailf:cli-reset-all-siblings;
      }
      leaf address {
        tailf:cli-drop-node-name;
        type inet:ipv4-address {
          tailf:info
            "A.B.C.D;;Aggregate address";
        }
      }
      leaf mask {
        tailf:cli-drop-node-name;
        type inet:ipv4-address {
          tailf:info
            "A.B.C.D;;Aggregate mask";
        }
      }
      leaf advertise-map {
        tailf:cli-break-sequence-commands;
        tailf:info
          "Set condition to advertise attribute";
        type string {
          tailf:info
            "WORD;;Route map to control attribute advertisement";
        }
      }
      leaf as-set {
        tailf:info
          "Generate AS set path information";
        type empty;
      }
      leaf attribute-map {
        type string {
          tailf:info
            "WORD;;Route map for parameter control";
        }
      }
      leaf as-override {
        tailf:info
          "Override matching AS-number while sending update";
        type empty;
      }
      leaf route-map {
        type string {
          tailf:info
            "WORD;;Route map for parameter control";
        }
      }
      leaf summary-only {
        tailf:info
          "Filter more specific routes from updates";
        type empty;
      }
      leaf suppress-map {
        tailf:info
          "Conditionally filter more specific routes from updates";
        type string {
          tailf:info
            "WORD;;Route map for suppression";
        }
      }
    }
    container bgp {
      tailf:info
        "BGP specific commands";
      leaf router-id {
        tailf:cli-full-command;
        tailf:info
          "Override configured router identifier (peers will reset)";
        type inet:ipv4-address {
          tailf:info
            "A.B.C.D;;Manually configured router identifier";
        }
      }
      leaf always-compare-med {
        tailf:info
          "Allow comparing MED from different neighbors";
        tailf:cli-full-command;
        type empty;
      }
      container bestpath {
        tailf:info
          "Change the default bestpath selection";
        leaf compare-routerid {
          tailf:info
            "Compare router-id for identical EBGP paths";
          tailf:cli-full-command;
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
      }
      container client-to-client {
        tailf:info
          "Configure client to client route reflection";
        leaf reflection {
          tailf:info
            "reflection of routes allowed";
          type empty;
        }
      }
      leaf cluster-id {
        tailf:cli-full-command;
        type union {
          type uint32 {
            range "1..4294967295";
            tailf:info
              "<1-4294967295>;;Route-Reflector Cluster-id as 32 bit quantity";
          }
          type inet:ipv4-address {
            tailf:info
              "A.B.C.D;;Route-Reflector Cluster-id in IP address format";
          }
        }
      }
      container confederation {
        tailf:info
          "AS confederation parameters";
        leaf identifier {
          tailf:cli-full-command;
          tailf:info
            "as number";
          type uint16 {
            range "1..65535";
            tailf:info
              "<1-65535>;;Set routing domain confederation AS";
          }
        }
        container peers {
          tailf:info
            "Peer ASs in BGP confederation";
          presence "Peer ASs in BGP confederation";
          leaf-list peers-as {
            tailf:cli-drop-node-name;
            tailf:cli-flat-list-syntax;
            type uint16 {
              range "1..65535";
              tailf:info
                "AS number";
            }
          }
        }
      }
      container dampening {
        tailf:info
          "Enable route-flap dampening";
        presence "true";
        choice dampening-choice {
          leaf route-map {
            tailf:info
              "Route-map to specify criteria for dampening";
            type string {
              tailf:info
                "WORD;;route-map name";
            }
          }
          container dampen {
            tailf:cli-drop-node-name;
            tailf:cli-compact-syntax;
            tailf:cli-sequence-commands;
            leaf half-life-time {
              tailf:cli-drop-node-name;
              tailf:cli-incomplete-command;
              type uint8 {
                tailf:info
                  "<1-45>;;Half-life time for the penalty";
                range "1..45";
              }
            }
            leaf reuse-time {
              tailf:cli-drop-node-name;
              tailf:cli-incomplete-command;
              type uint16 {
                tailf:info
                  "<1-20000>;;Value to start reusing a route";
                range "1..20000";
              }
            }
            leaf suppress-time {
              tailf:cli-drop-node-name;
              tailf:cli-incomplete-command;
              type uint16 {
                tailf:info
                  "<1-20000>;;Value to start suppressing a route";
                range "1..20000";
              }
            }
            leaf max-suppress-time {
              tailf:cli-drop-node-name;
              type uint8 {
                tailf:info
                  "<1-255>;;Maximum duration to suppress a stable route";
                range "1..255";
              }
            }
          }
        }
      }
      container default {
        tailf:info
          "Configure BGP defaults";
        leaf ipv4-unicast {
          tailf:info
            "Activate ipv4-unicast for a peer by default";
          tailf:cli-boolean-no;
          type boolean;
          default "true";
        }
        leaf ipv4-activate {
          tailf:cli-boolean-no;
          type boolean;
          default "true";
        }
        leaf local-preference {
          tailf:info
            "local preference (higher=more preferred)";
          type uint32 {
            tailf:info
              "<0-4294967295>;;Configure default local preference value";
            range "1..4294967295";
          }
        }
        container route-target {
          tailf:info
            "Control behavior based on Route-Target attributes";
          leaf filter {
            tailf:info
              "Control automatic VPN Route-Target filtering";
            tailf:cli-boolean-no;
            type boolean;
            default "true";
          }
        }
      }
      leaf deterministic-med {
        tailf:cli-full-command;
        tailf:info
          "Pick the best-MED path among paths advertised from the neighboring AS";
        type empty;
      }
      leaf dmzlink-bw {
        tailf:cli-full-command;
        tailf:info
          "Use DMZ Link Bandwidth as weight for BGP multipaths";
        type empty;
      }
      leaf enforce-first-as {
        tailf:info
          "Enforce the first AS for EBGP routes(default)";
        tailf:cli-full-command;
        type empty;
      }
      leaf fast-external-fallover {
        tailf:info
          "Immediately reset session if a link to a directly connected external peer goes down";
        tailf:cli-full-command;
        type empty;
      }
      container graceful-restart {
        tailf:info
          "Graceful restart capability parameters";
        tailf:cli-display-separated;
        tailf:cli-delete-when-empty;
        presence "true";
        leaf restart-time {
          tailf:cli-full-command;
          tailf:info
            "Set the max time needed to restart and come back up";
          type uint16 {
            tailf:info
              "<1-3600>;;Delay value (seconds)";
            range "1..3600";
          }
        }
        leaf stalepath-time {
          tailf:info
            "Set the max time to hold onto restarting peer's stale paths";
          type uint16 {
            tailf:info
              "<1-3600>;;Delay value (seconds)";
            range "1..3600";
          }
        }
      }
      list inject-map {
        tailf:info
          "Routemap which specifies prefixes to inject";
        tailf:cli-compact-syntax;
        tailf:cli-sequence-commands;
        tailf:cli-incomplete-command;
        tailf:cli-delete-when-empty;
        key "name";
        leaf name {
          type string {
            tailf:info
              "WORD;;route-map name";
          }
        }
        leaf exist-map {
          tailf:info
            "Routemap which specifies exist condition";
          type string {
            tailf:info
              "WORD;;route-map name";
          }
        }
        leaf copy-attributes {
          tailf:info
            "Copy attributes from aggregate";
          type empty;
        }
      }
      container transport {
        tailf:info
          "global enable/disable transport session parameters";
        leaf path-mtu-discovery {
          tailf:info
            "transport path MTU discovery";
          tailf:cli-boolean-no;
          tailf:cli-full-command;
          type boolean;
          default "true";
        }
      }
      leaf log-neighbor-changes {
        tailf:info
          "Log neighbor up/down and reset reason";
        tailf:cli-full-command;
        type empty;
      }
      container listen {
        tailf:info
          "Neighbor subnet range listener";
        tailf:cli-delete-when-empty;
        presence "true";
        container range {
          tailf:cli-compact-syntax;
          tailf:cli-sequence-commands {
            tailf:cli-reset-siblings;
          }
          leaf network-length {
            tailf:cli-drop-node-name;
            tailf:cli-incomplete-command;
            type ios:ipv4-prefix {
              tailf:info
                "A.B.C.D/nn;;Subnet range <network>/<length>, e.g., 10.0.0.0/24";
            }
          }
          leaf peer-group {
            tailf:info
              "Member of the peer-group";
            type string {
              tailf:info
                "WORD;;peer-group name";
            }
          }
        }
        leaf limit {
          tailf:info
            "Set the max limit for the dynamic subnet range neighbors";
          type uint32 {
            tailf:info
              "<1-5000>;;max number";
            range "1..5000";
          }
        }
      }
      leaf maxas-limit {
        tailf:info
          "Allow AS-PATH attribute from any neighbor imposing a limit on number of ASes";
        tailf:cli-full-command;
        type uint16 {
          range "1..2000";
          tailf:info
            "<1-2000>;;Number of ASes in the AS-PATH attribute";
        }
      }
      container additional-paths {
        tailf:info
          "Additional paths in the BGP table";
        choice send-receive-choice {
          leaf receive {
            tailf:info
              "Receive additional paths from neighbors";
            tailf:cli-full-command;
            type empty;
          }
          container send {
            tailf:info
              "Send additional paths to neighbors";
            tailf:cli-delete-when-empty;
            presence "true";
            leaf receive {
              tailf:info
                "Receive additional paths from neighbors";
              type empty;
            }
          }
        }
        leaf install {
          tailf:info
            "Additional paths to install into RIB";
          tailf:cli-full-command;
          type empty;
        }
      }
      container nexthop {
        tailf:info
          "Nexthop tracking commands";
        container trigger {
          tailf:info
            "Nexthop triggering";
          leaf delay {
            tailf:cli-full-command;
            tailf:info
              "Set the delay to tigger nexthop tracking";
            type uint8 {
              tailf:info
                "<0-100>;;Delay value (seconds)";
              range "0..100";
            }
          }
          leaf enable {
            tailf:info
              "Enable nexthop tracking";
            tailf:cli-full-command;
            tailf:cli-boolean-no;
            type boolean;
            default "true";
          }
        }
      }
      leaf redistribute-internal {
        tailf:info
          "Allow redistribution of iBGP into IGPs (dangerous)";
        tailf:cli-full-command;
        type empty;
      }
      container regexp {
        tailf:info
          "Select regular expression engine";
        leaf deterministic {
          tailf:info
            "Enable bounded-execution-time regular expression engine";
          type empty;
        }
      }
      leaf scan-time {
        tailf:cli-full-command;
        tailf:info
          "Configure background scanner interval";
        type uint8 {
          range "5..60";
          tailf:info
            "<5-60>;;Scanner interval (seconds)";
        }
      }
      leaf soft-reconfig-backup {
        tailf:info
          "Use soft-reconfiguration inbound only when route-refresh is not negotiated";
        tailf:cli-full-command;
        type empty;
      }
      leaf suppress-inactive {
        tailf:info
          "Suppress routes that are not in the routing table";
        tailf:cli-full-command;
        type empty;
      }
      leaf update-delay {
        tailf:cli-full-command;
        tailf:info
          "Set the max initial delay for sending update";
        type uint16 {
          range "1..3600";
          tailf:info
            "<1-3600>;;Delay value (seconds)";
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      container bgp {
        tailf:info
          "BGP distance";
        tailf:cli-compact-syntax;
        tailf:cli-sequence-commands;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "distance srcip wildbits";
        leaf distance {
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf access-list {
          tailf:cli-drop-node-name;
          type std-ip-acl-type;
        }
      }
    }
    uses ncs_rpc_notif_router-distribute-list-grouping;
    container maximum-paths {
      tailf:info
        "Forward packets over multiple paths";
      uses ncs_rpc_notif_router-bgp-max-path-grouping;
      container eibgp {
        tailf:info
          "Both eBGP and iBGP paths as multipath";
        uses ncs_rpc_notif_router-bgp-max-path-grouping;
      }
      container ibgp {
        tailf:info
          "iBGP-multipath";
        choice ibgp-choice {
          default "b";
          case a {
            container unequal-cost {
              tailf:info
                "Perform Un-Equal cost multipath selection";
              uses ncs_rpc_notif_router-bgp-max-path-grouping;
            }
          }
          case b {
            uses ncs_rpc_notif_router-bgp-max-path-grouping;
          }
        }
      }
      leaf import {
        tailf:info
          "Maximum import paths";
        type uint16 {
          tailf:info
            "<1-16>;;Number of import paths";
          range "1..16";
        }
      }
    }
    container import {
      tailf:info
        "Configure path import";
      container path {
        tailf:info
          "Path selection and path limit";
        container selection {
          tailf:info
            "Path selection policy";
          choice selection-choice {
            leaf all {
              tailf:info
                "Import all available paths";
              type empty;
            }
            container bestpath {
              tailf:info
                "Import the best available path.";
              tailf:cli-delete-when-empty;
              presence "true";
              leaf strict {
                tailf:info
                  "Do not fallback to best available path";
                type empty;
              }
            }
            container multipaths {
              tailf:info
                "Import all multipaths.";
              tailf:cli-delete-when-empty;
              presence "true";
              leaf strict {
                tailf:info
                  "Do not fallback to best available path";
                type empty;
              }
            }
          }
        }
        leaf limit {
          tailf:info
            "Per net imported path limit";
          type uint8 {
            tailf:info
              "<2-255>;;Maximum number of paths that can be imported into a net";
            range "2..255";
          }
        }
      }
    }
    container redistribute {
      tailf:info
        "Redistribute information from another routing protocol";
      container bgp {
        tailf:info
          "Border Gateway Protocol (BGP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses ncs_rpc_notif_router-bgp-redistribute-grouping;
      }
      container connected {
        tailf:info
          "Connected";
        tailf:cli-compact-syntax;
        tailf:cli-delete-when-empty;
        presence "Connected";
        uses ncs_rpc_notif_router-bgp-redistribute-grouping;
      }
      container static {
        tailf:info
          "Static routes";
        tailf:cli-compact-syntax;
        tailf:cli-delete-when-empty;
        presence "true";
        uses ncs_rpc_notif_router-bgp-redistribute-grouping;
      }
      container dvmrp {
        tailf:info
          "Redistribution of DVMRP into BGP IPv4 Multicast";
        tailf:cli-compact-syntax;
        tailf:cli-sequence-commands {
          tailf:cli-reset-siblings;
        }
        tailf:cli-delete-when-empty;
        presence "true";
        uses ncs_rpc_notif_route-map-metric-grouping;
      }
      list eigrp {
        tailf:info
          "Enhanced Interior Gateway Routing Protocol (EIGRP)";
        tailf:cli-suppress-mode;
        tailf:cli-delete-when-empty;
        tailf:cli-compact-syntax;
        key "as-number";
        leaf as-number {
          type uint32 {
            tailf:info
              "<1-65535>;;Autonomous system number";
            range "1..65535";
          }
        }
        uses ncs_rpc_notif_router-bgp-redistribute-grouping;
      }
      container isis {
        tailf:info
          "ISO IS-IS";
        tailf:cli-compact-syntax;
        presence "true";
        uses ncs_rpc_notif_redistribute-isis-grouping;
        list isis-list {
          tailf:cli-drop-node-name;
          tailf:cli-compact-syntax;
          tailf:cli-suppress-mode;
          tailf:cli-delete-when-empty;
          key "name";
          leaf name {
            type string {
              tailf:info
                "WORD;;ISO routing area tag";
              pattern '^([^mlir].*)|(i[^p].*)|(ip..*)|(l[^e].*)|(le[^v].*)|(lev[^e].*)|(leve[^l].*)|(level[^\-].*)|(m[^e].*)|(me[^t].*)|(met[^r].*)|(metr[^i].*)|(metri[^c].*)|(metric..*)*(r[^o].*)|(ro[^u].*)|(rou[^t].*)|(rout[^e].*)|(route[^\-].*)|(route-[^m].*)|(route-m[^a].*)|(route-ma[^p].*)|(route-map..*)$';
            }
          }
          uses ncs_rpc_notif_redistribute-isis-grouping;
        }
      }
      container iso-igrp {
        tailf:info
          "IGRP for OSI networks";
        tailf:cli-compact-syntax;
        uses ncs_rpc_notif_route-map-metric-grouping;
        list iso-igrp-area {
          tailf:cli-drop-node-name;
          tailf:cli-suppress-mode;
          tailf:cli-delete-when-empty;
          tailf:cli-compact-syntax;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses ncs_rpc_notif_route-map-metric-grouping;
        }
      }
      container mobile {
        presence "Mobile routes";
        tailf:info
          "Mobile routes";
        tailf:cli-compact-syntax;
        uses ncs_rpc_notif_router-bgp-redistribute-grouping;
      }
      container odr {
        presence "On Demand stub Routes";
        tailf:info
          "On Demand stub Routes";
        tailf:cli-compact-syntax;
        uses ncs_rpc_notif_router-bgp-redistribute-grouping;
      }
      list ospf {
        tailf:info
          "Open Shortest Path First (OSPF)";
        tailf:cli-suppress-mode;
        tailf:cli-delete-when-empty;
        tailf:cli-compact-syntax;
        key "id";
        leaf id {
          type uint16 {
            tailf:info
              "<1-65535>;;Process ID";
            range "1..65535";
          }
        }
        list vrf {
          tailf:info
            "VPN Routing/Forwarding Instance";
          tailf:cli-suppress-mode;
          tailf:cli-delete-when-empty;
          tailf:cli-compact-syntax;
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding Instance (VRF) name";
            }
          }
          container match {
            tailf:info
              "Redistribution of OSPF routes";
            tailf:cli-flatten-container;
            tailf:cli-compact-syntax;
            uses ncs_rpc_notif_redistribute-ospf-match-grouping;
            uses ncs_rpc_notif_router-bgp-redistribute-grouping;
          }
        }
        container non-vrf {
          tailf:cli-drop-node-name;
          tailf:cli-flatten-container;
          tailf:cli-compact-syntax;
          container match {
            tailf:info
              "Redistribution of OSPF routes";
            tailf:cli-flatten-container;
            tailf:cli-compact-syntax;
            uses ncs_rpc_notif_redistribute-ospf-match-grouping;
            uses ncs_rpc_notif_router-bgp-redistribute-grouping;
          }
        }
      }
      container rip {
        tailf:info
          "Routing Information Protocol (RIP)";
        tailf:cli-compact-syntax;
        presence "true";
        uses ncs_rpc_notif_router-bgp-redistribute-grouping;
      }
    }
    container neighbor-tag {
      tailf:cli-drop-node-name;
      list neighbor {
        tailf:info
          "Specify a neighbor router";
        tailf:cli-suppress-mode;
        tailf:cli-delete-when-empty;
        tailf:cli-incomplete-command;
        ordered-by user;
        key "id";
        leaf id {
          type string {
            tailf:info
              "WORD;;Neighbor tag";
          }
        }
        uses ncs_rpc_notif_router-bgp-neighbor-grouping;
      }
    }
    list neighbor {
      tailf:info
        "Specify a neighbor router";
      tailf:cli-suppress-mode;
      tailf:cli-delete-when-empty;
      tailf:cli-incomplete-command;
      key "id";
      leaf id {
        type union {
          type inet:ipv4-address {
            tailf:info
              "A.B.C.D;;Neighbor address";
          }
          type inet:ipv6-address {
            tailf:info
              "X:X:X:X::X;;Neighbor IPv6 address";
          }
        }
      }
      uses ncs_rpc_notif_router-bgp-neighbor-grouping;
    }
    list network {
      tailf:info
        "Specify a network to announce via BGP";
      tailf:cli-suppress-mode;
      tailf:cli-delete-when-empty;
      tailf:cli-compact-syntax;
      tailf:cli-reset-container;
      key "number";
      leaf number {
        type inet:ipv4-address {
          tailf:info
            "A.B.C.D;;Network number";
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    leaf synchronization {
      tailf:info
        "Perform IGP synchronization";
      tailf:cli-full-command;
      type empty;
    }
    leaf auto-summary {
      tailf:info
        "Enable automatic network number summarization";
      tailf:cli-boolean-no;
      tailf:cli-full-command;
      type boolean;
    }
    leaf table-map {
      tailf:info
        "Map external entry attributes into routing table";
      tailf:cli-full-command;
      type string {
        tailf:info
          "WORD;;route-map name";
      }
    }
  }

  grouping ncs_rpc_notif_router-ospf-af-grouping;

  grouping ncs_rpc_notif_router-ospfv3-af-grouping {
    container discard-route {
      tailf:info
        "Enable or disable discard-route installation";
      leaf external {
        tailf:info
          "Discard route for summarised redistributed routes";
        tailf:cli-boolean-no;
        tailf:cli-full-command;
        type boolean;
        default "true";
      }
      leaf internal {
        tailf:info
          "Discard route for summarised inter-area routes";
        tailf:cli-boolean-no;
        tailf:cli-full-command;
        type boolean;
        default "true";
      }
    }
  }

  grouping ncs_rpc_notif_router-ospf-common-af-grouping {
    container default-information {
      tailf:info
        "Control distribution of default information";
      container originate {
        tailf:info
          "Distribute a default route";
        tailf:cli-compact-syntax;
        tailf:cli-delete-when-empty;
        presence "true";
        leaf always {
          tailf:info
            "Always advertise default route";
          type empty;
        }
        leaf metric {
          tailf:info
            "OSPF default metric";
          type uint32 {
            tailf:info
              "<0-16777214>;;OSPF metric";
            range "0..16777214";
          }
        }
        leaf metric-type {
          tailf:info
            "OSPF metric type for default routes";
          type ospf-metric-type;
          default "2";
        }
        leaf route-map {
          tailf:info
            "Route map reference";
          type string {
            tailf:info
              "WORD;;Route map name";
          }
        }
      }
    }
    leaf default-metric {
      tailf:info
        "Set metric of redistributed routes";
      tailf:cli-full-command;
      type uint32 {
        tailf:info
          "<1-16777214>;;OSPF default metric";
        range "1..16777214";
      }
    }
    container distance {
      tailf:info
        "Define an administrative distance";
      leaf weight {
        tailf:cli-drop-node-name;
        type uint8 {
          tailf:info
            "<1-255>;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container ospf {
        tailf:info
          "OSPF routes Administrative distance";
        tailf:cli-compact-syntax;
        leaf intra-area {
          tailf:info
            "Intra-area routes";
          type uint32 {
            tailf:info
              "<1-255>;;Distance for intra-area routes";
            range "1..255";
          }
        }
        leaf inter-area {
          tailf:info
            "Inter-area routes";
          type uint32 {
            tailf:info
              "<1-255>;;Distance for inter-area routes";
            range "1..255";
          }
        }
        leaf external {
          tailf:info
            "External routes";
          type uint32 {
            tailf:info
              "<1-255>;;Distance for external routes";
            range "1..255";
          }
        }
      }
    }
    leaf maximum-paths {
      tailf:info
        "Forward packets over multiple paths";
      tailf:cli-full-command;
      type uint32 {
        range "1..32";
        tailf:info
          "<1-32>;;Number of paths";
      }
    }
    container redistribute {
      tailf:info
        "Redistribute information from another routing protocol";
      container bgp {
        tailf:info
          "Border Gateway Protocol (BGP)";
        tailf:cli-compact-syntax;
        leaf as-number {
          tailf:cli-drop-node-name;
          type uint32 {
            tailf:info
              "<1-65535>;;Autonomous system number";
            range "1..65535";
          }
        }
        uses ncs_rpc_notif_router-ospf-redistribute-grouping;
      }
      container connected {
        tailf:info
          "Connected";
        tailf:cli-compact-syntax;
        tailf:cli-delete-when-empty;
        presence "Connected";
        uses ncs_rpc_notif_router-ospf-redistribute-grouping;
      }
      list eigrp {
        tailf:info
          "Enhanced Interior Gateway Routing Protocol (EIGRP)";
        tailf:cli-suppress-mode;
        tailf:cli-delete-when-empty;
        tailf:cli-compact-syntax;
        key "as-number";
        leaf as-number {
          type uint32 {
            tailf:info
              "<1-65535>;;Autonomous system number";
            range "1..65535";
          }
        }
        uses ncs_rpc_notif_router-ospf-redistribute-grouping;
      }
      container isis {
        tailf:info
          "ISO IS-IS";
        tailf:cli-compact-syntax;
        presence "true";
        list isis-area {
          tailf:cli-drop-node-name;
          tailf:cli-suppress-mode;
          tailf:cli-delete-when-empty;
          tailf:cli-compact-syntax;
          key "name";
          leaf name {
            tailf:cli-disallow-value "level-1|level-2|level-1-2|metric|metric-type|route-map|subnets|tag";
            type string {
              tailf:info
                "WORD;;ISO routing area tag";
            }
          }
          uses ncs_rpc_notif_router-ospf-redistribute-grouping;
        }
        uses ncs_rpc_notif_router-ospf-redistribute-grouping;
      }
      container iso-igrp {
        tailf:info
          "IGRP for OSI networks";
        tailf:cli-compact-syntax;
        tailf:cli-sequence-commands;
        presence "true";
        leaf area-tag {
          tailf:cli-drop-node-name;
          tailf:cli-disallow-value "route-map";
          tailf:cli-optional-in-sequence;
          type string {
            tailf:info
              "WORD;;ISO routing area tag";
          }
        }
        leaf route-map {
          tailf:info
            "Route map reference";
          type string {
            tailf:info
              "WORD;;Pointer to route-map entries";
          }
        }
        uses ncs_rpc_notif_ospf-iso-igrp-redistribute-grouping;
      }
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        container threshold-warning-only-container {
          tailf:cli-drop-node-name;
          tailf:cli-flatten-container;
          tailf:cli-compact-syntax;
          leaf threshold {
            tailf:cli-drop-node-name;
            type uint32 {
              tailf:info
                "<1-100>;;Threshold value (%) at which to generate a warning message";
              range "1..100";
            }
          }
          leaf warning-only {
            tailf:info
              "Only give warning message when limit is exceeded";
            tailf:cli-full-command;
            type empty;
          }
        }
      }
      container mobile {
        tailf:info
          "Mobile routes";
        tailf:cli-compact-syntax;
        presence "true";
        uses ncs_rpc_notif_router-ospf-redistribute-grouping;
      }
      container odr {
        tailf:info
          "On Demand stub Routes";
        tailf:cli-compact-syntax;
        presence "true";
        uses ncs_rpc_notif_router-ospf-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint32 {
            tailf:info
              "<1-65535>;;Process ID";
            range "1..65535";
          }
        }
        uses ncs_rpc_notif_router-ospf-redistribute-grouping;
        container match {
          tailf:info
            "Redistribution of OSPF routes";
          tailf:cli-flatten-container;
          tailf:cli-compact-syntax;
          uses ncs_rpc_notif_redistribute-ospf-match-grouping;
          uses ncs_rpc_notif_ospf-redistribute-match-grouping;
        }
      }
      container rip {
        tailf:info
          "Routing Information Protocol (RIP)";
        tailf:cli-compact-syntax;
        presence "true";
        uses ncs_rpc_notif_router-ospf-redistribute-grouping;
        list redistribute-list-rip {
          tailf:cli-drop-node-name;
          tailf:cli-suppress-mode;
          tailf:cli-delete-when-empty;
          tailf:cli-compact-syntax;
          key "name";
          leaf name {
            type string {
              tailf:info
                "WORD;;User selected string identifying this process";
            }
          }
          uses ncs_rpc_notif_router-ospf-redistribute-grouping;
        }
      }
      container static {
        tailf:info
          "Static routes";
        tailf:cli-compact-syntax;
        tailf:cli-delete-when-empty;
        presence "Static routes";
        uses ncs_rpc_notif_router-ospf-redistribute-grouping;
      }
    }
  }

  grouping ncs_rpc_notif_router-ospf-common-grouping {
    list area {
      tailf:cli-break-sequence-commands;
      tailf:info
        "OSPF area parameters";
      tailf:cli-suppress-mode;
      tailf:cli-delete-when-empty;
      tailf:cli-incomplete-command;
      key "id";
      leaf id {
        tailf:cli-suppress-range;
        type ospf-area-type;
      }
      container authentication {
        tailf:info
          "Enable authentication";
        presence "true";
        leaf message-digest {
          tailf:info
            "Use message-digest authentication";
          type empty;
        }
      }
      container nssa {
        tailf:info
          "Specify a NSSA area";
        tailf:cli-compact-syntax;
        tailf:cli-delete-when-empty;
        presence "true";
        leaf no-redistribution {
          tailf:info
            "No redistribution into this NSSA area";
          type empty;
        }
        leaf default-information-originate {
          tailf:info
            "Originate Type 7 default into NSSA area";
          type empty;
        }
        leaf metric {
          tailf:info
            "OSPF default metric";
          when '../default-information-originate' {
            tailf:xpath-root 3;
          }
          type int32 {
            tailf:info
              "<0-16777214>;;OSPF metric";
            range "0..16777214";
          }
        }
        leaf metric-type {
          tailf:info
            "OSPF metric type for default routes";
          when '../default-information-originate' {
            tailf:xpath-root 3;
          }
          type ospf-metric-type;
          default "2";
        }
        leaf nssa-only {
          tailf:info
            "Limit default advertisement to this NSSA area";
          type empty;
        }
        leaf no-ext-capability {
          tailf:info
            "Do not send domain specific capabilities into NSSA";
          type empty;
        }
        leaf no-summary {
          tailf:info
            "Do not send summary LSA into NSSA";
          type empty;
        }
        container translate {
          tailf:info
            "Translate LSA";
          container type7 {
            tailf:info
              "From Type 7 to Type 5";
            tailf:cli-compact-syntax;
            leaf always {
              tailf:info
                "Always translate LSAs on this ABR";
              type empty;
            }
            leaf suppress-fa {
              tailf:info
                "Suppress forwarding address in translated LSAs";
              type empty;
            }
          }
        }
      }
      leaf default-cost {
        tailf:info
          "Set the summary default-cost of a NSSA/stub area";
        tailf:cli-full-command;
        tailf:cli-no-value-on-delete;
        type uint32 {
          tailf:info
            "<0-16777215;;Stub's advertised external route metric";
          range "0..16777215";
        }
      }
      list filter-list {
        tailf:info
          "Filter networks between OSPF areas";
        tailf:cli-suppress-mode;
        tailf:cli-delete-when-empty;
        tailf:cli-compact-syntax;
        key "direction";
        leaf prefix {
          tailf:cli-prefix-key;
          mandatory true;
          tailf:info
            "Filter prefixes between OSPF areas";
          type string {
            tailf:info
              "WORD;;Name of an IP prefix-list";
          }
        }
        leaf direction {
          type enumeration {
            enum "in" {
              tailf:info
                "Filter networks sent to this area";
            }
            enum "out" {
              tailf:info
                "Filter networks sent from this area";
            }
          }
        }
      }
      list range {
        tailf:info
          "Summarize routes matching address/mask (border routers only)";
        tailf:cli-compact-syntax;
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        choice advertise-choice {
          leaf advertise {
            tailf:info
              "Advertise this range (default)";
            type empty;
          }
          leaf not-advertise {
            tailf:info
              "DoNotAdvertise this range";
            type empty;
          }
        }
        leaf cost {
          tailf:info
            "User specified metric for this range";
          type uint32 {
            tailf:info
              "<0-16777215>;;Advertised metric for this range";
            range "0..16777215";
          }
        }
      }
      container range-ipv6 {
        tailf:cli-drop-node-name;
        list range {
          tailf:info
            "Summarize routes matching address/mask(border routers only)";
          tailf:cli-compact-syntax;
          tailf:cli-suppress-mode;
          tailf:cli-delete-when-empty;
          key "prefix";
          leaf prefix {
            type inet:ipv6-prefix {
              tailf:info
                "X:X:X:X::X/<0-128>;;IPv6 prefix to match";
            }
          }
          choice advertise-choice {
            leaf advertise {
              tailf:info
                "Advertise this range (default)";
              type empty;
            }
            leaf not-advertise {
              tailf:info
                "DoNotAdvertise this range";
              type empty;
            }
          }
          leaf cost {
            tailf:info
              "User specified metric for this range";
            type uint32 {
              tailf:info
                "<0-16777215>;;Advertised metric for this range";
              range "0..16777215";
            }
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            tailf:info
              "<1-65535>;;Cost of the sham-link";
            range "0..65535";
          }
        }
      }
      container stub {
        tailf:info
          "Specify a stub area";
        tailf:cli-compact-syntax;
        tailf:cli-delete-when-empty;
        presence "true";
        leaf no-summary {
          tailf:info
            "Do not send summary LSA into stub area";
          type empty;
        }
        leaf no-ext-capability {
          tailf:info
            "Do not send domain specific capabilities into stub area";
          type empty;
        }
      }
      list virtual-link {
        tailf:info
          "Define a virtual link and its parameters";
        tailf:cli-suppress-mode;
        tailf:cli-delete-when-empty;
        tailf:cli-compact-syntax;
        key "id";
        leaf id {
          type inet:ipv4-address {
            tailf:info
              "A.B.C.D;;ID (IP addr) associated with virtual link neighbor";
          }
        }
        leaf retransmit-interval {
          tailf:info
            "LSA retransmit interval";
          type uint16 {
            tailf:info
              "<1-8192>;;Seconds";
            range "1..8192";
          }
        }
        leaf transmit-delay {
          tailf:info
            "LSA transmission delay";
          type uint16 {
            tailf:info
              "<1-8192>;;Seconds";
            range "1..8192";
          }
          default "1";
        }
        leaf hello-interval {
          tailf:info
            "Hello packet interval";
          type int32 {
            range "1..8192";
            tailf:info
              "<1-8192;;Seconds>";
          }
        }
        leaf dead-interval {
          tailf:info
            "Dead router detection time";
          type uint16 {
            range "1..8192";
            tailf:info
              "<1-8192;;Seconds>";
          }
        }
        leaf authentication {
          tailf:info
            "Set authentication type";
          type empty;
        }
        container authentication-key {
          tailf:info
            "Set authentication key";
          tailf:cli-flatten-container;
          tailf:cli-compact-syntax;
          tailf:cli-sequence-commands {
            tailf:cli-reset-siblings;
          }
          leaf auth-type {
            tailf:cli-drop-node-name;
            tailf:cli-optional-in-sequence;
            tailf:cli-incomplete-command;
            type uint8 {
              tailf:info
                "<0-7>;;Encryption type (0 for not yet encrypted, 7 for proprietary)";
              range "0..7";
            }
            default "0";
          }
          leaf auth-key {
            tailf:cli-drop-node-name;
            tailf:cli-full-command;
            type string {
              tailf:info
                "WORD;;Authentication key (8 chars)";
              length "1..8";
            }
          }
        }
        list message-digest-key {
          tailf:info
            "Set message digest key";
          tailf:cli-suppress-mode;
          tailf:cli-delete-when-empty;
          tailf:cli-compact-syntax;
          tailf:cli-incomplete-command;
          key "id";
          leaf id {
            tailf:cli-suppress-range;
            type uint8 {
              tailf:info
                "<1-255>;;Key ID";
              range "1..255";
            }
          }
          container md5 {
            tailf:info
              "Use MD5 algorithm";
            tailf:cli-compact-syntax;
            tailf:cli-sequence-commands {
              tailf:cli-reset-siblings;
            }
            leaf auth-type {
              tailf:cli-drop-node-name;
              tailf:cli-optional-in-sequence;
              tailf:cli-incomplete-command;
              type uint8 {
                tailf:info
                  "<0-7>;;Encryption type (0 for not yet encrypted, 7 for proprietary)";
                range "0..7";
              }
              default "0";
            }
            leaf auth-key {
              tailf:cli-drop-node-name;
              tailf:cli-full-command;
              type string {
                tailf:info
                  "WORD;;Authentication key (16 chars)";
                length "1..16";
              }
            }
          }
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1..4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      tailf:cli-show-no;
      presence "true";
      leaf detail {
        tailf:info
          "Log all state changes";
        type empty;
      }
    }
    container max-lsa {
      tailf:info
        "maximum number of LSAs OSPF process will receive";
      tailf:cli-compact-syntax;
      tailf:cli-sequence-commands {
        tailf:cli-reset-all-siblings;
      }
      leaf maximum-number {
        tailf:cli-drop-node-name;
        type uint32 {
          tailf:info
            "<1-4294967294>;;Maximum number of non self-generated LSAs this process can receive";
          range "1..4294967294";
        }
      }
      leaf threshold-percentage {
        tailf:cli-break-sequence-commands;
        tailf:cli-drop-node-name;
        type uint8 {
          tailf:info
            "<1-100>;;Threshold value (%) at which to generate a warning msg";
          range "1..100";
        }
      }
      leaf warning-only {
        tailf:info
          "Only give warning message when limit is exceeded";
        tailf:cli-full-command;
        type empty;
      }
      leaf ignore-time {
        tailf:info
          "time during which all adjacencies are suppressed";
        type uint32 {
          tailf:info
            "<1-17895>;;number of minutes during which all adjacencies are suppressed";
          range "1..17895";
        }
      }
      leaf reset-time {
        tailf:info
          "time after which ignore-count is reset to zero";
        type uint32 {
          tailf:info
            "<2-35791>;;number of minutes after which ignore-count is reset to zero";
          range "2..35791";
        }
        default "60";
      }
      leaf ignore-count {
        tailf:info
          "maximum number of times adjacencies can be suppressed";
        type uint32 {
          range "1..65534";
          tailf:info
            "<1-65534>;;count on how many times adjacencies can be suppressed";
        }
      }
    }
    uses ncs_rpc_notif_passive-interface-grouping;
    container queue-depth {
      tailf:info
        "OSPF Hello/Router process queue depth";
      leaf hello {
        tailf:info
          "OSPF Hello process queue depth";
        type union {
          type uint32 {
            tailf:info
              "<1-2147483647>;;maximum numer of packets in the queue";
            range "1..2147483647";
          }
          type enumeration {
            enum "unlimited" {
              tailf:info
                "Unlimited queue depth";
            }
          }
        }
        default "unlimited";
      }
      leaf update {
        tailf:info
          "OSPF Router process queue depth";
        type union {
          type uint32 {
            tailf:info
              "<1-2147483647>;;maximum numer of packets in the queue";
            range "1..2147483647";
          }
          type enumeration {
            enum "unlimited" {
              tailf:info
                "Unlimited queue depth";
            }
          }
        }
      }
    }
    container timers {
      tailf:info
        "Adjust routing timers";
      container lsa {
        tailf:info
          "OSPF LSA timers";
        leaf arrival {
          tailf:info
            "OSPF LSA arrival timer";
          type uint32 {
            range "0..600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            range "5..100";
            tailf:info
              "<5-100>;;The minimum interval in msec to pace limit flooding on interface";
          }
        }
        leaf lsa-group {
          tailf:info
            "OSPF LSA group pacing timer";
          tailf:cli-full-command;
          type uint32 {
            range "10..1800";
            tailf:info
              "<10-1800>;;Interval in sec between group of LSA being refreshed or maxaged";
          }
        }
        leaf retransmission {
          tailf:info
            "OSPF retransmission pacing timer";
          tailf:cli-full-command;
          type uint32 {
            range "5..200";
            tailf:info
              "<5-200>;;The minimum interval in msec between neighbor retransmissions";
          }
        }
      }
      container throttle {
        tailf:info
          "OSPF throttle timers";
        container lsa {
          tailf:info
            "OSPF LSA throttle timers";
          tailf:cli-compact-syntax;
          tailf:cli-sequence-commands;
          leaf all {
            tailf:info
              "For all type of OSPF LSAs";
            tailf:cli-optional-in-sequence;
            tailf:cli-incomplete-command;
            type empty;
          }
          leaf start-interval {
            tailf:cli-drop-node-name;
            tailf:cli-incomplete-command;
            type uint32 {
              tailf:info
                "<0-600000>;;Delay to generate first occurrence of LSA in milliseconds";
              range "0..600000";
            }
          }
          leaf hold-interval {
            tailf:cli-drop-node-name;
            tailf:cli-incomplete-command;
            type uint32 {
              tailf:info
                "<0-600000>;;Minimum delay between originating the same LSA in milliseconds";
              range "0..600000";
            }
          }
          leaf max-interval {
            tailf:cli-drop-node-name;
            type uint32 {
              tailf:info
                "<0-600000>;;Maximum delay between originating the same LSA in milliseconds";
              range "0..600000";
            }
          }
        }
        container spf {
          tailf:info
            "OSPF SPF throttle timers";
          tailf:cli-sequence-commands;
          tailf:cli-compact-syntax;
          leaf spf-start {
            tailf:cli-drop-node-name;
            tailf:cli-incomplete-command;
            type uint32 {
              tailf:info
                "<0-600000>;;Delay between receiving a change to SPF calculation in milliseconds";
              range "0..600000";
            }
          }
          leaf spf-hold {
            tailf:cli-drop-node-name;
            tailf:cli-incomplete-command;
            type uint32 {
              tailf:info
                "<0-600000>;;Delay between first and second SPF calculation in milliseconds";
              range "0..600000";
            }
          }
          leaf spf-max-wait {
            tailf:cli-drop-node-name;
            type uint32 {
              tailf:info
                "<0-600000>;;Maximum wait time in milliseconds for SPF calculations";
              range "0..600000";
            }
          }
        }
      }
    }
    leaf router-id {
      tailf:cli-full-command;
      tailf:info
        "Override configured router identifier (peers will reset)";
      type inet:ipv4-address {
        tailf:info
          "A.B.C.D;;Manually configured router identifier";
      }
    }
  }

  grouping ncs_rpc_notif_router-ospf-grouping {
    container capability {
      tailf:info
        "Enable specific OSPF feature";
      leaf opaque {
        tailf:info
          "Opaque LSA";
        tailf:cli-boolean-no;
        tailf:cli-full-command;
        type boolean;
        default "true";
      }
      leaf lls {
        tailf:info
          "Link-local Signaling (LLS) support";
        tailf:cli-boolean-no;
        tailf:cli-full-command;
        type boolean;
        default "true";
      }
      leaf transit {
        tailf:info
          "Transit Area";
        tailf:cli-boolean-no;
        tailf:cli-full-command;
        type boolean;
        default "true";
      }
    }
    container compatible {
      tailf:info
        "OSPF compatibility list";
      leaf rfc1583 {
        tailf:info
          "compatible with RFC 1583";
        tailf:cli-boolean-no;
        type boolean;
        default "true";
      }
    }
    uses ncs_rpc_notif_router-distribute-list-grouping;
    container domain-id {
      tailf:info
        "OSPF domain-id";
      choice domain-id-choice {
        case a {
          leaf ip-format {
            tailf:cli-drop-node-name;
            type inet:ipv4-address {
              tailf:info
                "A.B.C.D;;OSPF domain ID in IP address format";
            }
          }
          container ip-format-secondary {
            tailf:cli-drop-node-name;
            tailf:cli-compact-syntax;
            tailf:cli-sequence-commands;
            leaf ip {
              tailf:cli-drop-node-name;
              type inet:ipv4-address {
                tailf:info
                  "A.B.C.D;;OSPF domain ID in IP address format";
              }
            }
            leaf secondary {
              tailf:info
                "Secondary Domain-ID";
              type empty;
            }
          }
        }
        leaf Null {
          tailf:info
            "Null Domain-ID";
          tailf:cli-full-command;
          type empty;
        }
        container type {
          tailf:info
            "OSPF domain ID type in Hex format";
          tailf:cli-sequence-commands;
          tailf:cli-compact-syntax;
          leaf type-leaf {
            tailf:cli-drop-node-name;
            tailf:cli-incomplete-command;
            type enumeration {
              enum "0005" {
                tailf:info
                  "Type 0x0005";
              }
              enum "0105" {
                tailf:info
                  "Type 0x0105";
              }
              enum "0205" {
                tailf:info
                  "Type 0x0205";
              }
              enum "8005" {
                tailf:info
                  "Type 0x8005";
              }
            }
          }
          leaf value {
            tailf:info
              "OSPF domain ID value in Hex format";
            type string {
              tailf:info
                "Hex-data;;OSPF domain ID ext. community value in Hex";
              pattern '[0-9a-fA-F]{12}';
            }
          }
        }
      }
    }
    leaf domain-tag {
      tailf:info
        "OSPF domain-tag";
      tailf:cli-full-command;
      type uint32 {
        range "1..4294967295";
        tailf:info
          "<1-4294967295>;;OSPF domain tag - 32-bit value";
      }
    }
    container ignore {
      tailf:info
        "Do not complain about specific event";
      container lsa {
        tailf:info
          "Do not complain upon receiving LSA of the specified type";
        leaf mospf {
          tailf:info
            "MOSPF Type 6 LSA";
          type empty;
        }
      }
    }
    leaf ispf {
      tailf:info
        "Enable incremental SPF computation";
      tailf:cli-full-command;
      type empty;
    }
    container limit {
      tailf:info
        "Limit a specific OSPF feature";
      container retransmissions {
        tailf:info
          "LS update, DBD, and LS request retransmissions";
        tailf:cli-compact-syntax;
        leaf dc {
          tailf:info
            "Demand circuit retransmissions";
          type limit-dc-non-dc-type;
        }
        leaf non-dc {
          tailf:info
            "Non-demand-circuit retransmissions";
          type limit-dc-non-dc-type;
        }
      }
    }
    container local-rib-criteria {
      tailf:info
        "Enable or disable usage of local RIB as route criteria";
      tailf:cli-compact-syntax;
      leaf forwarding-address {
        tailf:info
          "Local RIB used to validate external/NSSA forwarding addresses";
        type empty;
      }
      leaf inter-area-summary {
        tailf:info
          "Local RIB used as criteria for inter-area summaries";
        type empty;
      }
      leaf nssa-translation {
        tailf:info
          "Local RIB used as criteria for NSSA translation";
        type empty;
      }
    }
    container max-metric {
      tailf:info
        "Set maximum metric";
      container router-lsa {
        tailf:info
          "Maximum metric in self-originated router-LSAs";
        tailf:cli-compact-syntax;
        presence "true";
        leaf include-stub {
          tailf:info
            "Set maximum metric for stub links in router-LSAs";
          type empty;
        }
        leaf summary-lsa {
          tailf:info
            "Override summary-lsa metric with max-metric value";
          type empty;
        }
        leaf summary-lsa-max-metric-value {
          when '../summary-lsa' {
            tailf:xpath-root 3;
          }
          tailf:cli-drop-node-name;
          type uint32 {
            tailf:info
              " <1-16777215>;;Overriding metric in summary-LSAs (default 16711680)";
            range "1..16777215";
          }
        }
        leaf external-lsa {
          tailf:info
            "Override external-lsa metric with max-metric value";
          type empty;
        }
        leaf external-lsa-max-metric-value {
          when '../external-lsa' {
            tailf:xpath-root 3;
          }
          tailf:cli-drop-node-name;
          type uint32 {
            tailf:info
              "<1-16777215>;;Overriding metric in external-LSAs (default 16711680)";
            range "1..16777215";
          }
        }
        container on-startup {
          tailf:info
            "Set maximum metric temporarily after reboot";
          tailf:cli-flatten-container;
          tailf:cli-compact-syntax;
          choice time-wait-for-bgp-choice {
            leaf seconds {
              tailf:cli-drop-node-name;
              type uint32 {
                tailf:info
                  "<5-86400>;;Time, in seconds, router-LSAs are originated with max-metric";
                range "5..86400";
              }
            }
            leaf wait-for-bgp {
              tailf:info
                "Let BGP decide when to originate router-LSA with normal metric";
              type empty;
            }
          }
        }
      }
    }
    container mpls {
      tailf:info
        "Configure MPLS routing protocol parameters";
      container ldp {
        tailf:info
          "routing protocol commands for MPLS LDP";
        container autoconfig {
          tailf:info
            "Configure LDP automatic configuration";
          presence "Configure LDP automatic configuration";
          leaf area {
            tailf:info
              "Configure an OSPF area to run MPLS LDP";
            type ospf-area-type;
          }
        }
        container sync {
          tailf:info
            "Configure LDP-IGP Synchronization";
          presence "Configure LDP-IGP Synchronization";
        }
      }
      container traffic-eng {
        tailf:info
          "routing protocol commands for MPLS Traffic Engineering";
        tailf:cli-compact-syntax;
        leaf multicast-intact {
          tailf:info
            "MPLS TE and PIM interaction";
          tailf:cli-full-command;
          type empty;
        }
        leaf area {
          tailf:info
            "configure an ospf area to run MPLS Traffic Engineering";
          tailf:cli-full-command;
          type ospf-area-type;
        }
        container interface {
          tailf:info
            "MPLS TE interface configuration for this OSPF process";
          tailf:cli-sequence-commands;
          leaf name {
            tailf:cli-drop-node-name;
            tailf:cli-incomplete-command;
            type string {
              tailf:info
                "WORD;;Interface name";
            }
          }
          leaf area {
            tailf:info
              "advertise MPLS TE information for this interface into area";
            type uint32 {
              tailf:info
                "<0-0>;;OSPF area ID as a decimal value";
            }
          }
        }
        container mesh-group-container {
          tailf:cli-drop-node-name;
          tailf:cli-sequence-commands;
          leaf mesh-group {
            tailf:info
              "Traffic Engineering Mesh-Group advertisement";
            tailf:cli-incomplete-command;
            type uint32 {
              range "0..4294967295";
              tailf:info
                "<0-4294967295>;;Mesh Group Id";
            }
          }
          leaf interface {
            tailf:info
              "Interface";
            tailf:cli-incomplete-command;
            type string {
              tailf:info
                "WORD;;Interface name";
            }
          }
          list area {
            tailf:info
              "configure flooding scope as area";
            tailf:cli-suppress-mode;
            tailf:cli-delete-when-empty;
            key "id";
            leaf id {
              tailf:cli-suppress-range;
              type ospf-area-type;
            }
          }
        }
        container router-id {
          tailf:info
            "Traffic Engineering stable IP address for system";
          leaf interface {
            tailf:info
              "Interface";
            type string {
              tailf:info
                "WORD;;Interface name";
            }
          }
        }
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
      container cost-database-filter-container {
        tailf:cli-drop-node-name;
        tailf:cli-compact-syntax;
        leaf cost {
          tailf:info
            "OSPF cost for point-to-multipoint neighbor";
          type uint32 {
            tailf:info
              "<1-65535>;;metric";
            range "1..65535";
          }
        }
        container database-filter {
          tailf:info
            "Filter OSPF LSA during synchronization and flooding for point-to-multipoint neighbor";
          tailf:cli-flatten-container;
          tailf:cli-compact-syntax;
          container all {
            tailf:info
              "Filter all LSA";
            tailf:cli-flatten-container;
            tailf:cli-compact-syntax;
            leaf out {
              tailf:info
                "Outgoing LSA";
              type empty;
            }
          }
        }
      }
      container poll-interval-priority-container {
        tailf:cli-drop-node-name;
        tailf:cli-compact-syntax;
        leaf poll-interval {
          tailf:info
            "OSPF dead-router polling interval";
          type uint32 {
            tailf:info
              "<0-65535>;;Seconds";
            range "0..65535";
          }
        }
        leaf priority {
          tailf:info
            "OSPF priority of non-broadcast neighbor";
          type uint32 {
            tailf:info
              "<0-255>;;Priority";
            range "0..255";
          }
        }
      }
    }
    list network {
      tailf:info
        "Enable routing on an IP network";
      tailf:cli-incomplete-command;
      tailf:cli-suppress-mode;
      tailf:cli-delete-when-empty;
      key "ip mask";
      leaf ip {
        type inet:ipv4-address {
          tailf:info
            "A.B.C.D;;Network number";
        }
      }
      leaf mask {
        type inet:ipv4-address {
          tailf:info
            "A.B.C.D;;OSPF wild card bits";
        }
      }
      leaf area {
        tailf:info
          "Set the OSPF area ID";
        type ospf-area-type;
      }
    }
    container nsf {
      tailf:info
        "Non-stop forwarding";
      presence "true";
      container cisco {
        tailf:info
          "Cisco Non-stop forwarding";
        tailf:cli-delete-when-empty;
        presence "true";
        container helper {
          tailf:info
            "helper support";
          presence "true";
          leaf disable {
            tailf:info
              "disable helper support";
            tailf:cli-reset-container;
            type empty;
          }
        }
      }
      container ietf {
        tailf:info
          "IETF graceful restart";
        container helper {
          tailf:info
            "helper support";
          presence "helper support";
          leaf disable {
            tailf:info
              "disable helper support";
            tailf:cli-reset-container;
            tailf:cli-delete-container-on-delete;
            type empty;
          }
          leaf strict-lsa-checking {
            tailf:info
              "enable helper strict LSA checking";
            type empty;
          }
        }
      }
    }
    leaf prefix-suppression {
      tailf:info
        "OSPF prefix suppression";
      tailf:cli-full-command;
      type empty;
    }
    container process-min-time {
      tailf:info
        "Percentage of quantum to be used before releasing CPU";
      leaf percent {
        tailf:info
          "percent";
        type uint32 {
          range "1..100";
          tailf:info
            "<1-100>;;Minimum CPU quantum";
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    leaf shutdown {
      tailf:info
        "Shutdown the OSPF protocol under the current instance";
      tailf:cli-boolean-no;
      type boolean;
    }
    list summary-address {
      tailf:info
        "Configure IP address summaries";
      tailf:cli-suppress-mode;
      tailf:cli-delete-when-empty;
      key "ip wildcard";
      leaf ip {
        type inet:ipv4-address {
          tailf:info
            "A.B.C.D;;IP summary address";
        }
      }
      leaf wildcard {
        type inet:ipv4-address {
          tailf:info
            "A.B.C.D;;Summary mask";
        }
      }
      choice tag-no-advertise-choice {
        leaf tag {
          tailf:info
            "Set tag";
          tailf:cli-full-command;
          type uint32 {
            range "0..4294967295";
            tailf:info
              "<0-4294967295>;;32-bit tag value";
          }
        }
        leaf not-advertise {
          tailf:info
            "Do not advertise when translating OSPF type-7 LSA";
          type empty;
          tailf:cli-full-command;
        }
      }
    }
    container discard-route {
      tailf:info
        "Enable or disable discard-route installation";
      tailf:cli-compact-syntax;
      presence "true";
      leaf external {
        tailf:info
          "Discard route for redistributed summarised routes";
        type uint32 {
          tailf:info
            "<1-255>;;Administrative distance for redistributed summarised routes";
          range "1..255";
        }
      }
      leaf internal {
        tailf:info
          "Discard route for summarised internal routes";
        type uint32 {
          tailf:info
            "<1-255>;;Administrative distance for summarised internal routes";
          range "1..255";
        }
      }
    }
  }

  grouping ncs_rpc_notif_router-ospfv3-grouping;

  grouping ncs_rpc_notif_ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        tailf:info
          "<0-4294967295>;;32-bit tag value";
        range "0..4294967295";
      }
    }
  }

  grouping ncs_rpc_notif_ospf-iso-igrp-redistribute-grouping {
    leaf metric {
      tailf:info
        "Metric for redistributed routes";
      type uint32 {
        tailf:info
          "<0-16777214>;;OSPF default metric";
      }
    }
    leaf metric-type {
      tailf:info
        "OSPF/IS-IS exterior metric type for redistributed routes";
      type enumeration {
        enum "1" {
          tailf:info
            "Set OSPF External Type 1 metrics";
        }
        enum "2" {
          tailf:info
            "Set OSPF External Type 2 metrics";
        }
      }
      default "2";
    }
    leaf tag {
      tailf:info
        "Set tag for routes redistributed into OSPF";
      type uint32 {
        tailf:info
          "<0-4294967295>;;32-bit tag value";
        range "0..4294967295";
      }
    }
    leaf level {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    leaf subnets {
      tailf:info
        "Consider subnets for redistribution into OSPF";
      type empty;
    }
  }

  grouping ncs_rpc_notif_router-ospf-redistribute-grouping {
    uses ncs_rpc_notif_ospf-iso-igrp-redistribute-grouping;
    leaf route-map {
      tailf:info
        "Route map reference";
      type string {
        tailf:info
          "WORD;;Pointer to route-map entries";
      }
    }
  }

  grouping ncs_rpc_notif_router-rip-af-grouping {
    leaf auto-summary {
      tailf:info
        "Enable automatic network number summarization";
      tailf:cli-boolean-no;
      tailf:cli-full-command;
      type boolean;
      default "true";
    }
    leaf maximum-paths {
      tailf:info
        "Forward packets over multiple paths";
      tailf:cli-full-command;
      type uint8 {
        tailf:info
          "1-32;;Number of paths";
        range "1..32";
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
    }
    list network {
      tailf:info
        "Enable routing on an IP network";
      tailf:cli-suppress-mode;
      tailf:cli-delete-when-empty;
      key "ip";
      leaf ip {
        type inet:ipv4-address {
          tailf:info
            "A.B.C.D;;Network number";
        }
      }
    }
    leaf validate-update-source {
      tailf:info
        "Perform sanity checks against source address of routing updates";
      tailf:cli-boolean-no;
      tailf:cli-full-command;
      type boolean;
      default "true";
    }
    container default-information {
      tailf:info
        "Control distribution of default information";
      container originate {
        tailf:info
          "Distribute a default route";
        presence "true";
        leaf route-map {
          tailf:info
            "Route-map reference";
          type string {
            tailf:info
              "WORD;;Route map name";
          }
        }
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      tailf:cli-compact-syntax;
      leaf distance-leaf {
        tailf:cli-drop-node-name;
        tailf:cli-full-command;
        type uint8 {
          tailf:info
            "1-255;;Administrative distance";
          range "1..255";
        }
      }
      list distance-list {
        tailf:cli-drop-node-name;
        tailf:cli-suppress-mode;
        tailf:cli-delete-when-empty;
        key "number ip mask";
        leaf number {
          tailf:cli-suppress-range;
          type uint8 {
            tailf:info
              "1-255;;Administrative distance";
            range "1..255";
          }
        }
        leaf ip {
          type inet:ipv4-address {
            tailf:info
              "A.B.C.D;;IP source address";
          }
        }
        leaf mask {
          type inet:ipv4-address {
            tailf:info
              "A.B.C.D;;Wildcard bits";
          }
        }
        leaf access-list {
          tailf:cli-drop-node-name;
          type std-ip-acl-type;
        }
      }
    }
    uses ncs_rpc_notif_router-distribute-list-grouping;
    list offset-list {
      tailf:info
        "Add or subtract offset from RIP metrics";
      tailf:cli-suppress-mode;
      tailf:cli-delete-when-empty;
      tailf:cli-compact-syntax;
      tailf:cli-sequence-commands;
      tailf:cli-incomplete-command;
      key "direction";
      leaf direction {
        type enumeration {
          enum "in" {
            tailf:info
              "Perform offset on incoming updates";
          }
          enum "out" {
            tailf:info
              "Perform offset on outgoing updates";
          }
        }
      }
      leaf id {
        tailf:cli-drop-node-name;
        tailf:cli-prefix-key;
        type rip-offset-list-id-type;
      }
      leaf offset {
        tailf:cli-drop-node-name;
        type uint8 {
          tailf:info
            "<0-16>;;Offset";
          range "0..16";
        }
      }
    }
    container redistribute {
      tailf:info
        "Redistribute information from another routing protocol";
      container connected {
        tailf:info
          "Connected";
        tailf:cli-compact-syntax;
        presence "true";
        uses ncs_rpc_notif_rip-metric-route-map-grouping;
      }
      container bgp {
        tailf:info
          "Border Gateway Protocol (BGP)";
        tailf:cli-compact-syntax;
        leaf as-number {
          tailf:cli-drop-node-name;
          type union {
            type uint32 {
              tailf:info
                "<1-4294967295>;;Autonomous system number";
            }
            type string {
              tailf:info
                "<1.0-XX.YY>;;Autonomous system number";
            }
          }
        }
        uses ncs_rpc_notif_rip-metric-route-map-grouping;
      }
      list eigrp {
        tailf:info
          "Enhanced Interior Gateway Routing Protocol (EIGRP)";
        tailf:cli-suppress-mode;
        tailf:cli-delete-when-empty;
        tailf:cli-compact-syntax;
        key "as-number";
        leaf as-number {
          type uint16 {
            tailf:info
              "<1-65535>;;AS number";
            range "1..65535";
          }
        }
        uses ncs_rpc_notif_rip-metric-route-map-grouping;
      }
      container isis {
        tailf:info
          "ISO IS-IS";
        tailf:cli-compact-syntax;
        tailf:cli-delete-when-empty;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses ncs_rpc_notif_rip-metric-route-map-grouping;
        }
        leaf level {
          tailf:cli-drop-node-name;
          type isis-level-type;
        }
        uses ncs_rpc_notif_rip-metric-route-map-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses ncs_rpc_notif_rip-metric-route-map-grouping;
        }
        uses ncs_rpc_notif_rip-metric-route-map-grouping;
      }
      container mobile {
        tailf:info
          "Mobile routes";
        tailf:cli-compact-syntax;
        presence "Mobile routes";
        uses ncs_rpc_notif_rip-metric-route-map-grouping;
      }
      container odr {
        tailf:info
          "On Demand stub Routes";
        tailf:cli-compact-syntax;
        presence "On Demand stub Routes";
        uses ncs_rpc_notif_rip-metric-route-map-grouping;
      }
      list ospf {
        tailf:info
          "Open Shortest Path First (OSPF)";
        tailf:cli-suppress-mode;
        tailf:cli-delete-when-empty;
        tailf:cli-compact-syntax;
        key "process-id";
        leaf process-id {
          tailf:cli-suppress-range;
          type uint16 {
            tailf:info
              "<1-65535>;;Process ID";
            range "1..65535";
          }
        }
        uses ncs_rpc_notif_rip-metric-route-map-grouping;
        container match {
          tailf:info
            "Redistribution of OSPF routes";
          tailf:cli-flatten-container;
          tailf:cli-compact-syntax;
          uses ncs_rpc_notif_redistribute-ospf-match-grouping;
          uses ncs_rpc_notif_rip-metric-route-map-grouping;
        }
      }
      container static {
        tailf:info
          "Static routes";
        tailf:cli-compact-syntax;
        tailf:cli-delete-when-empty;
        presence "Static routes";
        uses ncs_rpc_notif_rip-metric-route-map-grouping;
      }
      container rip {
        tailf:info
          "Routing Information Protocol (RIP)";
        tailf:cli-compact-syntax;
        presence "true";
        uses ncs_rpc_notif_rip-metric-route-map-grouping;
      }
    }
    container timers {
      tailf:info
        "Adjust routing timers";
      tailf:cli-incomplete-no;
      tailf:cli-compact-syntax;
      container basic {
        tailf:info
          "Basic routing protocol update timers";
        tailf:cli-compact-syntax;
        tailf:cli-sequence-commands;
        tailf:cli-full-no;
        leaf updates {
          tailf:cli-drop-node-name;
          tailf:cli-incomplete-command;
          tailf:cli-no-value-on-delete;
          type uint32 {
            tailf:info
              "1-4294967295;;Interval between updates for RIP";
            range "1..4294967295";
          }
        }
        leaf invalid {
          tailf:cli-drop-node-name;
          tailf:cli-incomplete-command;
          tailf:cli-no-value-on-delete;
          type uint32 {
            tailf:info
              "1-4294967295;;Invalid";
            range "1..4294967295";
          }
        }
        leaf holddown {
          tailf:cli-drop-node-name;
          tailf:cli-incomplete-command;
          tailf:cli-no-value-on-delete;
          type uint32 {
            tailf:info
              "1-4294967295;;Holddown";
            range "1..4294967295";
          }
        }
        leaf flush {
          tailf:cli-drop-node-name;
          tailf:cli-incomplete-command;
          tailf:cli-no-value-on-delete;
          type uint32 {
            tailf:info
              "1-4294967295;;Flush";
            range "1..4294967295";
          }
        }
        leaf sleep {
          tailf:cli-drop-node-name;
          tailf:cli-no-value-on-delete;
          type uint32 {
            tailf:info
              "1-4294967295;;Sleep time, in milliseconds";
            range "1..4294967295";
          }
        }
      }
    }
    leaf version {
      tailf:info
        "Set routing protocol version";
      tailf:cli-diff-dependency "/ios:ip/routing" {
        tailf:xpath-root 3;
        tailf:cli-trigger-on-set;
      }
      type uint8 {
        tailf:info
          "1-2;;rip version 1 or 2";
        range "1..2";
      }
    }
    container traffic-share {
      tailf:info
        "How to compute traffic share over alternate paths";
      container min {
        tailf:info
          "All traffic shared among min metric paths";
        leaf across-interfaces {
          tailf:info
            "Use different interfaces for equal-cost paths";
          type empty;
        }
      }
    }
  }

  grouping ncs_rpc_notif_router-rip-grouping {
    uses ncs_rpc_notif_router-rip-af-grouping;
    uses ncs_rpc_notif_passive-interface-grouping;
    leaf output-delay {
      tailf:info
        "Interpacket delay for RIP updates";
      tailf:cli-full-command;
      type uint8 {
        tailf:info
          "8-50;;Delay in milliseconds";
        range "8..50";
      }
    }
    leaf input-queue {
      tailf:info
        "Specify input queue depth";
      tailf:cli-full-command;
      type uint16 {
        tailf:info
          "0-1024;;queue depth";
        range "0..1024";
      }
    }
    leaf flash-update-threshold {
      tailf:info
        "Specify flash update threshold in second";
      tailf:cli-full-command;
      type uint8 {
        tailf:info
          "<0-30>;;threshold in seconds";
        range "0..30";
      }
    }
  }

  grouping ncs_rpc_notif_rip-metric-route-map-grouping {
    leaf metric {
      tailf:info
        "Metric for redistributed routes";
      type union {
        type uint8 {
          tailf:info
            "<0-16>;;Default metric";
          range "0..16";
        }
        type enumeration {
          enum "transparent" {
            tailf:info
              "Transparently redistribute metric";
          }
        }
      }
    }
    leaf route-map {
      tailf:info
        "Route map reference";
      type string {
        tailf:info
          "WORD;;Pointer to route-map entries";
      }
    }
  }

  grouping ncs_rpc_notif_eigrp-metric-route-map-grouping {
    container metric {
      tailf:info
        "Metric for redistributed routes";
      tailf:cli-flatten-container;
      tailf:cli-compact-syntax;
      tailf:cli-sequence-commands {
        tailf:cli-reset-siblings;
      }
      leaf bandwidth-metric {
        tailf:cli-drop-node-name;
        tailf:cli-incomplete-command;
        type uint32 {
          tailf:info
            "<1-4294967295>;;Bandwidth metric in Kbits per second";
        }
      }
      leaf delay-metric {
        tailf:cli-drop-node-name;
        tailf:cli-incomplete-command;
        type uint32 {
          tailf:info
            "<0-4294967295>;;EIGRP delay metric, in 10 microsecond units";
        }
      }
      leaf reliability-metric {
        tailf:cli-drop-node-name;
        tailf:cli-incomplete-command;
        type uint8 {
          tailf:info
            "<0-255>;;EIGRP reliability metric where 255 is 100% reliable";
        }
      }
      leaf effective-bandwidth-metric {
        tailf:cli-drop-node-name;
        tailf:cli-incomplete-command;
        type uint8 {
          tailf:info
            "<1-255>;;EIGRP Effective bandwidth metric (Loading) where 255 is 100% loaded";
          range "1..255";
        }
      }
      leaf mtu-bytes {
        tailf:cli-drop-node-name;
        type uint16 {
          tailf:info
            "<1-65535>;;EIGRP MTU of the path";
          range "1..65535";
        }
      }
    }
    leaf route-map {
      tailf:info
        "Route map reference";
      type string {
        tailf:info
          "WORD;;Pointer to route-map entries";
      }
    }
  }

  grouping ncs_rpc_notif_narrow-wide-transition-grouping {
    leaf narrow-wide {
      tailf:cli-drop-node-name;
      tailf:cli-full-command;
      type isis-level-type;
    }
    leaf transition {
      tailf:info
        "Accept both styles of TLVs during transition";
      tailf:cli-full-command;
      type isis-level-type;
    }
  }

  grouping ncs_rpc_notif_spf-intervals-grouping {
    leaf interval {
      tailf:cli-drop-node-name;
      type uint32 {
        tailf:info
          "<1-120>;;Interval between consecutive SPFs in seconds";
        range "1..120";
      }
    }
    leaf initial-wait {
      tailf:cli-drop-node-name;
      type uint32 {
        tailf:info
          "<1-120000>;;Initial wait before first SPF in milliseconds";
        range "1..120000";
      }
    }
    leaf minimum-wait {
      tailf:cli-drop-node-name;
      type uint32 {
        tailf:info
          "<1-120000>;;Minimum wait between first and second SPF in milliseconds";
        range "1..120000";
      }
    }
  }

  grouping ncs_rpc_notif_router-isis-authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping ncs_rpc_notif_lsp-gen-interval-grouping {
    leaf interval {
      tailf:cli-drop-node-name;
      type uint32 {
        range "1..120";
        tailf:info
          "<1-120>;;Interval in seconds";
      }
    }
    leaf initial-wait {
      tailf:cli-drop-node-name;
      type uint32 {
        range "1..120000";
        tailf:info
          "<1-120000>;;Initial wait in milliseconds";
      }
    }
    leaf wait {
      tailf:cli-drop-node-name;
      type uint32 {
        range "1..120000";
        tailf:info
          "<1-120000>;;Wait between first and second lsp generation in milliseconds";
      }
    }
  }

  grouping ncs_rpc_notif_set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping ncs_rpc_notif_summary-address-metric-tag-grouping {
    leaf metric {
      tailf:info
        "Set metric for summay route";
      tailf:cli-full-command;
      type uint32 {
        range "1..4294967295";
        tailf:info
          "<1-4294967295>;;metric";
      }
    }
    leaf tag {
      tailf:info
        "Set tag";
      type uint32 {
        range "1..4294967295";
        tailf:info
          "<1-4294967295>;;32-bit tag value";
      }
    }
  }

  grouping ncs_rpc_notif_authentication-level-grouping {
    leaf level {
      tailf:cli-drop-node-name;
      type authentication-level-type;
    }
  }

  grouping ncs_rpc_notif_redist-level-grouping {
    leaf level {
      tailf:cli-drop-node-name;
      tailf:cli-break-sequence-commands;
      type isis-level-type;
    }
  }

  grouping ncs_rpc_notif_isis-redist-container-content-grouping {
    uses ncs_rpc_notif_redist-level-grouping;
    leaf metric {
      tailf:info
        "ISIS default metric";
      type uint32 {
        tailf:info
          "<0-4294967295>;;ISIS default metric";
        range "0..4294967295";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    leaf route-map {
      tailf:info
        "Route map reference";
      type string {
        tailf:info
          "WORD;;Pointer to route-map entries";
      }
    }
  }

  grouping ncs_rpc_notif_router-isis-redistribute-grouping {
    uses ncs_rpc_notif_isis-redist-container-content-grouping;
  }

  grouping ncs_rpc_notif_isis-redist-af-grouping {
    container isis-redist-af-container {
      tailf:cli-drop-node-name;
      leaf include-connected {
        tailf:info
          "Include connected";
        type empty;
      }
      uses ncs_rpc_notif_isis-redist-container-content-grouping;
    }
  }

  grouping ncs_rpc_notif_isis-redist-ospf-match-grouping {
    uses ncs_rpc_notif_redist-level-grouping;
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
  }

  grouping ncs_rpc_notif_isis-redist-clns-ip-grouping {
    uses ncs_rpc_notif_router-isis-redistribute-grouping;
    container clns {
      tailf:info
        "Redistribution of BGP NSAP routes";
      presence "Redistribution of BGP NSAP routes";
      leaf route-map {
        tailf:info
          "Route map reference";
        type string {
          tailf:info
            "WORD;;Pointer to route-map entries";
        }
      }
    }
    leaf ip {
      tailf:info
        "Redistribution of BGP IP routes";
      type empty;
    }
  }

  grouping ncs_rpc_notif_router-isis-interface-grouping {
    container authentication {
      tailf:info
        "ISIS authentication for LSPs";
      container mode {
        tailf:info
          "Authentication mode";
        container md5 {
          tailf:info
            "Keyed message digest";
          presence "true";
          uses ncs_rpc_notif_authentication-level-grouping;
        }
        container text {
          tailf:info
            "Clear text password";
          presence "true";
          uses ncs_rpc_notif_authentication-level-grouping;
        }
      }
      container key-chain {
        tailf:info
          "Authentication key-chain";
        tailf:cli-compact-syntax;
        tailf:cli-sequence-commands;
        leaf name {
          tailf:cli-drop-node-name;
          type string {
            tailf:info
              "WORD;;Name of key-chain";
          }
        }
        uses ncs_rpc_notif_authentication-level-grouping;
      }
      container send-only {
        tailf:info
          "Authentication send only, receive ignore";
        presence "true";
        uses ncs_rpc_notif_authentication-level-grouping;
      }
    }
  }

  grouping ncs_rpc_notif_router-isis-af-grouping {
    leaf adjacency-check {
      tailf:info
        "Check ISIS neighbor protocol support";
      tailf:cli-full-command;
      type empty;
    }
    container default-information {
      tailf:info
        "Control distribution of default information";
      tailf:cli-incomplete-no;
      container originate {
        tailf:info
          "Distribute a default route";
        presence "true";
        leaf route-map {
          tailf:info
            "Route-map reference";
          type string {
            tailf:info
              "WORD;;Route map name";
          }
        }
      }
    }
    leaf maximum-paths {
      tailf:info
        "Forward packets over multiple paths";
      tailf:cli-full-command;
      type uint32 {
        tailf:info
          "<1-32>;;Number of paths";
        range "1..32";
      }
    }
    container metric {
      tailf:info
        "Set ISIS metric for all interfaces";
      tailf:cli-compact-syntax;
      tailf:cli-sequence-commands;
      leaf default {
        tailf:cli-drop-node-name;
        type uint32 {
          tailf:info
            "<1-63>;;Default metric";
          range "1..63";
        }
      }
      leaf level-1-2 {
        tailf:cli-drop-node-name;
        type enumeration {
          enum "level-1" {
            tailf:info
              "Apply metric to level-1 links";
          }
          enum "level-2" {
            tailf:info
              "Apply metric to level-2 links";
          }
        }
      }
    }
    container prc-interval {
      tailf:info
        "Minimum interval between partial route calculations";
      tailf:cli-compact-syntax;
      tailf:cli-sequence-commands;
      leaf interval {
        tailf:cli-drop-node-name;
        type uint32 {
          tailf:info
            "<1-120>;;PRC interval in seconds";
          range "1..120";
        }
      }
      leaf initial-wait {
        tailf:cli-drop-node-name;
        type uint32 {
          tailf:info
            "<1-120000>;;Initial wait for PRC in milliseconds";
          range "1..120000";
        }
      }
      leaf minimum-wait {
        tailf:cli-drop-node-name;
        type uint32 {
          tailf:info
            "<1-120000>;;Minimum wait between first and second PRC in milliseconds";
          range "1..120000";
        }
      }
    }
    container set-overload-bit {
      tailf:info
        "Signal other routers not to use us in SPF";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  tailf:info
                    "<5-86400>;;Time in seconds to advertise ourself as overloaded after reboot";
                  range "5..86400";
                }
              }
              leaf suppress {
                tailf:info
                  "If overload-bit set, suppress the following types of IP prefixes";
                tailf:cli-incomplete-command;
                type empty;
              }
              uses ncs_rpc_notif_set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                uses ncs_rpc_notif_set-overload-bit-suppress-grouping;
              }
            }
          }
        }
        container suppress {
          tailf:info
            "If overload-bit set, suppress the following types of IP prefixes";
          tailf:cli-compact-syntax;
          uses ncs_rpc_notif_set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses ncs_rpc_notif_spf-intervals-grouping;
        }
        container intervals {
          tailf:cli-drop-node-name;
          tailf:cli-compact-syntax;
          tailf:cli-sequence-commands;
          uses ncs_rpc_notif_spf-intervals-grouping;
        }
      }
    }
    container traffic-share {
      tailf:info
        "How to compute traffic share over alternate paths";
      container min {
        tailf:info
          "All traffic shared among min metric paths";
        leaf across-interface {
          tailf:info
            "Use different interfaces for equal-cost paths";
          type empty;
        }
      }
    }
  }

  grouping ncs_rpc_notif_router-isis-grouping {
    container isis-main-container {
      tailf:cli-drop-node-name;
      uses ncs_rpc_notif_router-isis-af-grouping;
      uses ncs_rpc_notif_router-isis-interface-grouping;
      container address-family {
        tailf:info
          "Enter Address Family command mode";
        container ipv6 {
          tailf:info
            "Address family";
          container unicast {
            tailf:cli-add-mode;
            tailf:cli-mode-name "config-router-af";
            tailf:info
              "Address Family Modifier";
            tailf:cli-full-command;
            tailf:cli-exit-command "exit-address-family" {
              tailf:info
                "Exit from Address Family configuration mode";
            }
            uses ncs_rpc_notif_router-isis-af-grouping;
            leaf distance {
              tailf:info
                "Administrative distance";
              tailf:cli-full-command;
              type uint32 {
                tailf:info
                  "<1-255>;;OSPF Administrative distance";
                range "1..255";
              }
            }
            container multi-topology {
              tailf:info
                "Enable multi-topology mode";
              presence "Enable multi-topology mode";
              leaf transition {
                tailf:info
                  "Accept and generate both IS-IS IPv6 and Multi-topology IPv6 TLVs";
                type empty;
              }
            }
            container redistribute {
              tailf:info
                "Redistribute IPv6 prefixes from another routing protocol";
              container bgp {
                tailf:info
                  "Border Gateway Protocol (BGP)";
                tailf:cli-compact-syntax;
                tailf:cli-sequence-commands;
                leaf as-number {
                  tailf:cli-drop-node-name;
                  type uint32 {
                    range "1..65535";
                    tailf:info
                      "<1-65535>;;Autonomous system number";
                  }
                }
                uses ncs_rpc_notif_isis-redist-af-grouping;
              }
              container connected {
                tailf:info
                  "Connected";
                presence "Connected";
                uses ncs_rpc_notif_router-isis-redistribute-grouping;
              }
              list eigrp {
                tailf:info
                  "Enhanced Interior Gateway Routing Protocol (EIGRP)";
                tailf:cli-suppress-mode;
                tailf:cli-delete-when-empty;
                key "as-number";
                leaf as-number {
                  tailf:cli-drop-node-name;
                  type uint32 {
                    range "1..65535";
                    tailf:info
                      "<1-65535>;;Autonomous system number";
                  }
                }
                uses ncs_rpc_notif_isis-redist-af-grouping;
              }
              container isis {
                tailf:info
                  "ISO IS-IS";
                tailf:cli-compact-syntax;
                leaf area-tag {
                  tailf:cli-drop-node-name;
                  tailf:cli-disallow-value "level-1|level-2";
                  type string {
                    tailf:info
                      "WORD;;IPv6 process name";
                  }
                }
                container levels {
                  tailf:cli-drop-node-name;
                  tailf:cli-sequence-commands;
                  leaf isis-redist-levels1 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf into {
                    tailf:info
                      "from level-n into level-m";
                    tailf:cli-incomplete-command;
                    type empty;
                  }
                  leaf isis-redist-levels2 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf distribute-list {
                    tailf:info
                      "select routes";
                    type string {
                      tailf:info
                        "WORD;;IPv6 prefix-list name";
                    }
                  }
                }
              }
              container nemo {
                tailf:info
                  "Network Mobility (NEMO)";
                tailf:cli-compact-syntax;
                uses ncs_rpc_notif_isis-redist-af-grouping;
              }
              list ospf {
                tailf:info
                  "Open Shortest Path First (OSPF)";
                tailf:cli-suppress-mode;
                tailf:cli-delete-when-empty;
                tailf:cli-compact-syntax;
                key "process-id";
                leaf process-id {
                  tailf:cli-suppress-range;
                  type uint32 {
                    tailf:info
                      "<1-65535>;;Process ID";
                    range "1..65535";
                  }
                }
                uses ncs_rpc_notif_isis-redist-af-grouping;
                container match {
                  tailf:info
                    "Redistribution of OSPF routes";
                  tailf:cli-flatten-container;
                  tailf:cli-compact-syntax;
                  uses ncs_rpc_notif_redistribute-ospf-match-grouping;
                  uses ncs_rpc_notif_isis-redist-ospf-match-grouping;
                }
              }
              list rip {
                tailf:info
                  "IPv6 Routing Information Protocol (RIPv6)";
                tailf:cli-suppress-mode;
                tailf:cli-delete-when-empty;
                key "process";
                leaf process {
                  type string {
                    tailf:info
                      "WORD;;User selected string identifying this process";
                  }
                }
                uses ncs_rpc_notif_isis-redist-af-grouping;
              }
              container static {
                tailf:info
                  "Static routes";
                presence "Static routes";
                uses ncs_rpc_notif_router-isis-redistribute-grouping;
              }
            }
            list summary-prefix {
              tailf:info
                "Configure IPv6 summary prefix";
              tailf:cli-suppress-mode;
              tailf:cli-delete-when-empty;
              key "prefix";
              leaf prefix {
                type inet:ipv6-prefix {
                  tailf:info
                    "X:X:X:X::X/<0-128>;;IPv6 prefix x:x::y/<z>";
                }
              }
              leaf levels {
                tailf:cli-drop-node-name;
                type enumeration {
                  enum "level-1" {
                    tailf:info
                      "Summarize into level-1 area";
                  }
                  enum "level-1-2" {
                    tailf:info
                      "Summarize into both area and sub-domain";
                  }
                  enum "level-2" {
                    tailf:info
                      "Summarize into level-2 sub-domain";
                  }
                }
              }
            }
          }
        }
      }
      container advertise {
        tailf:info
          "Control which IP routes flow in L1 and L2 LSPs";
        leaf passive-only {
          tailf:info
            "only interface address of passive interfaces";
          type empty;
        }
      }
      container area-password {
        tailf:info
          "Configure the authentication password for an area";
        tailf:cli-compact-syntax;
        tailf:cli-sequence-commands;
        leaf name {
          tailf:cli-drop-node-name;
          type string {
            tailf:info
              "WORD;;Area password";
          }
        }
        uses ncs_rpc_notif_router-isis-authenticate-snp-grouping;
      }
      container nsf {
        tailf:info
          "Non-stop forwarding";
        leaf cisco {
          tailf:info
            "Checkpoint method";
          type empty;
        }
      }
      container bfd {
        tailf:info
          "BFD configuration commands";
        leaf all-interfaces {
          tailf:info
            "Enable BFD on all interfaces";
          type empty;
        }
      }
      container distance {
        tailf:info
          "Define an administrative distance";
        tailf:cli-compact-syntax;
        container clns-container {
          tailf:cli-drop-node-name;
          tailf:cli-sequence-commands;
          leaf distance {
            tailf:cli-drop-node-name;
            type uint32 {
              tailf:info
                "<1-255>;;OSPF Administrative distance";
              range "1..255";
            }
          }
          leaf clns {
            tailf:info
              "Distance applied for CLNS derived routes";
            tailf:cli-full-command;
            type empty;
          }
        }
        container ip-container {
          tailf:cli-drop-node-name;
          tailf:cli-sequence-commands;
          leaf distance {
            tailf:cli-drop-node-name;
            type uint32 {
              range "1..255";
              tailf:info
                "<1-255>;;OSPF Administrative distance";
            }
          }
          leaf ip {
            tailf:info
              "Distance applied for IP derived routes";
            tailf:cli-full-command;
            type empty;
          }
        }
        container acl-container {
          tailf:cli-drop-node-name;
          tailf:cli-sequence-commands;
          leaf distance {
            tailf:cli-drop-node-name;
            type uint32 {
              tailf:info
                "<1-255>;;OSPF Administrative distance";
              range "1..255";
            }
          }
          list acl {
            tailf:cli-drop-node-name;
            tailf:cli-suppress-mode;
            tailf:cli-delete-when-empty;
            key "ip wildcard";
            leaf ip {
              type inet:ipv4-address {
                tailf:info
                  "A.B.C.D;;IP source address";
              }
            }
            leaf wildcard {
              type inet:ipv4-address {
                tailf:info
                  "A.B.C.D;;Wildcard bits";
              }
            }
            leaf access-list {
              tailf:cli-drop-node-name;
              type std-ip-acl-type;
            }
          }
        }
      }
      container domain-password {
        tailf:info
          "Set the authentication password for a routing domain";
        tailf:cli-sequence-commands;
        tailf:cli-compact-syntax;
        leaf name {
          tailf:cli-drop-node-name;
          type string {
            tailf:info
              "WORD;;Routing domain password";
          }
        }
        uses ncs_rpc_notif_router-isis-authenticate-snp-grouping;
      }
      container fast-flood {
        tailf:info
          "Flood LSPs (that triggered SPF) before running SPF";
        presence "Flood LSPs (that triggered SPF) before running SPF";
        leaf number {
          tailf:cli-drop-node-name;
          type uint32 {
            range "1..15";
            tailf:info
              "<1-15>;;number of LSPs to be flooded before starting SPF";
          }
        }
      }
      container hello {
        tailf:info
          "Pad ISIS hello PDUs to full MTU";
        container padding {
          tailf:info
            "Pad hello PDU";
          presence "Pad hello PDU";
          leaf pad-type {
            tailf:cli-drop-node-name;
            type enumeration {
              enum "multi-point" {
                tailf:info
                  "Pad LAN hello PDUs";
              }
              enum "point-to-point" {
                tailf:info
                  "Pad point-to-point hello PDUs";
              }
            }
          }
        }
      }
      container hostname {
        tailf:info
          "Dynamic hostname for IS-IS";
        leaf dynamic {
          tailf:info
            "Dynamic hostname";
          type empty;
        }
      }
      leaf ignore-lsp-errors {
        tailf:info
          "Ignore LSPs with bad checksums";
        tailf:cli-full-command;
        type empty;
      }
      container ip {
        tailf:info
          "IP specific commands";
        container route {
          tailf:info
            "ISIS IP routes";
          container priority {
            tailf:info
              "Assign priority to IP prefixes";
            container high {
              tailf:info
                "Assign high priority to important IP prefixes in ISIS IP local RIB";
              leaf tag {
                tailf:info
                  "Assign high priority to IP prefixes with a specific route tag";
                type uint32 {
                  range "1..4294967295";
                  tailf:info
                    "<1-4294967295>;;tag value";
                }
              }
            }
          }
        }
      }
      leaf is-type {
        tailf:info
          "IS Level for this routing process (OSI only)";
        tailf:cli-full-command;
        type enumeration {
          enum "level-1" {
            tailf:info
              "Act as a station router only";
          }
          enum "level-1-2" {
            tailf:info
              "Act as both a station router and an area router";
          }
          enum "level-2-only" {
            tailf:info
              "Act as an area router only";
          }
        }
      }
      container ispf {
        tailf:info
          "Configure execution of incremental SPF";
        tailf:cli-compact-syntax;
        tailf:cli-sequence-commands;
        leaf level {
          tailf:cli-drop-node-name;
          type enumeration {
            enum "level-1" {
              tailf:info
                "Do incremental SPF for level-1";
            }
            enum "level-1-2" {
              tailf:info
                "Do incremental SPF for both levels";
            }
            enum "level-2" {
              tailf:info
                "Do incremental SPF for level-2";
            }
          }
        }
        leaf number {
          tailf:cli-drop-node-name;
          type uint32 {
            range "1..600";
            tailf:info
              "<1-600>;;Number of seconds before activating incremental-spf";
          }
        }
      }
      container log-adjacency-changes {
        tailf:info
          "Log changes in adjacency state";
        presence "true";
        leaf all {
          tailf:info
            "Include changes generated by non-IIH event";
          type empty;
        }
      }
      container lsp-full {
        tailf:info
          "If we run out of LSP fragments";
        container suppress {
          tailf:info
            "suppress the following types of IP prefixes";
          choice lsp-full-choince {
            container external-interlevel-container {
              tailf:cli-drop-node-name;
              tailf:cli-compact-syntax;
              leaf external {
                tailf:info
                  "don't advertise IP prefixes learned from other protocols";
                type empty;
              }
              leaf interlevel {
                tailf:info
                  "don't advertise IP prefixes learned from another ISIS level";
                type empty;
              }
            }
            leaf none {
              tailf:info
                "don't suppress any prefixes";
              type empty;
            }
          }
        }
      }
      container lsp-gen-interval {
        tailf:info
          "Minimum interval between regenerating same LSP";
        choice lsp-gen-interval-choice {
          container intervals {
            tailf:cli-drop-node-name;
            tailf:cli-compact-syntax;
            tailf:cli-sequence-commands;
            uses ncs_rpc_notif_lsp-gen-interval-grouping;
          }
          container intervals-levels {
            tailf:cli-drop-node-name;
            container intervals-level-1 {
              tailf:cli-drop-node-name;
              tailf:cli-compact-syntax;
              tailf:cli-sequence-commands;
              leaf level-1 {
                tailf:info
                  "Set interval for level 1 only";
                type empty;
              }
              uses ncs_rpc_notif_lsp-gen-interval-grouping;
            }
            container intervals-level-2 {
              tailf:cli-drop-node-name;
              tailf:cli-compact-syntax;
              tailf:cli-sequence-commands;
              leaf level-2 {
                tailf:info
                  "Set interval for level 2 only";
                type empty;
              }
              uses ncs_rpc_notif_lsp-gen-interval-grouping;
            }
          }
        }
      }
      leaf lsp-mtu {
        tailf:info
          "Set maximum LSP size";
        tailf:cli-full-command;
        type uint32 {
          range "128..4352";
          tailf:info
            "<128-4352>;;Max LSP size in bytes";
        }
      }
      leaf lsp-refresh-interval {
        tailf:info
          "Set LSP refresh interval";
        tailf:cli-full-command;
        type uint32 {
          range "1..65535";
          tailf:info
            "<1-65535>;;LSP refresh time in seconds";
        }
      }
      leaf max-area-addresses {
        tailf:info
          "Allow configuration of more manual area addresses";
        tailf:cli-full-command;
        type uint32 {
          range "3..254";
          tailf:info
            "<3-254>;;Max number of manual area addresses";
        }
      }
      leaf max-lsp-lifetime {
        tailf:info
          "Set maximum LSP lifetime";
        tailf:cli-full-command;
        type uint32 {
          range "1..65535";
          tailf:info
            "<1-65535>;;Maximum LSP lifetime in seconds";
        }
      }
      container metric-style {
        tailf:info
          "Use old-style (ISO 10589) or new-style packet formats";
        choice metric-style-choice {
          container narrow {
            tailf:info
              "Use old style of TLVs with narrow metric";
            presence "true";
            uses ncs_rpc_notif_narrow-wide-transition-grouping;
          }
          container transition {
            tailf:info
              "Send and accept both styles of TLVs during transition";
            presence "true";
            leaf level {
              tailf:cli-drop-node-name;
              type isis-level-type;
            }
          }
          container wide {
            tailf:info
              "Use new style of TLVs to carry wider metric";
            presence "true";
            uses ncs_rpc_notif_narrow-wide-transition-grouping;
          }
        }
      }
      container mpls {
        tailf:info
          "Configure MPLS routing protocol parameters";
        container ldp {
          tailf:info
            "routing protocol commands for MPLS LDP";
          leaf sync {
            tailf:info
              "Configure LDP-IGP Synchronization";
            type empty;
          }
        }
        container traffic-eng {
          tailf:info
            "routing protocol commands for MPLS Traffic Engineering";
          leaf level-1 {
            tailf:info
              "Run MPLS TE on IS-IS level 1 only";
            tailf:cli-full-command;
            type empty;
          }
          leaf level-2 {
            tailf:info
              "Run MPLS TE on IS-IS level 2 only";
            tailf:cli-full-command;
            type empty;
          }
          leaf multicast-intact {
            tailf:info
              "MPLS TE and PIM interaction";
            tailf:cli-full-command;
            type empty;
          }
          container router-id {
            tailf:info
              "Traffic Engineering stable IP address for system";
            uses ncs_rpc_notif_interface-name-grouping;
          }
          container scanner {
            tailf:info
              "Timer parameters for TE database";
            presence "Timer parameters for TE database";
            tailf:cli-compact-syntax;
            leaf interval {
              tailf:info
                "time (secs) between LSPDB walks for TE";
              type uint32 {
                range "1..60";
                tailf:info
                  "<1-60>;;interval between LSPDB walks for TE TLVs extraction";
              }
            }
            leaf max-flash {
              tailf:info
                "Number of ISIS LSPs to be processed with no delay";
              type uint32 {
                range "0..200";
                tailf:info
                  "<0-200>;;Max. number of LSPs ISIS may send to TE db without delay";
              }
            }
          }
        }
      }
      list net {
        tailf:info
          "A Network Entity Title for this process (OSI only)";
        tailf:cli-suppress-mode;
        tailf:cli-delete-when-empty;
        key "tag";
        leaf tag {
          type string {
            tailf:info
              "XX.XXXX. ... .XXX.XX;;Network entity title (NET)";
          }
        }
      }
      container partition {
        tailf:info
          "CLNS area partition";
        leaf avoidance {
          tailf:info
            "Withdraw area prefix if partition detected";
          type empty;
        }
      }
      uses ncs_rpc_notif_passive-interface-grouping;
      container protocol {
        tailf:info
          "Set protocol's administrative state";
        leaf shutdown {
          tailf:info
            "Set protocol's administrative state to disable";
          type empty;
        }
      }
      container redistribute {
        tailf:info
          "Redistribute information from another routing protocol";
        container bgp {
          tailf:info
            "Border Gateway Protocol (BGP)";
          tailf:cli-compact-syntax;
          leaf as-number {
            tailf:cli-drop-node-name;
            type uint32 {
              range "1..65535";
              tailf:info
                "<1-65535>;;Autonomous system number";
            }
          }
          uses ncs_rpc_notif_isis-redist-clns-ip-grouping;
        }
        container connected {
          tailf:info
            "Connected";
          tailf:cli-compact-syntax;
          tailf:cli-delete-when-empty;
          presence "Connected";
          uses ncs_rpc_notif_router-isis-redistribute-grouping;
        }
        list eigrp {
          tailf:info
            "Enhanced Interior Gateway Routing Protocol (EIGRP)";
          tailf:cli-suppress-mode;
          tailf:cli-delete-when-empty;
          tailf:cli-compact-syntax;
          key "as-number";
          leaf as-number {
            tailf:cli-drop-node-name;
            type uint32 {
              range "1..65535";
              tailf:info
                "<1-65535>;;Autonomous system number";
            }
          }
          uses ncs_rpc_notif_router-isis-redistribute-grouping;
        }
        container isis {
          tailf:info
            "ISO IS-IS";
          tailf:cli-compact-syntax;
          leaf area-tag {
            tailf:cli-drop-node-name;
            tailf:cli-disallow-value "ip";
            type string {
              tailf:info
                "WORD;;ISO routing area tag";
            }
          }
          container ip {
            tailf:info
              "Redistribution of IP routes between levels";
            tailf:cli-flatten-container;
            tailf:cli-compact-syntax;
            tailf:cli-sequence-commands;
            leaf level {
              tailf:cli-drop-node-name;
              tailf:cli-incomplete-command;
              type enumeration {
                enum "level-1" {
                  tailf:info
                    "Inter-area routes from level-1";
                }
                enum "level-2" {
                  tailf:info
                    "Inter-area routes from level-2";
                }
              }
            }
            leaf into {
              tailf:info
                "from level-n into level-m";
              tailf:cli-incomplete-command;
              type empty;
            }
            leaf level2 {
              tailf:cli-drop-node-name;
              tailf:cli-incomplete-command;
              type enumeration {
                enum "level-1" {
                  tailf:info
                    "Inter-area routes from level-1";
                }
                enum "level-2" {
                  tailf:info
                    "Inter-area routes from level-2";
                }
              }
            }
            choice isis-redist-isis-ip-choice {
              leaf distribute-list {
                tailf:info
                  "select routes";
                type uint32 {
                  tailf:info
                    "<100-199>;;IP extended acces-list number";
                  range "100..199";
                }
              }
              leaf route-map {
                tailf:info
                  "Route map for route matching";
                type string {
                  tailf:info
                    "WORD;;Name of the route-map";
                }
              }
            }
          }
        }
        container iso-igrp {
          tailf:info
            "IGRP for OSI networks";
          presence "IGRP for OSI networks";
          tailf:cli-compact-syntax;
          tailf:cli-sequence-commands;
          choice iso-igrp-choice {
            container area-tag-route-map-container {
              tailf:cli-drop-node-name;
              tailf:cli-flatten-container;
              tailf:cli-compact-syntax;
              tailf:cli-sequence-commands;
              leaf area-tag {
                tailf:cli-drop-node-name;
                tailf:cli-disallow-value "route-map";
                type string {
                  tailf:info
                    "WORD;;ISO routing area tag";
                }
              }
              leaf route-map {
                tailf:info
                  "Route map reference";
                type string {
                  tailf:info
                    "WORD;;Pointer to route-map entries";
                }
              }
            }
            leaf route-map {
              tailf:info
                "Route map reference";
              type string {
                tailf:info
                  "WORD;;Pointer to route-map entries";
              }
            }
          }
          uses ncs_rpc_notif_redist-level-grouping;
          leaf metric {
            tailf:info
              "ISIS default metric";
            type uint32 {
              tailf:info
                "<0-4294967295>;;ISIS default metric";
              range "0..4294967295";
            }
          }
          leaf metric-type {
            tailf:info
              "OSPF/IS-IS exterior metric type for redistributed routes";
            type enumeration {
              enum "external" {
                tailf:info
                  "Set IS-IS External metric type";
              }
              enum "internal" {
                tailf:info
                  "Set IS-IS Internal metric type";
              }
            }
          }
        }
        container maximum-prefix {
          tailf:info
            "Maximum number of prefixes redistributed to protocol";
          tailf:cli-compact-syntax;
          tailf:cli-sequence-commands;
          leaf number {
            tailf:cli-drop-node-name;
            type uint32 {
              range "1..4294967295";
              tailf:info
                "<1-4294967295>;;Maximum number of IP prefixes redistributed";
            }
          }
          leaf threshold-value {
            tailf:cli-drop-node-name;
            tailf:cli-break-sequence-commands;
            type uint32 {
              tailf:info
                "<1-100>;;Threshold value (%) at which to generate a warning message";
              range "1..100";
            }
          }
          leaf warning-only {
            tailf:info
              "Only give warning message when limit is exceeded";
            tailf:cli-full-command;
            type empty;
          }
          leaf withdraw {
            tailf:info
              "Withdraw redistibuted prefixes";
            tailf:cli-full-command;
            type empty;
          }
        }
        container mobile {
          tailf:info
            "Mobile routes";
          tailf:cli-compact-syntax;
          presence "Mobile routes";
          uses ncs_rpc_notif_router-isis-redistribute-grouping;
        }
        container odr {
          tailf:info
            "On Demand stub Routes";
          tailf:cli-compact-syntax;
          presence "On Demand stub Routes";
          uses ncs_rpc_notif_router-isis-redistribute-grouping;
        }
        list ospf {
          tailf:info
            "Open Shortest Path First (OSPF)";
          tailf:cli-suppress-mode;
          tailf:cli-delete-when-empty;
          tailf:cli-compact-syntax;
          key "process-id";
          leaf process-id {
            tailf:cli-suppress-range;
            type uint32 {
              tailf:info
                "<1-65535>;;Process ID";
              range "1..65535";
            }
          }
          uses ncs_rpc_notif_router-isis-redistribute-grouping;
          container match {
            tailf:info
              "Redistribution of OSPF routes";
            tailf:cli-flatten-container;
            tailf:cli-compact-syntax;
            uses ncs_rpc_notif_redistribute-ospf-match-grouping;
            uses ncs_rpc_notif_isis-redist-ospf-match-grouping;
          }
        }
        container rip {
          tailf:info
            "Routing Information Protocol (RIP)";
          tailf:cli-compact-syntax;
          presence "Routing Information Protocol (RIP)";
          uses ncs_rpc_notif_router-isis-redistribute-grouping;
        }
        container static {
          tailf:info
            "Static routes";
          tailf:cli-compact-syntax;
          tailf:cli-delete-when-empty;
          presence "Static routes";
          uses ncs_rpc_notif_isis-redist-clns-ip-grouping;
        }
      }
      container set-attached-bit {
        tailf:info
          "Conditionally advertise us as attached to L2";
        leaf route-map {
          tailf:info
            "Route-map reference";
          type string {
            tailf:info
              "WORD;;Route map name";
          }
        }
      }
      list summary-address {
        tailf:info
          "Configure IP address summaries";
        tailf:cli-suppress-mode;
        tailf:cli-delete-when-empty;
        key "ip mask";
        leaf ip {
          type inet:ipv4-address {
            tailf:info
              "A.B.C.D;;IP summary address";
          }
        }
        leaf mask {
          type inet:ipv4-address {
            tailf:info
              "A.B.C.D;;Summary mask";
          }
        }
        container level-1 {
          tailf:info
            "Summarize into level-1 area";
          presence "Summarize into level-1 area";
          tailf:cli-compact-syntax;
          uses ncs_rpc_notif_summary-address-metric-tag-grouping;
        }
        container level-1-2 {
          tailf:info
            "Summarize into both area and sub-domain";
          presence "Summarize into both area and sub-domain";
          tailf:cli-compact-syntax;
          uses ncs_rpc_notif_summary-address-metric-tag-grouping;
        }
        container level-2 {
          tailf:info
            "Summarize into level-2 sub-domain";
          presence "Summarize into level-2 sub-domain";
          tailf:cli-compact-syntax;
          uses ncs_rpc_notif_summary-address-metric-tag-grouping;
        }
        container metric-tag-container {
          tailf:cli-drop-node-name;
          tailf:cli-compact-syntax;
          uses ncs_rpc_notif_summary-address-metric-tag-grouping;
        }
      }
      leaf update-queue-depth {
        tailf:info
          "Set Update process queue depth";
        type uint32 {
          tailf:info
            "<1-2147483647>;;Max queue depth";
          range "1..2147483647";
        }
      }
      container use {
        tailf:info
          "Use different algorithms during SPF";
        leaf external-metrics {
          tailf:info
            "Honour external metrics during SPF";
          type empty;
        }
      }
    }
  }

  grouping ncs_rpc_notif_interface-switch-grouping {
    container switchport {
      tailf:info
        "Set switching mode characteristics";
      tailf:cli-display-separated;
      tailf:callpoint interface-switchport-hook {
        tailf:set-hook node;
      }
      tailf:cli-diff-dependency "../ip/route-cache-conf/route-cache" {
        tailf:xpath-root 3;
        tailf:cli-trigger-on-set;
      }
      presence "true";
      container access {
        tailf:info
          "Set access mode characteristics of the interface";
        leaf vlan {
          tailf:info
            "Set VLAN when interface is in access mode";
          tailf:cli-diff-dependency "/ios:vlan/vlan-list/id" {
            tailf:xpath-root 3;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
        }
      }
      container trunk {
        tailf:info
          "Set trunking characteristics of the interface";
        leaf encapsulation {
          tailf:info
            "Set encapsulation format on trunk port";
          type enumeration {
            enum "dot1q" {
              tailf:info
                "Interface uses only 802.1q trunking encapsulation when trunking";
            }
            enum "isl" {
              tailf:info
                "Interface uses only ISL trunking encapsulation when trunking";
            }
            enum "negotiate" {
              tailf:info
                "Device will negotiate trunking encapsulation with peer on interface";
            }
          }
          default "negotiate";
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container allowed {
          tailf:info
            "Set allowed VLAN characteristics when interface is in trunking mode";
          container vlan {
            tailf:info
              "Set allowed VLANs when interface is in trunking mode";
            choice vlan-choice {
              leaf-list vlans {
                tailf:cli-replace-all;
                tailf:cli-range-list-syntax;
                tailf:cli-drop-node-name;
                type uint16 {
                  tailf:info
                    "WORD;;VLAN IDs of the allowed VLANs when this port is in trunking mode";
                }
              }
              leaf all {
                tailf:info
                  "all VLANs";
                type empty;
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-range-list-syntax;
                tailf:cli-drop-node-name;
                type uint16 {
                  tailf:info
                    "WORD;;VLAN IDs of the allowed VLANs when this port is in trunking mode";
                }
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
      }
      container autostate {
        tailf:info
          "Include or exclude this port from vlan link up calculation";
        tailf:cli-incomplete-command;
        leaf exclude {
          tailf:info
            "Exclude this port from vlan link up calculation";
          type empty;
        }
      }
      container private-vlan {
        tailf:info
          "Set the private VLAN configuration";
        container trunk {
          tailf:info
            "Set the private vlan trunking configuration";
          container native {
            tailf:info
              "Set the private vlan trunking native configuration";
            leaf vlan {
              tailf:info
                "Set native VLAN configuration";
              type union {
                type enumeration {
                  enum "tag" {
                    tailf:info
                      "Set native VLAN tagging state";
                  }
                }
                type uint16 {
                  tailf:info
                    "<1-4094>;;VLAN ID of the native VLAN when this port is in trunking mode";
                  range "1..4094";
                }
              }
            }
          }
          container allowed {
            tailf:info
              "Set allowed VLAN characteristics when interface is in private-vlan trunking mode";
            container vlan {
              tailf:info
                "Set allowed VLANs when interface is in private-vlan trunking mode";
              choice vlan-choice {
                leaf-list vlans {
                  tailf:cli-replace-all;
                  tailf:cli-range-list-syntax;
                  tailf:cli-drop-node-name;
                  type uint16 {
                    tailf:info
                      "WORD;;VLAN IDs of the allowed VLANs when interface is in private-vlan trunking mode";
                  }
                }
                leaf all {
                  tailf:info
                    "all VLANs";
                  type empty;
                }
                leaf-list except {
                  tailf:info
                    "all VLANs except the following";
                  tailf:cli-range-list-syntax;
                  type uint16 {
                    tailf:info
                      "WORD;;VLAN IDs of disallowed VLANS when this port is in trunking mode ";
                  }
                }
                leaf none {
                  tailf:info
                    "no VLANs";
                  type empty;
                }
              }
            }
          }
        }
        container association {
          tailf:info
            "Set the private VLAN association";
          list trunk {
            tailf:cli-suppress-mode;
            tailf:cli-delete-when-empty;
            tailf:cli-incomplete-command;
            key "primary-vlan-id";
            leaf primary-vlan-id {
              type uint16 {
                tailf:info
                  "<2-4094>;;Primary VLAN ID of the private VLAN trunk association";
                range "2..4094";
              }
            }
            leaf secondary-vlan-id {
              tailf:cli-drop-node-name;
              type uint16 {
                tailf:info
                  "<2-4094>;;Secondary VLAN ID of the private VLAN port/trunk association";
                range "2..4094";
              }
            }
          }
        }
      }
      container mode {
        tailf:info
          "Set trunking mode of the interface";
        choice mode-choice {
          container access {
            tailf:info
              "Set trunking mode to ACCESS unconditionally";
            presence "true";
          }
          container dot1q-tunnel {
            tailf:info
              "set trunking mode to TUNNEL unconditionally";
            presence "true";
          }
          leaf dynamic {
            tailf:info
              "Set trunking mode to dynamically negotiate access or trunk mode";
            type enumeration {
              enum "auto" {
                tailf:info
                  "Set trunking mode dynamic negotiation parameter to AUTO";
              }
              enum "desirable" {
                tailf:info
                  "Set trunking mode dynamic negotiation parameter to DESIRABLE";
              }
            }
          }
          container trunk {
            tailf:info
              "Set trunking mode to TRUNK unconditionally";
            tailf:cli-diff-dependency "../../trunk" {
              tailf:xpath-root 3;
            }
            presence "true";
          }
          container private-vlan {
            tailf:info
              "Set private-vlan mode";
            choice private-vlan-choice {
              leaf host {
                tailf:info
                  "Set the mode to private-vlan host";
                type empty;
              }
              leaf promiscuous {
                tailf:info
                  "Set the mode to private-vlan promiscuous";
                type empty;
              }
              container trunk {
                tailf:info
                  "Set the mode to private-vlan trunk";
                presence "true";
              }
            }
          }
        }
      }
      leaf nonegotiate {
        tailf:info
          "Device will not engage in negotiation protocol on this interface";
        tailf:cli-diff-dependency "../trunk" {
          tailf:xpath-root 3;
        }
        type empty;
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      container port-security {
        tailf:info
          "Security related command";
        tailf:cli-display-separated;
        tailf:cli-diff-dependency "../trunk" {
          tailf:xpath-root 3;
        }
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-compact-syntax;
          tailf:cli-sequence-commands {
            tailf:cli-reset-siblings;
          }
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        container maximum {
          tailf:info
            "Max secure addresses";
          tailf:cli-compact-syntax;
          tailf:cli-sequence-commands {
            tailf:cli-reset-siblings;
          }
          leaf max-addresses {
            tailf:cli-drop-node-name;
            type uint16 {
              tailf:info
                "<1-4097>;;Maximum addresses";
              range "1..4097";
            }
          }
          leaf vlan {
            tailf:info
              "Max secure addresses per vlan";
            type string {
              tailf:info
                "WORD;;VLAN IDs to which this maximum applies";
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      leaf protected {
        tailf:info
          "Configure an interface to be a protected port";
        type empty;
      }
      leaf host {
        tailf:info
          "Set port host";
        type empty;
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container mst {
        tailf:info
          "Multiple spanning tree";
        choice mst-choice {
          list instance-range {
            tailf:cli-suppress-mode;
            tailf:cli-delete-when-empty;
            tailf:cli-drop-node-name;
            tailf:cli-compact-syntax;
            tailf:cli-range-list-syntax;
            key "id";
            leaf id {
              type uint16 {
                tailf:info
                  "MST instance list, example 0,2-4,6,8-12";
              }
            }
            leaf cost {
              tailf:info
                "Change the interface spanning tree path cost for an instance";
              type uint32 {
                tailf:info
                  "<1-200000000>;;Change the interface spanning tree path cost for an instance";
                range "1..200000000";
              }
            }
            leaf port-priority {
              tailf:info
                "Change the spanning tree port priority for an instance";
              type uint16 {
                tailf:info
                  "<0-240>;;port priority in increments of 16";
                range "0..240" {
                  tailf:step "16";
                }
              }
            }
          }
          leaf pre-standard {
            tailf:info
              "Force pre-standard MST BPDU transmission on port";
            type empty;
          }
        }
      }
      container portfast {
        tailf:info
          "Spanning tree portfast options";
        tailf:cli-delete-when-empty;
        presence "true";
        leaf enable {
          tailf:cli-full-command;
          tailf:cli-drop-node-name;
          type enumeration {
            enum "disable" {
              tailf:info
                "Disable portfast for this interface";
            }
          }
        }
        leaf trunk {
          type empty;
        }
      }
      container loopguard {
        tailf:info
          "Spanning tree loopguard options";
        leaf default {
          tailf:info
            "Enable loopguard by default on all ports";
          type empty;
        }
      }
    }
    container srr-queue {
      container bandwidth {
        container shape {
          tailf:cli-compact-syntax;
          tailf:cli-sequence-commands;
          tailf:cli-reset-container;
          leaf weight1 {
            tailf:cli-drop-node-name;
            tailf:cli-incomplete-command;
            type uint16;
          }
          leaf weight2 {
            tailf:cli-drop-node-name;
            tailf:cli-incomplete-command;
            type uint16;
          }
          leaf weight3 {
            tailf:cli-drop-node-name;
            tailf:cli-incomplete-command;
            type uint16;
          }
          leaf weight4 {
            tailf:cli-drop-node-name;
            type uint16;
          }
        }
        container share {
          tailf:cli-compact-syntax;
          tailf:cli-sequence-commands;
          tailf:cli-reset-container;
          leaf weight1 {
            tailf:cli-drop-node-name;
            tailf:cli-incomplete-command;
            type uint8 {
              range "1..255";
            }
          }
          leaf weight2 {
            tailf:cli-drop-node-name;
            tailf:cli-incomplete-command;
            type uint8 {
              range "1..255";
            }
          }
          leaf weight3 {
            tailf:cli-drop-node-name;
            tailf:cli-incomplete-command;
            type uint8 {
              range "1..255";
            }
          }
          leaf weight4 {
            tailf:cli-drop-node-name;
            type uint8 {
              range "1..255";
            }
          }
        }
      }
    }
    leaf queue-set {
      type uint8;
    }
  }

  grouping ncs_rpc_notif_password-07-grouping {
    leaf type {
      tailf:cli-drop-node-name;
      tailf:cli-optional-in-sequence;
      type enumeration {
        enum "0" {
          tailf:info
            "Specifies an UNENCRYPTED password/key will follow";
        }
        enum "7" {
          tailf:info
            "Specifies a HIDDEN password/key will follow";
        }
      }
    }
    leaf secret {
      tailf:cli-drop-node-name;
      type string {
        tailf:info
          "LINE;;The UNENCRYPTED (cleartext) password/key";
      }
    }
  }

  grouping ncs_rpc_notif_router-lisp-af4-common-grouping {
    leaf map-request-source {
      tailf:info
        "Configures inner header source address in Map-Requestmessage";
      type inet:ipv4-address {
        tailf:info
          "A.B.C.D;;IPv4 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv4-local-locator {
        tailf:cli-drop-node-name;
        tailf:cli-optional-in-sequence;
        type inet:ipv4-address {
          tailf:info
            "A.B.C.D;;IPv4 address in ITR-RLOC field of map-request";
        }
      }
      leaf ipv6-local-locator {
        tailf:cli-drop-node-name;
        type inet:ipv6-address {
          tailf:info
            "X:X:X:X::X;;IPv6 address in ITR-RLOC field of map-request";
        }
      }
    }
  }

  grouping ncs_rpc_notif_router-lisp-af6-common-grouping {
    leaf map-request-source {
      tailf:info
        "Configures inner header source address in Map-Request message";
      type inet:ipv6-address {
        tailf:info
          "X:X:X:X::X;;IPv6 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv6-local-locator {
        tailf:cli-drop-node-name;
        tailf:cli-optional-in-sequence;
        type inet:ipv6-address {
          tailf:info
            "X:X:X:X::X;;IPv6 address in ITR-RLOC field of map-request";
        }
      }
      leaf ipv4-local-locator {
        tailf:cli-drop-node-name;
        type inet:ipv4-address {
          tailf:info
            "A.B.C.D;;IPv4 address in ITR-RLOC field of map-request";
        }
      }
    }
  }

  grouping ncs_rpc_notif_router-lisp-af-common-grouping {
    leaf map-cache-limit {
      tailf:info
        "Configures maximum size of map-cache";
      type uint32 {
        tailf:info
          "<0-100000>;;Maximum number of map-cache entries";
        range "0..100000";
      }
    }
    container map-cache-persistent {
      tailf:info
        "Dump map-cache onto flash, making it persistent across reboots";
      tailf:cli-show-no;
      presence "true";
      leaf interval {
        tailf:info
          "Interval in minutes of how often the map-cache is saved";
        type uint16 {
          tailf:info
            "<1-1440>;;Interval in minutes, default 60";
          range "1..1440";
        }
      }
    }
    leaf proxy-etr {
      tailf:info
        "Configures a LISP Proxy Engress Tunnel Router (PETR)";
      tailf:cli-full-command;
      type empty;
    }
    list use-petr {
      tailf:info
        "Encapsulate to Proxy ETR when matching forward-native entry";
      tailf:cli-suppress-mode;
      tailf:cli-delete-when-empty;
      tailf:cli-compact-syntax;
      tailf:cli-sequence-commands;
      key "address";
      leaf address {
        type union {
          type inet:ipv4-address {
            tailf:info
              "A.B.C.D;;IPv4 locator address of PETR";
          }
          type inet:ipv6-address {
            tailf:info
              "X:X:X:X::X;;IPv6 locator address of PETR";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
          range "0..100";
        }
      }
    }
  }

  grouping ncs_rpc_notif_router-lisp-af-grouping {
    leaf map-server {
      tailf:info
        "Configures a LISP Map Server (MS)";
      type empty;
    }
    leaf map-resolver {
      tailf:info
        "Configures a LISP Map Resolver (MR)";
      type empty;
    }
    container itr {
      tailf:info
        "Configures a LISP Ingress Tunnel Router (ITR)";
      tailf:cli-display-separated;
      presence "true";
      list map-resolver {
        tailf:cli-suppress-mode;
        tailf:cli-delete-when-empty;
        key "address";
        leaf address {
          type union {
            type inet:ipv4-address {
              tailf:info
                "IPv4 Address of map resolver";
            }
            type inet:ipv6-address {
              tailf:info
                "IPv6 Address of map resolver";
            }
          }
        }
      }
    }
    container etr {
      tailf:info
        "Configures a LISP Egress Tunnel Router (ETR)";
      tailf:cli-display-separated;
      presence "true";
      list map-server {
        tailf:cli-suppress-mode;
        tailf:cli-delete-when-empty;
        tailf:cli-incomplete-command;
        key "address";
        leaf address {
          type union {
            type inet:ipv4-address {
              tailf:info
                "IPv4 Address of map server";
            }
            type inet:ipv6-address {
              tailf:info
                "IPv6 Address of map server";
            }
          }
        }
        container key {
          tailf:info
            "Authentication key used with map server";
          tailf:cli-compact-syntax;
          tailf:cli-sequence-commands {
            tailf:cli-reset-siblings;
          }
          leaf encryption {
            tailf:cli-drop-node-name;
            tailf:cli-incomplete-command;
            tailf:cli-optional-in-sequence;
            type enumeration {
              enum "0" {
                tailf:info
                  "Specifies an UNENCRYPTED password will follow";
              }
              enum "6" {
                tailf:info
                  "Specifies an ENCRYPTED password will follow";
              }
            }
          }
          leaf key {
            tailf:cli-drop-node-name;
            tailf:cli-multi-value;
            type string {
              tailf:info
                "LINE;;The UNENCRYPTED (cleartext) password";
            }
          }
        }
      }
    }
  }

  grouping ncs_rpc_notif_router-lisp-eid-table-grouping {
    leaf instance-id {
      tailf:info
        "EID instance-ID";
      tailf:cli-hide-in-submode;
      mandatory true;
      type uint32 {
        tailf:info
          "<0-16777214>;;Instance-ID";
        range "0..16777214";
      }
    }
    list map-cache {
      tailf:cli-suppress-mode;
      tailf:cli-delete-when-empty;
      tailf:cli-compact-syntax;
      tailf:cli-sequence-commands;
      tailf:cli-incomplete-command;
      key "prefix";
      leaf prefix {
        type union {
          type ios:ipv4-prefix {
            tailf:info
              "A.B.C.D/nn;;IPv4 EID-prefix for RLOC static mapping";
          }
          type ios:ipv6-prefix {
            tailf:info
              "X:X:X:X::X/<0-128>;;IPv6 EID-prefix for RLOC static mapping";
          }
        }
      }
      choice map-cache-choice {
        case locator {
          leaf locator {
            tailf:cli-drop-node-name;
            tailf:cli-incomplete-command;
            type union {
              type inet:ipv4-address {
                tailf:info
                  "A.B.C.D;;IPv4 Address of loopback or other ETR interface";
              }
              type inet:ipv6-address {
                tailf:info
                  "X:X:X:X::X;;IPv6 Address of loopback or other ETR interface";
              }
            }
          }
          leaf priority {
            tailf:info
              "Lower priority Locator takes preference";
            tailf:cli-incomplete-command;
            type uint8 {
              tailf:info
                "<0-255>;;Lower priority Locator takes preference";
            }
          }
          leaf weight {
            tailf:info
              "Traffic load-spreading among Locators";
            type uint8 {
              tailf:info
                "<0-100>;;Relative weight of locator";
              range "0..100";
            }
          }
        }
        leaf map-request {
          tailf:info
            "Send Map-Request for LISP destination EID";
          tailf:cli-full-command;
          type empty;
        }
        leaf native-forward {
          tailf:info
            "Natively forward packets that match this map-cache entry";
          tailf:cli-full-command;
          type empty;
        }
        leaf drop {
          tailf:info
            "Drop packets that match this map-cache entry";
          tailf:cli-full-command;
          type empty;
        }
      }
    }
    list database-mapping {
      tailf:info
        "Configures Locator addresses for an ETR";
      tailf:cli-incomplete-command;
      tailf:cli-suppress-mode;
      tailf:cli-delete-when-empty;
      tailf:cli-compact-syntax;
      tailf:cli-sequence-commands;
      key "prefix";
      max-elements 100;
      leaf prefix {
        type union {
          type ios:ipv4-prefix {
            tailf:info
              "A.B.C.D/nn;;EID-prefix to advertise locators for (max 100 prefixes)";
          }
          type ios:ipv6-prefix {
            tailf:info
              "X:X:X:X::X/<0-128>;;EID-prefix to advertise locators for (max 100 prefixes)";
          }
        }
      }
      choice rloc-choice {
        leaf ipv4-address {
          tailf:cli-drop-node-name;
          tailf:cli-incomplete-command;
          type inet:ipv4-address {
            tailf:info
              "A.B.C.D;;IPv4 Address of loopback or other ETR interface";
          }
        }
        container IPv4-interface {
          tailf:info
            "Use IPv4 address of interface as locator";
          tailf:cli-flatten-container;
          tailf:cli-compact-syntax;
          tailf:cli-incomplete-command;
          uses ncs_rpc_notif_interface-name-grouping;
        }
        container IPv6-interface {
          tailf:info
            "Use IPv6 address of interface as locator";
          tailf:cli-flatten-container;
          tailf:cli-compact-syntax;
          tailf:cli-incomplete-command;
          uses ncs_rpc_notif_interface-name-grouping;
        }
        leaf ipv6-address {
          tailf:cli-drop-node-name;
          tailf:cli-incomplete-command;
          type inet:ipv6-address {
            tailf:info
              "X:X:X:X::X;;IPv6 Address of loopback or other ETR interface";
          }
        }
        leaf auto-discover-rlocs {
          tailf:info
            "Auto discover locators registered by other xTRs";
          tailf:cli-full-command;
          type empty;
        }
        leaf locator-set {
          tailf:info
            "Use locators defined by locator-set";
          tailf:cli-full-command;
          type string;
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
        }
      }
    }
    container loc-reach-algorithm {
      tailf:info
        "Configure locator reachability algorithm";
      leaf lsb-reports {
        tailf:info
          "Configure data packet LSB report handling";
        type enumeration {
          enum "ignore" {
            tailf:info
              "Ignore data packet LSB reports";
          }
        }
      }
      leaf rloc-probing {
        tailf:info
          "Probe high priority RLOCs with Map-Requests as last resort";
        type empty;
      }
    }
    container ipv4 {
      tailf:info
        "IPv4 address family";
      uses ncs_rpc_notif_router-lisp-af-common-grouping;
      uses ncs_rpc_notif_router-lisp-af4-common-grouping;
    }
    container ipv6 {
      tailf:info
        "IPv6 address family";
      uses ncs_rpc_notif_router-lisp-af-common-grouping;
      uses ncs_rpc_notif_router-lisp-af6-common-grouping;
    }
  }

  grouping ncs_rpc_notif_router-lisp-grouping {
    list locator-set {
      tailf:info
        "Configure a named locator set";
      tailf:cli-mode-name "config-router-lisp-locator-set";
      tailf:cli-full-command;
      key "name";
      leaf name {
        type string {
          tailf:info
            "Configure a named locator set";
        }
      }
      list IPv4-address {
        tailf:cli-drop-node-name;
        tailf:cli-suppress-mode;
        tailf:cli-delete-when-empty;
        tailf:cli-compact-syntax;
        tailf:cli-sequence-commands;
        tailf:cli-incomplete-command;
        key "name";
        leaf name {
          type inet:ipv4-address {
            tailf:info
              "A.B.C.D;;IP address";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-address {
        tailf:cli-drop-node-name;
        tailf:cli-suppress-mode;
        tailf:cli-delete-when-empty;
        tailf:cli-compact-syntax;
        tailf:cli-sequence-commands;
        tailf:cli-incomplete-command;
        key "name";
        leaf name {
          type inet:ipv6-address {
            tailf:info
              "X:X:X:X::X;;Address of loopback or other ETR interface";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv4-interface {
        tailf:info
          "Use IPv4 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-interface {
        tailf:info
          "Use IPv6 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
    }
    container map-request {
      tailf:info
        "Configure map-request handling";
      leaf itr-rlocs {
        tailf:info
          "Configure to use the specified RLOC set as ITR RLOC in map-request";
        type string {
          tailf:info
            "WORD;;Existing locator set";
        }
        tailf:non-strict-leafref {
          path "../../locator-set/name";
        }
      }
    }
    container eid-table {
      tailf:info
        "Configure an EID instance for a VRF";
      list default-vrf {
        tailf:cli-drop-node-name;
        tailf:cli-mode-name "config-router-lisp-eid-table";
        key "name";
        leaf name {
          type enumeration {
            enum "default" {
              tailf:info
                "Default VRF";
            }
          }
        }
        uses ncs_rpc_notif_router-lisp-eid-table-grouping;
      }
      list vrf {
        tailf:cli-mode-name "config-router-lisp-eid-table";
        key "name";
        leaf name {
          type string {
            tailf:info
              "WORD;;VRF name";
          }
        }
        uses ncs_rpc_notif_router-lisp-eid-table-grouping;
      }
    }
    list site {
      tailf:info
        "Configure a LISP site on a map server (MS)";
      tailf:cli-mode-name "config-router-lisp-site";
      tailf:cli-full-command;
      key "name";
      leaf name {
        type string {
          tailf:info
            "WORD;;The site name";
        }
      }
      leaf description {
        tailf:info
          "Provide a description string for the LISP site";
        tailf:cli-multi-value;
        type string {
          tailf:info
            "LINE;;Site description";
        }
      }
      container authentication-key {
        tailf:info
          "Authentication key used by LISP site";
        tailf:cli-compact-syntax;
        tailf:cli-sequence-commands {
          tailf:cli-reset-siblings;
        }
        leaf encryption {
          tailf:cli-drop-node-name;
          tailf:cli-incomplete-command;
          tailf:cli-optional-in-sequence;
          type enumeration {
            enum "0" {
              tailf:info
                "Specifies an UNENCRYPTED password will follow";
            }
            enum "6" {
              tailf:info
                "Specifies an ENCRYPTED password will follow";
            }
          }
        }
        leaf key {
          tailf:cli-drop-node-name;
          tailf:cli-multi-value;
          type string {
            tailf:info
              "LINE;;The UNENCRYPTED (cleartext) password";
          }
        }
      }
      list eid-prefix {
        tailf:info
          "Site EID address prefix";
        tailf:cli-suppress-mode;
        tailf:cli-delete-when-empty;
        tailf:cli-compact-syntax;
        key "prefix";
        leaf prefix {
          type union {
            type ios:ipv4-prefix {
              tailf:info
                "A.B.C.D/nn;;IPv4 EID prefix belonging to the SITE";
            }
            type ios:ipv6-prefix {
              tailf:info
                "X:X:X:X::X/<0-128>;;IPv6 EID prefix belonging to the SITE";
            }
          }
        }
      }
      container eid-prefix-instance {
        tailf:cli-drop-node-name;
        list eid-prefix {
          tailf:cli-suppress-mode;
          tailf:cli-delete-when-empty;
          tailf:cli-compact-syntax;
          key "instance-id prefix";
          leaf instance-id {
            tailf:info
              "EID instance-ID";
            tailf:cli-expose-key-name;
            type uint32 {
              tailf:info
                "<1-16777214>;;Instance-ID";
              range "1..16777214";
            }
          }
          leaf prefix {
            type union {
              type ios:ipv4-prefix {
                tailf:info
                  "A.B.C.D/nn;;IPv4 EID prefix belonging to the SITE";
              }
              type ios:ipv6-prefix {
                tailf:info
                  "X:X:X:X::X/<0-128>;;IPv6 EID prefix belonging to the SITE";
              }
            }
          }
        }
      }
    }
    container ipv4 {
      tailf:info
        "IPv4 address family";
      uses ncs_rpc_notif_router-lisp-af-grouping;
      uses ncs_rpc_notif_router-lisp-af-common-grouping;
      uses ncs_rpc_notif_router-lisp-af4-common-grouping;
    }
    container ipv6 {
      tailf:info
        "IPv6 address family";
      uses ncs_rpc_notif_router-lisp-af-grouping;
      uses ncs_rpc_notif_router-lisp-af-common-grouping;
      uses ncs_rpc_notif_router-lisp-af6-common-grouping;
    }
  }

  grouping ncs_rpc_notif_ip-nat-inside-souce-static-grouping {
    leaf extendable {
      tailf:info
        "Extend this translation when used";
      tailf:cli-optional-in-sequence;
      type empty;
    }
    leaf no-alias {
      tailf:info
        "Do not create an alias for the global address";
      tailf:cli-optional-in-sequence;
      type empty;
    }
    leaf no-payload {
      tailf:info
        "No translation of embedded address/port in the payload";
      tailf:cli-optional-in-sequence;
      type empty;
    }
    leaf route-map {
      tailf:info
        "Specify route-map";
      tailf:cli-optional-in-sequence;
      type string {
        tailf:info
          "WORD;;Route-map name";
      }
    }
    leaf reversible {
      when '../route-map' {
        tailf:xpath-root 3;
      }
      tailf:cli-optional-in-sequence;
      type empty;
    }
    leaf redundancy {
      tailf:info
        "NAT redundancy operation";
      tailf:cli-optional-in-sequence;
      type union {
        type uint8 {
          tailf:info
            "<1-2>;IP redundancy ID";
        }
        type string {
          tailf:info
            "WORD;;IP redundancy name";
        }
      }
    }
    leaf mapping-id {
      when '../redundancy' {
        tailf:xpath-root 3;
      }
      tailf:info
        "Associate a mapping id to this mapping";
      tailf:cli-optional-in-sequence;
      type uint32 {
        tailf:info
          "<1-2147483647>;;Stateful NAT mapping id";
        range "1..2147483647";
      }
    }
    leaf vrf {
      tailf:info
        "Specify vrf";
      tailf:cli-optional-in-sequence;
      tailf:cli-diff-dependency "/ios:ip/vrf" {
        tailf:xpath-root 3;
      }
      tailf:cli-diff-dependency "/ios:vrf/definition" {
        tailf:xpath-root 3;
      }
      type string {
        tailf:info
          "WORD;;vrf name";
      }
    }
    leaf match-in-vrf {
      when '../vrf' {
        tailf:xpath-root 3;
      }
      tailf:info
        "Match incoming vrf";
      tailf:cli-optional-in-sequence;
      type empty;
    }
    leaf forced {
      tailf:info
        "Delete this entry and its children, even if in use";
      tailf:cli-optional-in-sequence;
      type empty;
    }
    leaf overload {
      tailf:info
        "Overload an address translation";
      type empty;
    }
  }

  grouping ncs_rpc_notif_ip-nat-inside-grouping {
    choice pool-or-interface {
      case pool-choice {
        leaf pool {
          tailf:info
            "Name pool of global addresses";
          type string;
          // NCS drop tailf-common:non-strict-leafref statement
        }
        leaf redundancy {
          tailf:info
            "NAT redundancy operation";
          tailf:cli-optional-in-sequence;
          type uint8 {
            tailf:info
              "<1-2>;;IP redundancy ID";
            range "1..2";
          }
        }
        leaf mapping-id {
          tailf:info
            "Associate a mapping id to this mapping";
          tailf:cli-optional-in-sequence;
          type uint32 {
            tailf:info
              "<1-2147483647>;;Stateful NAT mapping id";
            range "1..2147483647";
          }
        }
      }
      case interface-choice {
        container interface {
          tailf:info
            "Specify interface for global address";
          tailf:cli-flatten-container;
          tailf:cli-compact-syntax;
          uses ncs_rpc_notif_interface-name-grouping;
        }
      }
    }
    leaf no-payload {
      tailf:info
        "No translation of embedded address/port in the payload";
      tailf:cli-optional-in-sequence;
      type empty;
    }
    leaf reversible {
      tailf:cli-optional-in-sequence;
      type empty;
    }
    leaf vrf {
      tailf:info
        "Specify vrf";
      tailf:cli-optional-in-sequence;
      tailf:cli-diff-dependency "/ios:ip/vrf" {
        tailf:xpath-root 3;
      }
      tailf:cli-diff-dependency "/ios:vrf/definition" {
        tailf:xpath-root 3;
      }
      type string {
        tailf:info
          "WORD;;vrf name";
      }
    }
    leaf match-in-vrf {
      when '../vrf' {
        tailf:xpath-root 3;
      }
      tailf:info
        "Match incoming vrf";
      tailf:cli-optional-in-sequence;
      type empty;
    }
    leaf overload {
      tailf:info
        "Overload an address translation";
      tailf:cli-optional-in-sequence;
      type empty;
    }
    leaf oer {
      tailf:info
        "Use with vtemplate only. On new translation, if OER BR is UP, OER will select IP from outgoing Interface. All packets matching translation are forwarded over Interface for duration of translation.";
      type empty;
    }
  }

  grouping ncs_rpc_notif_mobile-ip-spi-grouping {
    choice spi-type-choice {
      leaf hex {
        tailf:cli-drop-node-name;
        type string {
          tailf:info
            "<100-FFFFFFFF>;;SPI hex value";
        }
      }
      leaf decimal {
        tailf:info
          "decimal Security parameter index - bidirectional";
        type uint32 {
          tailf:info
            "<256-4294967295>;;SPI decimal value";
          range "256..4294967295";
        }
      }
    }
  }

  grouping ncs_rpc_notif_interface-xconnect-grouping {
    choice xconnect-choice {
      container xconnect {
        tailf:cli-break-sequence-commands;
        tailf:cli-add-mode;
        tailf:cli-mode-name "config-xconn";
        tailf:cli-compact-syntax;
        tailf:cli-sequence-commands;
        tailf:cli-incomplete-command;
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure L2TP session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          type string {
            tailf:info
              "WORD;;Pseudowire-class name";
          }
        }
        leaf pw-type {
          tailf:info
            "MPLS Pseudo-wire Type";
          tailf:cli-optional-in-sequence;
          tailf:cli-hide-in-submode;
          type uint8 {
            tailf:info
              "<4-5>;;Type-5 : Ethernet Port, Type-4 : Ethernet VLAN";
            range "4..5";
          }
        }
        leaf sequencing {
          tailf:info
            "Configure sequencing options for xconnect";
          tailf:cli-full-command;
          tailf:cli-hide-in-submode;
          when "../encapsulation = 'l2tpv3'" {
            tailf:xpath-root 3;
          }
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              type string {
                tailf:info
                  "Optional Pseudowire-class to use for backup pseudowire";
              }
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-sequence-commands;
          tailf:cli-compact-syntax;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            type string {
              tailf:info
                "WORD;;Pseudowire-class name";
            }
          }
        }
      }
    }
  }

  grouping ncs_rpc_notif_ip-pim-grouping {
    container ssm {
      tailf:info
        "Configure Source Specific Multicast";
      choice ip-pim-ssm-choice {
        leaf default {
          tailf:info
            "Use 232/8 group range for SSM";
          type empty;
        }
        leaf range {
          tailf:info
            "ACL for group range to be used for SSM";
          type union {
            type uint16 {
              tailf:info
                "<1-99>;;Access list number";
              range "1..99";
            }
            type string {
              tailf:info
                "WORD;;IP named access list";
              pattern '[a-zA-Z].*';
            }
          }
        }
      }
    }
    list bsr-candidate {
      tailf:info
        "Candidate bootstrap router (candidate BSR)";
      tailf:cli-suppress-mode;
      tailf:cli-delete-when-empty;
      tailf:cli-compact-syntax;
      key "name";
      leaf name {
        type string {
          tailf:info
            "WORD;;Interface name";
        }
      }
      leaf hash-mask-length {
        tailf:cli-drop-node-name;
        type uint8 {
          tailf:info
            "<0-32>;;Hash Mask length for RP selection";
          range "0..32";
        }
      }
      leaf priority {
        tailf:cli-drop-node-name;
        type uint8 {
          tailf:info
            "<0-255>;;Priority value for candidate bootstrap router";
        }
      }
    }
    container rp-address {
      tailf:info
        "PIM RP-address (Rendezvous Point)";
      tailf:cli-compact-syntax;
      tailf:cli-sequence-commands {
        tailf:cli-reset-siblings;
      }
      leaf address {
        tailf:cli-drop-node-name;
        type inet:ipv4-address {
          tailf:info
            "A.B.C.D;;IP address of Rendezvous-point for group";
        }
      }
      leaf access-list {
        tailf:cli-drop-node-name;
        tailf:cli-optional-in-sequence;
        type std-acl-type;
      }
      leaf override {
        tailf:info
          "Overrides dynamically learnt RP mappings";
        type empty;
      }
    }
    list rp-candidate {
      tailf:info
        "To be a PIMv2 RP candidate";
      tailf:cli-suppress-mode;
      tailf:cli-delete-when-empty;
      tailf:cli-compact-syntax;
      key "name";
      leaf name {
        type string {
          tailf:info
            "WORD;;Interface name";
        }
      }
      leaf bidir {
        type empty;
      }
      leaf group-list {
        tailf:info
          "group-list";
        type union {
          type uint8 {
            tailf:info
              "<1-99>;;Access-list reference for group prefixes";
            range "1..99";
          }
          type string {
            tailf:info
              "WORD;;Named access list";
          }
        }
      }
      leaf interval {
        tailf:info
          "RP candidate advertisement interval";
        type uint16 {
          tailf:info
            "<1-16383>;;number of seconds";
          range "1..16383";
        }
      }
      leaf priority {
        tailf:info
          "RP candidate priority";
        type uint8 {
          tailf:info
            "<0-255>;;Priority value";
        }
      }
    }
  }

  grouping ncs_rpc_notif_event-manager-applet-event-grouping {
    container none {
      tailf:info
        "Manually run policy event";
      leaf maxrun {
        tailf:info
          "Maximum runtime of applet";
        type uint32 {
          tailf:info
            "<0-31536000>;;Enter seconds[.milliseconds] value";
        }
      }
    }
    container snmp-notification {
      tailf:info
        "SNMP Notification Event";
      tailf:cli-compact-syntax;
      tailf:cli-reset-container;
      leaf oid {
        tailf:info
          "Object ID of data element";
        type string {
          tailf:info
            "WORD;;OID string";
        }
      }
      leaf oid-val {
        tailf:info
          "Comparison value";
        type string {
          tailf:info
            "WORD;;Comparision value";
        }
      }
      leaf op {
        tailf:info
          "Operator";
        type operator-type;
      }
      leaf src-ip-address {
        tailf:info
          "Source ip address";
        type union {
          type inet:ipv4-address {
            tailf:info
              "A.B.C.D;;Source ip address value";
          }
          type inet:ipv6-address {
            tailf:info
              "X:X:X:X::X;;Source ip address value";
          }
        }
      }
      leaf dest-ip-address {
        tailf:info
          "Destination ip address";
        type union {
          type inet:ipv4-address {
            tailf:info
              "A.B.C.D;;Destination ip address value";
          }
          type inet:ipv6-address {
            tailf:info
              "X:X:X:X::X;;Destination ip address value";
          }
        }
      }
    }
    container syslog {
      tailf:info
        "Syslog event";
      leaf pattern {
        tailf:info
          "Pattern match string for the entire message";
        type string {
          tailf:info
            "WORD;;Pattern match string for the entire message";
        }
      }
    }
    container cli {
      tailf:info
        "CLI event";
      tailf:cli-compact-syntax;
      container pattern {
        tailf:info
          "CLI command pattern match";
        tailf:cli-compact-syntax;
        tailf:cli-sequence-commands {
          tailf:cli-reset-siblings;
        }
        leaf regular-expression {
          tailf:cli-drop-node-name;
          type string {
            tailf:info
              "WORD;;Pattern match string";
          }
        }
        leaf sync {
          tailf:info
            "CLI and EEM policy execution sync or async";
          type enumeration {
            enum "no" {
              tailf:info
                "Policy and CLI will run asynchronously";
            }
            enum "yes" {
              tailf:info
                "Run policy and the result determines whether to run CLI";
            }
          }
        }
      }
    }
    container track {
      tailf:info
        "Tracking object event";
      tailf:cli-compact-syntax;
      tailf:cli-sequence-commands;
      leaf object-number {
        tailf:cli-drop-node-name;
        type uint16 {
          tailf:info
            "<1-500>;;Tracking object number";
        }
      }
      leaf state {
        tailf:info
          "State of tracking object";
        tailf:cli-optional-in-sequence;
        type enumeration {
          enum "any" {
            tailf:info
              "Any state";
          }
          enum "down" {
            tailf:info
              "Down state";
          }
          enum "up" {
            tailf:info
              "Up state";
          }
        }
      }
      leaf maxrun {
        tailf:info
          "Maximum runtime of applet";
        type uint32 {
          tailf:info
            "<0-31536000>;;Enter seconds[.milliseconds] value";
          range "0..31536000";
        }
      }
    }
  }

  grouping ncs_rpc_notif_vrf-route-target-grouping {
    list export {
      tailf:info
        "Export Target-VPN community";
      tailf:cli-suppress-mode;
      tailf:cli-delete-when-empty;
      key "asn-ip";
      leaf asn-ip {
        type asn-ip-type {
          tailf:info
            "ASN:nn or IP-address:nn;;Target VPN Extended Community";
        }
      }
    }
    list import {
      tailf:info
        "Import Target-VPN community";
      tailf:cli-suppress-mode;
      tailf:cli-delete-when-empty;
      key "asn-ip";
      leaf asn-ip {
        type asn-ip-type {
          tailf:info
            "ASN:nn or IP-address:nn;;Target VPN Extended Community";
        }
      }
    }
  }

  grouping ncs_rpc_notif_vrf-definition-af-grouping {
    container export {
      tailf:info
        "VRF export";
      leaf map {
        tailf:info
          "Route-map based VRF export";
        type string {
          tailf:info
            "WORD;;Route-map reference";
        }
      }
    }
    container route-target {
      tailf:info
        "Specify Target VPN Extended Communities";
      uses ncs_rpc_notif_vrf-route-target-grouping;
    }
    container maximum {
      tailf:info
        "Set a limit";
      container routes {
        tailf:info
          "Maximum number of routes allowed in this routing table";
        tailf:cli-compact-syntax;
        tailf:cli-sequence-commands {
          tailf:cli-reset-siblings;
        }
        leaf limit {
          tailf:cli-drop-node-name;
          tailf:cli-incomplete-command;
          type uint32 {
            tailf:info
              "<1-4294967294>;;Maximum number of routes allowed";
          }
        }
        choice action {
          case a {
            leaf warning-only {
              tailf:info
                "Only give a warning message if limit is exceeded";
              type empty;
            }
          }
          case b {
            leaf warn-threshold {
              tailf:cli-drop-node-name;
              type uint8 {
                tailf:info
                  "<1-100>;;Threshold value (%) at which to generate a warning msg";
                range "1..100";
              }
            }
            leaf reinstall {
              tailf:info
                "Reinstall previous rejected route due to over maximum route limit";
              type uint8 {
                tailf:info
                  "<1-100>;;Threshold value (%) at which to reinstall routes back to VRF";
                range "1..100";
              }
            }
          }
        }
      }
    }
  }

  grouping ncs_rpc_notif_snmp-server-host-grouping {
    leaf message-type {
      tailf:cli-optional-in-sequence;
      tailf:cli-drop-node-name;
      tailf:cli-incomplete-command;
      type enumeration {
        enum "informs" {
          tailf:info
            "Send Inform messages to this host";
        }
        enum "traps" {
          tailf:info
            "Send Trap messages to this host";
        }
      }
      default "traps";
    }
    container version {
      tailf:info
        "SNMP version to use for notification messages";
      tailf:cli-optional-in-sequence;
      tailf:cli-flatten-container;
      tailf:cli-compact-syntax;
      tailf:cli-incomplete-command;
      leaf version {
        tailf:cli-drop-node-name;
        type enumeration {
          enum "1" {
            tailf:info
              "Use SNMPv1";
          }
          enum "2c" {
            tailf:info
              "Use SNMPv2c";
          }
          enum "3" {
            tailf:info
              "Use SNMPv3";
          }
        }
      }
      leaf security-level {
        tailf:cli-drop-node-name;
        when "../version = '3'" {
          tailf:xpath-root 3;
        }
        type enumeration {
          enum "auth" {
            tailf:info
              "Use the SNMPv3 authNoPriv Security Level";
          }
          enum "noauth" {
            tailf:info
              "Use the SNMPv3 noAuthNoPriv Security Level";
          }
          enum "priv" {
            tailf:info
              "Use the SNMPv3 authPriv Security Level";
          }
        }
      }
    }
    leaf community-string {
      tailf:cli-drop-node-name;
      tailf:cli-disallow-value "version|informs|traps|vrf";
      type string {
        tailf:info
          "WORD;;SNMPv1/v2c community string or SNMPv3 user name";
      }
    }
    leaf-list allowed-traps {
      tailf:cli-drop-node-name;
      tailf:cli-flat-list-syntax {
        tailf:cli-replace-all;
      }
      type enumeration {
        enum "aaa_server" {
          tailf:info
            "Allow SNMP AAA traps";
        }
        enum "alarms" {
          tailf:info
            "Allow SNMP alarms traps";
        }
        enum "atm" {
          tailf:info
            "Allow SNMP atm traps";
        }
        enum "bfd" {
          tailf:info
            "Allow SNMP BFD traps";
        }
        enum "bgp" {
          tailf:info
            "Allow BGP state change traps";
        }
        enum "bstun" {
          tailf:info
            "Allow bstun event traps";
        }
        enum "bulkstat" {
          tailf:info
            "Allow Data-Collection-MIB traps";
        }
        enum "cable" {
          tailf:info
            "Allow SNMP cable traps";
        }
        enum "call-home" {
          tailf:info
            "Allow SNMP CISCO-CALLHOME-MIB traps";
        }
        enum "casa" {
          tailf:info
            "Allow casa event traps";
        }
        enum "cef" {
          tailf:info
            "Allows cef traps";
        }
        enum "cnpd" {
          tailf:info
            "Allow NBAR Protocol Discovery traps";
        }
        enum "config" {
          tailf:info
            "Allow SNMP config traps";
        }
        enum "config-copy" {
          tailf:info
            "Allow SNMP config-copy traps";
        }
        enum "config-ctid" {
          tailf:info
            "Allow SNMP config-ctid traps";
        }
        enum "cpu" {
          tailf:info
            "Allow cpu related traps";
        }
        enum "dhcp" {
          tailf:info
            "Allow dhcp traps";
        }
        enum "dlsw" {
          tailf:info
            "Allow dlsw traps";
        }
        enum "ds1" {
          tailf:info
            "Allow SNMP ds1 traps";
        }
        enum "dsp" {
          tailf:info
            "Allow SNMP DSP traps";
        }
        enum "dspu" {
          tailf:info
            "Allow dspu event traps";
        }
        enum "eigrp" {
          tailf:info
            "Allow SNMP EIGRP traps";
        }
        enum "entity" {
          tailf:info
            "Allow SNMP entity traps";
        }
        enum "entity-diag" {
          tailf:info
            "Allow SNMP CISCO-ENTITY-DIAG-MIB traps";
        }
        enum "entity-qfp" {
          tailf:info
            "Allow SNMP CISCO-ENTITY-QFP-MIB traps";
        }
        enum "entity-state" {
          tailf:info
            "Allow ENTITY-STATE-MIB traps";
        }
        enum "envmon" {
          tailf:info
            "Allow environmental monitor traps";
        }
        enum "ethernet-cfm" {
          tailf:info
            "Allow SNMP Ethernet CFM traps";
        }
        enum "evc" {
          tailf:info
            "Allow SNMP EVC traps";
        }
        enum "event-manager" {
          tailf:info
            "Allow SNMP Embedded Event Manager traps";
        }
        enum "firewall" {
          tailf:info
            "Allow SNMP Firewall traps";
        }
        enum "flash" {
          tailf:info
            "Allow SNMP FLASH traps";
        }
        enum "flowmon" {
          tailf:info
            "Allow SNMP flow monitor notifications";
        }
        enum "frame-relay" {
          tailf:info
            "Allow SNMP frame-relay traps";
        }
        enum "fru-ctrl" {
          tailf:info
            "Allow entity FRU control traps";
        }
        enum "gdoi" {
          tailf:info
            "Allows gdoi traps";
        }
        enum "hsrp" {
          tailf:info
            "Allow SNMP HSRP traps";
        }
        enum "iplocalpool" {
          tailf:info
            "Allow SNMP IP Local Pool traps";
        }
        enum "ipmulticast" {
          tailf:info
            "Allow SNMP ipmulticast traps";
        }
        enum "ipsec" {
          tailf:info
            "Allow SNMP IPsec traps";
        }
        enum "ipsla" {
          tailf:info
            "Allow SNMP Host IP SLA traps";
        }
        enum "isakmp" {
          tailf:info
            "Allow SNMP ISAKMP traps";
        }
        enum "isg-mib" {
          tailf:info
            "Allow SNMP isgmib traps";
        }
        enum "isis" {
          tailf:info
            "Allow IS-IS traps";
        }
        enum "l2tun-pseudowire-status" {
          tailf:info
            "Allow SNMP L2 pseudowire status traps";
        }
        enum "l2tun-session" {
          tailf:info
            "Allow SNMP L2 session traps";
        }
        enum "license" {
          tailf:info
            "Allow license traps";
        }
        enum "memory" {
          tailf:info
            "Allow SNMP Mempool traps";
        }
        enum "mpls-fast-reroute" {
          tailf:info
            "Allow SNMP MPLS traffic engineering fast reroute traps";
        }
        enum "mpls-ldp" {
          tailf:info
            "Allow SNMP MPLS label distribution protocol traps";
        }
        enum "mpls-traffic-eng" {
          tailf:info
            "Allow SNMP MPLS traffic engineering traps";
        }
        enum "mpls-vpn" {
          tailf:info
            "Allow SNMP MPLS Virtual Private Network traps";
        }
        enum "msdp" {
          tailf:info
            "Allow SNMP MSDP traps";
        }
        enum "mvpn" {
          tailf:info
            "Allow Multicast Virtual Private Network traps";
        }
        enum "nhrp" {
          tailf:info
            "Allow SNMP NHRP traps";
        }
        enum "ospf" {
          tailf:info
            "Allow OSPF traps";
        }
        enum "ospfv3" {
          tailf:info
            "Allow OSPFv3 traps";
        }
        enum "pfr" {
          tailf:info
            "Allow SNMP PfR traps";
        }
        enum "pim" {
          tailf:info
            "Allow SNMP PIM traps";
        }
        enum "pw-vc" {
          tailf:info
            "Allow SNMP Pseudowire VC traps";
        }
        enum "resource-policy" {
          tailf:info
            "Enable CISCO-ERM-MIB notifications";
        }
        enum "rf" {
          tailf:info
            "Allow all SNMP traps defined in CISCO-RF-MIB";
        }
        enum "rsrb" {
          tailf:info
            "Allow rsrb event traps";
        }
        enum "rsvp" {
          tailf:info
            "Allow RSVP flow change traps";
        }
        enum "sdlc" {
          tailf:info
            "Allow sdlc event traps";
        }
        enum "sdllc" {
          tailf:info
            "Allow sdllc event traps";
        }
        enum "snmp" {
          tailf:info
            "Allow SNMP-type notifications";
        }
        enum "sonet" {
          tailf:info
            "Allow SNMP SONET traps";
        }
        enum "srp" {
          tailf:info
            "Allow SRP protocol traps";
        }
        enum "stun" {
          tailf:info
            "Allow stun event traps";
        }
        enum "syslog" {
          tailf:info
            "Allow SNMP syslog traps";
        }
        enum "trustsec-sxp" {
          tailf:info
            "Allow SNMP CISCO-TRUSTSEC-SXP-MIB traps";
        }
        enum "tty" {
          tailf:info
            "Allow TCP connection traps";
        }
        enum "udp-port" {
          tailf:info
            "The notification host's UDP port number (default port 162)";
        }
        enum "voice" {
          tailf:info
            "Allow SNMP Voice traps";
        }
        enum "vrfmib" {
          tailf:info
            "Allow SNMP vrfmib traps";
        }
        enum "vrrp" {
          tailf:info
            "Allow SNMP vrrp traps";
        }
        enum "x25" {
          tailf:info
            "Allow x25 event traps";
        }
      }
    }
  }

  grouping ncs_rpc_notif_ip-sla-proto-grouping {
    leaf tos {
      tailf:cli-break-sequence-commands;
      tailf:info
        "Type Of Service";
      type uint8 {
        tailf:info
          "<0-255>;;Type of Service Value";
      }
    }
    leaf verify-data {
      tailf:info
        "Verify data";
      type empty;
    }
    leaf data-pattern {
      tailf:info
        "Data Pattern";
      type string {
        tailf:info
          "WORD;;Data Pattern in Hex";
        pattern '[a-fA-F0-9].*';
      }
    }
    leaf vrf {
      tailf:info
        "Configure IP SLAs for a VPN Routing/Forwarding instance";
      tailf:cli-diff-dependency "/ios:ip/vrf" {
        tailf:xpath-root 3;
      }
      tailf:cli-diff-dependency "/ios:vrf/definition" {
        tailf:xpath-root 3;
      }
      type string {
        tailf:info
          "WORD;;VRF name";
      }
    }
    leaf owner {
      tailf:info
        "Owner of Entry";
      tailf:cli-multi-value;
      tailf:cli-full-command;
      type string {
        tailf:info
          "LINE;;Owner String";
      }
    }
    leaf tag {
      tailf:info
        "User defined tag";
      tailf:cli-multi-value;
      tailf:cli-full-command;
      type string {
        tailf:info
          "LINE;;Tag string";
      }
    }
    leaf frequency {
      tailf:info
        "Frequency of an operation";
      type uint32 {
        tailf:info
          "<1-604800>;;Frequency in seconds (default 60)";
        range "1..604800";
      }
      default "60";
    }
    leaf timeout {
      tailf:info
        "Timeout of an operation";
      type uint32 {
        tailf:info
          "<0-604800000>;;Timeout in milliseconds";
        range "0..604800000";
      }
    }
    leaf threshold {
      tailf:info
        "Operation threshold in milliseconds";
      type uint16 {
        tailf:info
          "<0-60000>;;Millisecond threshold value";
        range "0..60000";
      }
    }
    container history {
      tailf:info
        "History and Distribution Data";
      leaf hours-of-statistics-kept {
        tailf:info
          "Maximum number of statistics hour groups to capture";
        type uint8 {
          tailf:info
            "<0-25>;;Hour groups size value (default 2)";
          range "0..25";
        }
        default "2";
      }
      leaf distributions-of-statistics-kept {
        tailf:info
          "Maximum number of statistics distribution buckets to capture";
        type uint8 {
          tailf:info
            "<1-20>;;Distribution bucket size value (default 1)";
          range "1..20";
        }
        default "1";
      }
      leaf statistics-distribution-interval {
        tailf:info
          "Statistics distribution interval size";
        type uint8 {
          tailf:info
            "<1-100>;;Distribution interval value (default 20)";
          range "1..100";
        }
        default "20";
      }
      leaf lives-kept {
        tailf:info
          "Maximum number of history lives to collect";
        type uint8 {
          tailf:info
            "<0-2>;;Life size value (default 0)";
          range "0..2";
        }
        default "0";
      }
      leaf buckets-kept {
        tailf:info
          "Maximum number of history buckets to collect";
        type uint8 {
          tailf:info
            "<1-60>;;Bucket size value (default 15)";
          range "1..60";
        }
        default "15";
      }
      leaf filter {
        tailf:info
          "Add operation to History when...";
        type enumeration {
          enum "all" {
            tailf:info
              "Collect every operation in History";
          }
          enum "failures" {
            tailf:info
              "Collect operations that fail in History";
          }
          enum "none" {
            tailf:info
              "Shutoff History collection";
          }
          enum "overThreshold" {
            tailf:info
              "Collect operations that are over threshold in History";
          }
        }
      }
      container enhanced {
        tailf:info
          "Enable enhanced history collection";
        tailf:cli-compact-syntax;
        tailf:cli-sequence-commands;
        leaf interval {
          tailf:info
            "Aggregation interval";
          tailf:cli-incomplete-command;
          type uint16 {
            tailf:info
              "<1-3600>;;Interval in seconds";
            range "1..3600";
          }
        }
        leaf buckets {
          tailf:info
            "Number of buckets to collect data";
          type uint8 {
            tailf:info
              "<1-100>;;Number of buckets";
            range "1..100";
          }
        }
      }
    }
  }

  grouping ncs_rpc_notif_aaa-authentication-method-grouping {
    leaf cache {
      tailf:info
        "Use Cached-group";
      type aaa-group-type;
    }
    leaf group {
      tailf:info
        "Use Server-group";
      type aaa-group-type;
    }
    leaf krb5 {
      tailf:info
        "Use Kerberos 5 authentication.";
      type empty;
    }
    leaf local {
      tailf:info
        "Use local username authentication.";
      type empty;
    }
    leaf line {
      tailf:info
        "Use line password for authentication.";
      type empty;
    }
    leaf enable {
      tailf:info
        "Use enable password for authentication.";
      type empty;
    }
    leaf none {
      tailf:info
        "NO authentication.";
      tailf:cli-full-command;
      type empty;
    }
  }

  grouping ncs_rpc_notif_aaa-authorization-method-grouping {
    leaf cache {
      tailf:info
        "Use Cached-group";
      type aaa-group-type;
    }
    leaf group {
      tailf:info
        "Use server-group.";
      type aaa-group-type;
    }
    leaf krb5-instance {
      tailf:info
        "Use Kerberos instance privilege maps.";
      type empty;
    }
    leaf if-authenticated {
      tailf:info
        "Succeed if user has authenticated.";
      type empty;
    }
    leaf local {
      tailf:info
        "Use local database.";
      type empty;
    }
    leaf none {
      tailf:info
        "No authorization (always succeeds).";
      tailf:cli-full-command;
      type empty;
    }
  }

  grouping ncs_rpc_notif_aaa-accounting-method-grouping {
    leaf action-type {
      tailf:cli-drop-node-name;
      type enumeration {
        enum "none" {
          tailf:info
            "No accounting.";
        }
        enum "start-stop" {
          tailf:info
            "Record start and stop without waiting";
        }
        enum "stop-only" {
          tailf:info
            "Record stop when service terminates.";
        }
      }
    }
    leaf broadcast {
      tailf:info
        "Use Broadcast for Accounting";
      tailf:cli-optional-in-sequence;
      tailf:cli-incomplete-command;
      type empty;
    }
    leaf group {
      tailf:info
        "Use Server-group";
      type aaa-group-type;
    }
  }

  grouping ncs_rpc_notif_cable-modulation-profile-grouping {
    leaf fec-tbytes {
      tailf:cli-drop-node-name;
      tailf:cli-incomplete-command;
      type uint8 {
        tailf:info
          "<0-16>;;FEC tbytes";
      }
    }
    leaf fec-len {
      tailf:cli-drop-node-name;
      tailf:cli-incomplete-command;
      type uint8 {
        tailf:info
          "<16-253>;;FEC codeword length in k bytes";
      }
    }
    leaf burst-len {
      tailf:cli-drop-node-name;
      tailf:cli-incomplete-command;
      type uint8 {
        tailf:info
          "<0-255>;;max burst size in minislots";
      }
    }
    leaf guard-t {
      tailf:cli-drop-node-name;
      tailf:cli-incomplete-command;
      type uint8 {
        tailf:info
          "<0-255>;;guard time in symbols";
      }
    }
    leaf mod {
      tailf:cli-drop-node-name;
      tailf:cli-incomplete-command;
      type enumeration {
        enum "8qam" {
          tailf:info
            "8-QAM modulation";
        }
        enum "16qam" {
          tailf:info
            "16-QAM modulation";
        }
        enum "32qam" {
          tailf:info
            "32-QAM modulation";
        }
        enum "64qam" {
          tailf:info
            "64-QAM modulation";
        }
        enum "qpsk" {
          tailf:info
            "qpsk modulation";
        }
      }
    }
    leaf scrambler {
      tailf:cli-drop-node-name;
      tailf:cli-incomplete-command;
      type enumeration {
        enum "no-scrambler" {
          tailf:info
            "scrambler disabled";
        }
        enum "scrambler" {
          tailf:info
            "scrambler enabled";
        }
      }
    }
    leaf seed {
      when "../scrambler = 'scrambler'" {
        tailf:xpath-root 3;
        tailf:dependency "../scrambler";
      }
      tailf:cli-drop-node-name;
      tailf:cli-incomplete-command;
      type string {
        tailf:info
          "<0x0-0x7FFF>;;scrambler seed in hex";
      }
    }
    leaf diff {
      tailf:cli-drop-node-name;
      tailf:cli-incomplete-command;
      type enumeration {
        enum "diff" {
          tailf:info
            "diff encoding enabled";
        }
        enum "no-diff" {
          tailf:info
            "diff encoding disabled";
        }
      }
    }
    leaf pre-len {
      tailf:cli-drop-node-name;
      tailf:cli-incomplete-command;
      type uint16 {
        tailf:info
          "<4-1536>;;preamble length in bits";
      }
    }
    leaf last-cw {
      tailf:cli-drop-node-name;
      type enumeration {
        enum "fixed" {
          tailf:info
            "fixed codeword";
        }
        enum "shortened" {
          tailf:info
            "shortened codeword";
        }
      }
    }
    leaf preamble {
      tailf:cli-drop-node-name;
      type enumeration {
        enum "qpsk0" {
          tailf:info
            "QPSK0 preamble";
        }
        enum "qpsk1" {
          tailf:info
            "QPSK1 preamble";
        }
      }
    }
    leaf rs-interleave-depth {
      tailf:cli-drop-node-name;
      type uint8 {
        tailf:info
          "<0-114>;;RS interleave depth";
      }
    }
    leaf rs-interleave-block {
      tailf:cli-drop-node-name;
      type uint16 {
        tailf:info
          "<18-2048>;;RS interleave block size";
      }
    }
  }

  grouping ncs_rpc_notif_cable-load-balance-docsis-group-grouping {
    leaf restricted {
      tailf:info
        "Set load balance group as restricted";
      type empty;
    }
    container downstream {
      tailf:info
        "Set downstream RF channels";
      tailf:cli-compact-syntax;
      tailf:cli-sequence-commands;
      leaf Modular-Cable {
        tailf:info
          "Modular cable";
        tailf:cli-incomplete-command;
        type string {
          tailf:info
            "<slot>/<card>/<port>;;Enter slot/subslot/bay";
        }
      }
      leaf rf-channel {
        tailf:info
          "RF channel";
        type string {
          tailf:info
            "<grouplist>;;List of port numbers and number ranges";
        }
      }
    }
    container upstream {
      tailf:info
        "Set upstream channels";
      tailf:cli-compact-syntax;
      tailf:cli-sequence-commands;
      leaf Cable {
        tailf:info
          "CMTS interface";
        tailf:cli-allow-join-with-value {
          tailf:cli-display-joined;
        }
        tailf:cli-incomplete-command;
        type string {
          tailf:info
            "<slot>/<card>/<port>;;Enter slot/subslot/port";
        }
      }
      leaf upstream-list {
        tailf:cli-drop-node-name;
        type string {
          tailf:info
            "<grouplist>;;List of Ranges for upstream channels <0-7>";
        }
      }
    }
    container method {
      tailf:info
        "Set load balancing type/method";
      container utilization {
        tailf:info
          "Interface utilization";
        presence "true";
      }
    }
    container threshold {
      tailf:info
        "Load balancing threshold in %";
      container load {
        tailf:info
          "Interface load threshold settings";
        leaf percentage {
          tailf:cli-drop-node-name;
          type uint8 {
            tailf:info
              "<1-100>;;Threshold value in %";
            range "1..100";
          }
        }
        leaf minimum {
          tailf:info
            "Set minimum number of modems/flows difference before loadbalancing starts";
          type uint8 {
            tailf:info
              "<1-100>;;Minimum number of modems/flows";
            range "1..100";
          }
        }
      }
      leaf stability {
        tailf:info
          "Threshold for stability detection";
        type uint8 {
          tailf:info
            "<0-100>;;Stability condition detection threshold in %";
          range "0..100";
        }
      }
    }
    leaf policy {
      tailf:info
        "Set load balancing policy";
      type enumeration {
        tailf:info
          "pure-ds-load;;Do not count US load when calculating DS utilization";
        enum "pcmm" {
          tailf:info
            "Enable balancing of modems with active PCMM service flows";
        }
        enum "pure-ds-load" {
          tailf:info
            "Do not count US load when calculating DS utilization";
        }
        enum "ugs" {
          tailf:info
            "Enable balancing of modems with active UGS service flows";
        }
        enum "us-across-ds" {
          tailf:info
            "Load balancing on US groups across DS, DS method will be ignored";
        }
      }
    }
    leaf interval {
      tailf:info
        "Set interface polling interval";
      type uint16 {
        tailf:info
          "<1-1000>;;Interface polling interval in seconds";
        range "1..1000";
      }
    }
    container init-tech-list {
      tailf:info
        "Set DCC initialization technique list";
      tailf:cli-compact-syntax;
      tailf:cli-sequence-commands {
        tailf:cli-reset-all-siblings;
      }
      leaf grouplist {
        tailf:cli-drop-node-name;
        type string {
          tailf:info
            "<grouplist> ";
        }
      }
      leaf ucc {
        tailf:info
          "Allow the use of UCC in upstream load balancing";
        type empty;
      }
    }
    leaf docsis-policy {
      tailf:info
        "Enter load balance group policy";
      type uint32 {
        tailf:info
          "<0-4294967295>;;Load balance group policy number";
        range "0..4294967295";
      }
    }
    list tag {
      tailf:info
        "Add tag to load balancing group";
      tailf:cli-suppress-mode;
      tailf:cli-delete-when-empty;
      key "name";
      leaf name {
        type string {
          tailf:info
            "WORD;;tag name";
        }
      }
    }
  }

  grouping ncs_rpc_notif_facility-alarm-grouping {
    container major {
      tailf:info
        "Major warning threshold";
      leaf temperature {
        tailf:cli-drop-node-name;
        type uint8 {
          tailf:info
            "<20-100>;;<##> threshold temperature (degrees C)";
          range "20..100";
        }
      }
    }
    container minor {
      tailf:info
        "Minor warning threshold";
      leaf temperature {
        tailf:cli-drop-node-name;
        type uint8 {
          tailf:info
            "<20-100>;;<##> threshold temperature (degrees C)";
          range "20..100";
        }
      }
    }
    container critical {
      tailf:info
        "Critical warning threshold";
      leaf exceed-action {
        tailf:info
          "Critical outlet temperature exceed action";
        tailf:cli-full-command;
        type enumeration {
          enum "shutdown" {
            tailf:info
              "Auto-shutdown when critical outlet temperature is exceeded";
          }
        }
      }
      leaf temperature {
        tailf:cli-drop-node-name;
        tailf:cli-full-command;
        type uint8 {
          tailf:info
            "<1-255>;;<##> threshold temperature (degrees C)";
          range "1..255";
        }
      }
    }
  }

  grouping ncs_rpc_notif_process-cpu-threshold-grouping {
    leaf rising {
      tailf:info
        "rising threshold";
      tailf:cli-incomplete-command;
      type uint8 {
        tailf:info
          "<1-100>";
        range "1..100";
      }
    }
    leaf interval {
      tailf:info
        "observation interval";
      type uint32 {
        tailf:info
          "<5-86400>";
        range "5..86400";
      }
    }
    leaf falling {
      tailf:info
        "falling threshold ";
      type uint8 {
        tailf:info
          "<1-100>";
        range "1..100";
      }
    }
    container falling-interval {
      tailf:cli-flatten-container;
      tailf:cli-drop-node-name;
      leaf interval {
        tailf:info
          "observation interval";
        type uint32 {
          tailf:info
            "<5-86400>";
          range "5..86400";
        }
      }
    }
  }

  grouping ncs_rpc_notif_cable-submgmt-default-filter-group-grouping {
    leaf upstream {
      tailf:info
        "Default Upstream Group";
      type uint8 {
        tailf:info
          "<1-254>;;Group ID";
        range "1..254";
      }
    }
    leaf downstream {
      tailf:info
        "Default Downstream Group";
      type uint8 {
        tailf:info
          "<1-254>;;Group ID";
        range "1..254";
      }
    }
  }

  grouping ncs_rpc_notif_storm-control-level-bps-pps-grouping {
    container level-bps-pps {
      tailf:cli-drop-node-name;
      container level {
        tailf:info
          "Set storm suppression level on this interface";
        choice level-choice {
          leaf bps {
            tailf:info
              "Enter suppression level in bits per second";
            type string {
              tailf:info
                "<0.0 - 10000000000.0>[k|m|g];;Enter rising threshold";
            }
          }
          leaf pps {
            tailf:info
              "Enter suppression level in packets per second";
            type string {
              tailf:info
                "<0.0 - 10000000000.0>[k|m|g];;Enter rising threshold";
            }
          }
        }
      }
    }
  }

  grouping ncs_rpc_notif_service-policy-grouping {
    leaf input {
      tailf:info
        "Assign input policy-map";
      type string {
        tailf:info
          "WORD;;input Policy-map name";
      }
      // NCS drop tailf-common:non-strict-leafref statement
    }
    leaf output {
      tailf:info
        "Assign output policy-map";
      type string {
        tailf:info
          "WORD;;output Policy-map name";
      }
      // NCS drop tailf-common:non-strict-leafref statement
    }
  }

  grouping redistribute-ospf-match-grouping {
    leaf internal {
      tailf:info
        "Redistribute OSPF internal routes";
      type empty;
    }
    container external-1 {
      tailf:cli-drop-node-name;
      tailf:cli-flatten-container;
      leaf external {
        tailf:info
          "Redistribute OSPF external routes";
        type enumeration {
          enum "1" {
            tailf:info
              "Redistribute external type 1 routes";
          }
        }
      }
    }
    container external-2 {
      tailf:cli-drop-node-name;
      tailf:cli-flatten-container;
      leaf external {
        tailf:info
          "Redistribute OSPF external routes";
        type enumeration {
          enum "2" {
            tailf:info
              "Redistribute external type 2 routes";
          }
        }
      }
    }
    container nssa-external-1 {
      tailf:cli-drop-node-name;
      tailf:cli-flatten-container;
      leaf nssa-external {
        tailf:info
          "Redistribute OSPF NSSA external routes";
        type enumeration {
          enum "1" {
            tailf:info
              "Redistribute NSSA external type 1 routes";
          }
        }
      }
    }
    container nssa-external-2 {
      tailf:cli-drop-node-name;
      tailf:cli-flatten-container;
      leaf nssa-external {
        tailf:info
          "Redistribute OSPF NSSA external routes";
        type enumeration {
          enum "2" {
            tailf:info
              "Redistribute NSSA external type 2 routes";
          }
        }
      }
    }
  }

  grouping police-action-transmit-grouping {
    leaf transmit {
      tailf:info
        "transmit packet";
      type empty;
    }
  }

  grouping police-action-drop-grouping {
    leaf drop {
      tailf:info
        "drop packet";
      type empty;
    }
  }

  grouping police-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type cos_value-type;
        }
      }
    }
    container conform-set-cos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type dscp-type;
        }
      }
    }
    container conform-set-dscp-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-dscp-transmit {
          tailf:info
            "set dscp and send it";
          type dscp-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-imposition-transmit {
          tailf:info
            "set exp at tag imposition and send it";
          type exp_value-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-topmost-transmit {
          tailf:info
            "set exp on topmost label and send it";
          type exp_value-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type prec_value-type;
        }
      }
    }
    container conform-set-prec-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-prec-transmit {
          tailf:info
            "rewrite packet precedence and send it";
          type prec_value-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type qos_value-type;
        }
      }
    }
    container conform-set-qos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-qos-transmit {
          tailf:info
            "set qos-group and send it";
          type qos_value-type;
        }
        leaf table {
          tailf:info
            "Specify table-map";
          type string {
            tailf:info
              "WORD;;table-map name";
          }
          tailf:non-strict-leafref {
            path "/ncs:devices/ncs:device/ncs:config/ios:table-map/name" {
              tailf:xpath-root 3;
            }
          }
        }
      }
    }
    container conform-transmit {
      tailf:cli-no-keyword;
      tailf:cli-drop-node-name;
      tailf:cli-flatten-container;
      container conform-action {
        tailf:info
          "action when rate is less than conform burst";
        tailf:cli-flatten-container;
        uses police-action-transmit-grouping;
      }
    }
    container conform-drop {
      tailf:cli-no-keyword;
      tailf:cli-drop-node-name;
      tailf:cli-flatten-container;
      container conform-action {
        tailf:info
          "action when rate is less than conform burst";
        tailf:cli-flatten-container;
        uses police-action-drop-grouping;
      }
    }
  }

  grouping police-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type cos_value-type;
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type qos_value-type;
        }
      }
    }
    container exceed-transmit {
      tailf:cli-no-keyword;
      tailf:cli-drop-node-name;
      tailf:cli-flatten-container;
      container exceed-action {
        tailf:info
          "action when rate is within conform and conform + exceed burst";
        tailf:cli-flatten-container;
        uses police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses police-action-drop-grouping;
      }
    }
  }

  grouping police-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses police-action-drop-grouping;
      }
    }
  }

  grouping police-action-grouping {
    container actions {
      tailf:cli-break-sequence-commands;
      tailf:cli-no-keyword;
      tailf:cli-drop-node-name;
      tailf:cli-flatten-container;
      uses police-conform-action-grouping;
      uses police-exceed-action-grouping;
      uses police-violate-action-grouping;
    }
  }

  grouping password-grouping {
    container password-container {
      tailf:cli-drop-node-name;
      tailf:cli-flatten-container;
      tailf:cli-compact-syntax;
      tailf:cli-sequence-commands;
      leaf encryption {
        tailf:cli-drop-node-name;
        tailf:cli-optional-in-sequence;
        tailf:cli-incomplete-command;
        type uint8 {
          tailf:info
            "<0-7>;;Encryption type (0 to disable encryption, 7 for proprietary)";
          range "0..7";
        }
      }
      leaf password {
        tailf:cli-drop-node-name;
        type string {
          tailf:info
            "LINE;;The password";
          pattern '([1-680-9a-zA-Z].*)|(0.+)|(7.+)';
        }
      }
    }
  }

  grouping crypto-key-grouping {
    leaf encryption {
      tailf:cli-drop-node-name;
      tailf:cli-incomplete-command;
      tailf:cli-optional-in-sequence;
      type enumeration {
        enum "0" {
          tailf:info
            "Specifies an UNENCRYPTED password will follow";
        }
        enum "6" {
          tailf:info
            "Specifies an ENCRYPTED password will follow";
        }
      }
    }
    leaf secret {
      tailf:cli-drop-node-name;
      tailf:cli-full-command;
      type string {
        tailf:info
          "LINE;;The UNENCRYPTED (cleartext) user password";
      }
    }
  }

  grouping distribute-list-content-grouping {
    choice distribute-type {
      case access-list {
        leaf access-list-name {
          tailf:cli-drop-node-name;
          tailf:cli-prefix-key;
          type exp-ip-acl-type;
        }
      }
      case prefix-list-gateway {
        leaf prefix {
          tailf:info
            "Filter prefixes in routing updates";
          tailf:cli-prefix-key;
          tailf:cli-optional-in-sequence;
          type string {
            tailf:info
              "WORD;;Name of an IP prefix-list";
          }
        }
        leaf gateway {
          tailf:info
            "Filtering incoming updates based on gateway";
          tailf:cli-prefix-key;
          tailf:cli-optional-in-sequence;
          type string {
            tailf:info
              "WORD;;Name of an IP prefix-list";
          }
        }
      }
      case route-map {
        leaf routemap {
          tailf:info
            "Filter prefixes based on the route-map";
          tailf:cli-prefix-key;
          type string {
            tailf:info
              "WORD;;route-map name";
          }
        }
      }
    }
  }

  grouping router-distribute-list-grouping {
    list distribute-list {
      tailf:info
        "Filter networks in routing updates";
      tailf:cli-suppress-mode;
      tailf:cli-delete-when-empty;
      tailf:cli-compact-syntax;
      tailf:cli-sequence-commands;
      tailf:cli-remove-before-change;
      key "direction";
      leaf direction {
        type enumeration {
          enum "in" {
            tailf:info
              "Filter incoming routing updates";
          }
          enum "out" {
            tailf:info
              "Filter outgoing routing updates";
          }
        }
      }
      uses distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses distribute-list-content-grouping;
      }
    }
  }

  grouping passive-interface-grouping {
    container passive-interface {
      tailf:info
        "Suppress routing updates on an interface";
      choice passive-interface-choice {
        leaf default {
          tailf:info
            "Suppress routing updates on all interfaces";
          type empty;
        }
        list interface {
          tailf:cli-drop-node-name;
          tailf:cli-suppress-mode;
          tailf:cli-delete-when-empty;
          key "name";
          leaf name {
            type string {
              tailf:info
                "WORD;;Interface name";
            }
          }
        }
      }
    }
    container disable {
      tailf:info
        "Use with 'disable passive-interface' for 'no passive-interface' config";
      when '../passive-interface/default' {
        tailf:xpath-root 3;
      }
      list passive-interface {
        tailf:cli-suppress-mode;
        tailf:cli-delete-when-empty;
        tailf:cli-compact-syntax;
        key "interface";
        leaf interface {
          tailf:cli-multi-word-key;
          type string {
            tailf:info
              "WORD;;Interface name";
          }
        }
      }
    }
  }

  grouping interface-name-grouping {
    choice interface-choice {
      leaf Null {
        tailf:info
          "Null interface";
        tailf:cli-allow-join-with-value {
          tailf:cli-display-joined;
        }
        type uint8 {
          tailf:info
            "<0-0>;;Null interface number";
          range "0";
        }
        tailf:non-strict-leafref {
          path "/ncs:devices/ncs:device/ncs:config/ios:interface/Null/name" {
            tailf:xpath-root 3;
          }
        }
      }
      leaf Loopback {
        tailf:info
          "Loopback interface";
        tailf:cli-allow-join-with-value {
          tailf:cli-display-joined;
        }
        type string {
          tailf:info
            "<0-2147483647>;;Loopback interface number";
          pattern '([0-9.])+';
        }
        tailf:non-strict-leafref {
          path "/ncs:devices/ncs:device/ncs:config/ios:interface/Loopback/name" {
            tailf:xpath-root 3;
          }
        }
      }
      leaf Embedded-Service-Engine {
        tailf:info
          "cisco embedded service engine module";
        tailf:cli-allow-join-with-value {
          tailf:cli-display-joined;
        }
        type string;
        tailf:non-strict-leafref {
          path "/ncs:devices/ncs:device/ncs:config/ios:interface/Embedded-Service-Engine/name" {
            tailf:xpath-root 3;
          }
        }
      }
      leaf Tunnel {
        tailf:info
          "Tunnel interface";
        tailf:cli-allow-join-with-value {
          tailf:cli-display-joined;
        }
        type uint32;
        tailf:non-strict-leafref {
          path "/ncs:devices/ncs:device/ncs:config/ios:interface/Tunnel/name" {
            tailf:xpath-root 3;
          }
        }
      }
      leaf Port-channel {
        tailf:info
          "Ethernet Channel of interfaces";
        tailf:cli-allow-join-with-value {
          tailf:cli-display-joined;
        }
        type uint32;
        tailf:non-strict-leafref {
          path "/ncs:devices/ncs:device/ncs:config/ios:interface/Port-channel/name" {
            tailf:xpath-root 3;
          }
        }
      }
      container Port-channel-subinterface {
        tailf:cli-drop-node-name;
        tailf:cli-flatten-container;
        tailf:cli-compact-syntax;
        leaf Port-channel {
          tailf:cli-allow-join-with-value {
            tailf:cli-display-joined;
          }
          type string {
            pattern '[0-9]+\.[0-9]+';
          }
          tailf:non-strict-leafref {
            path "/ncs:devices/ncs:device/ncs:config/ios:interface/Port-channel-subinterface/Port-channel/name" {
              tailf:xpath-root 3;
            }
          }
        }
      }
      leaf Multilink {
        tailf:info
          "Multilink-group interface";
        tailf:cli-allow-join-with-value {
          tailf:cli-display-joined;
        }
        type uint16 {
          range "1..65535";
        }
        tailf:non-strict-leafref {
          path "/ncs:devices/ncs:device/ncs:config/ios:interface/Multilink/name" {
            tailf:xpath-root 3;
          }
        }
      }
      leaf MFR {
        tailf:info
          "Multilink Frame Relay bundle interface";
        tailf:cli-allow-join-with-value {
          tailf:cli-display-joined;
        }
        type uint32;
        tailf:non-strict-leafref {
          path "/ncs:devices/ncs:device/ncs:config/ios:interface/MFR/name" {
            tailf:xpath-root 3;
          }
        }
      }
      container MFR-subinterface {
        tailf:cli-drop-node-name;
        tailf:cli-flatten-container;
        tailf:cli-compact-syntax;
        leaf MFR {
          tailf:cli-allow-join-with-value {
            tailf:cli-display-joined;
          }
          type string {
            pattern '[0-9]+\.[0-9]+';
          }
          tailf:non-strict-leafref {
            path "/ncs:devices/ncs:device/ncs:config/ios:interface/MFR-subinterface/MFR/name" {
              tailf:xpath-root 3;
            }
          }
        }
      }
      leaf BRI {
        tailf:info
          "ISDN Basic Rate Interface";
        tailf:cli-allow-join-with-value {
          tailf:cli-display-joined;
        }
        type uint16;
        tailf:non-strict-leafref {
          path "/ncs:devices/ncs:device/ncs:config/ios:interface/BRI/name" {
            tailf:xpath-root 3;
          }
        }
      }
      leaf Ethernet {
        tailf:info
          "Ethernet";
        tailf:cli-allow-join-with-value {
          tailf:cli-display-joined;
        }
        type string {
          pattern '[0-9]+.*';
        }
        tailf:non-strict-leafref {
          path "/ncs:devices/ncs:device/ncs:config/ios:interface/Ethernet/name" {
            tailf:xpath-root 3;
          }
        }
      }
      leaf FastEthernet {
        tailf:info
          "FastEthernet IEEE 802.3";
        tailf:cli-allow-join-with-value {
          tailf:cli-display-joined;
        }
        type string;
        tailf:non-strict-leafref {
          path "/ncs:devices/ncs:device/ncs:config/ios:interface/FastEthernet/name" {
            tailf:xpath-root 3;
          }
        }
      }
      leaf GigabitEthernet {
        tailf:info
          "GigabitEthernet IEEE 802.3z";
        tailf:cli-allow-join-with-value {
          tailf:cli-display-joined;
        }
        type string;
        tailf:non-strict-leafref {
          path "/ncs:devices/ncs:device/ncs:config/ios:interface/GigabitEthernet/name" {
            tailf:xpath-root 3;
          }
        }
      }
      leaf TenGigabitEthernet {
        tailf:info
          "Ten Gigabit Ethernet";
        tailf:cli-allow-join-with-value {
          tailf:cli-display-joined;
        }
        type string;
        tailf:non-strict-leafref {
          path "/ncs:devices/ncs:device/ncs:config/ios:interface/TenGigabitEthernet/name" {
            tailf:xpath-root 3;
          }
        }
      }
      leaf BDI {
        tailf:info
          "Bridge-Domain interface";
        tailf:cli-allow-join-with-value {
          tailf:cli-display-joined;
        }
        type uint16 {
          tailf:info
            "<1-4095>;;BDI interface number";
          range "1..4095";
        }
        tailf:non-strict-leafref {
          path "/ncs:devices/ncs:device/ncs:config/ios:interface/BDI/name" {
            tailf:xpath-root 3;
          }
        }
      }
      leaf Cable {
        tailf:info
          "CMTS interface";
        tailf:cli-allow-join-with-value {
          tailf:cli-display-joined;
        }
        type string;
        tailf:non-strict-leafref {
          path "/ncs:devices/ncs:device/ncs:config/ios:interface/Cable/name" {
            tailf:xpath-root 3;
          }
        }
      }
      leaf Modular-Cable {
        tailf:info
          "Modular Cable interface";
        tailf:cli-allow-join-with-value {
          tailf:cli-display-joined;
        }
        type string;
        tailf:non-strict-leafref {
          path "/ncs:devices/ncs:device/ncs:config/ios:interface/Modular-Cable/name" {
            tailf:xpath-root 3;
          }
        }
      }
      leaf Wideband-Cable {
        tailf:info
          "Wideband CMTS interface";
        tailf:cli-allow-join-with-value {
          tailf:cli-display-joined;
        }
        type string;
        tailf:non-strict-leafref {
          path "/ncs:devices/ncs:device/ncs:config/ios:interface/Wideband-Cable/name" {
            tailf:xpath-root 3;
          }
        }
      }
      leaf Bundle {
        tailf:info
          "Virtual Bundle";
        tailf:cli-allow-join-with-value {
          tailf:cli-display-joined;
        }
        type uint8 {
          tailf:info
            "<1-255>;;Bundle interface number";
          range "1..255";
        }
        tailf:non-strict-leafref {
          path "/ncs:devices/ncs:device/ncs:config/ios:interface/Bundle/name" {
            tailf:xpath-root 3;
          }
        }
      }
      leaf Cellular {
        tailf:info
          "Cellular";
        tailf:cli-allow-join-with-value {
          tailf:cli-display-joined;
        }
        type string;
        tailf:non-strict-leafref {
          path "/ncs:devices/ncs:device/ncs:config/ios:interface/Cellular/name" {
            tailf:xpath-root 3;
          }
        }
      }
      leaf Vlan {
        tailf:info
          "Catalyst Vlans";
        tailf:cli-allow-join-with-value {
          tailf:cli-display-joined;
        }
        type uint16 {
          tailf:info
            "<1-4094>;;Vlan interface number";
          range "1..4094";
        }
        tailf:non-strict-leafref {
          path "/ncs:devices/ncs:device/ncs:config/ios:interface/Vlan/name" {
            tailf:xpath-root 3;
          }
        }
      }
      leaf Async {
        tailf:info
          "Async interface";
        tailf:cli-allow-join-with-value {
          tailf:cli-display-joined;
        }
        type uint16;
        tailf:non-strict-leafref {
          path "/ncs:devices/ncs:device/ncs:config/ios:interface/Async/name" {
            tailf:xpath-root 3;
          }
        }
      }
      leaf Group-Async {
        tailf:info
          "Async Group interface";
        tailf:cli-allow-join-with-value {
          tailf:cli-display-joined;
        }
        type uint16;
        tailf:non-strict-leafref {
          path "/ncs:devices/ncs:device/ncs:config/ios:interface/Group-Async/name" {
            tailf:xpath-root 3;
          }
        }
      }
      leaf Serial {
        tailf:info
          "Serial interface";
        tailf:cli-allow-join-with-value {
          tailf:cli-display-joined;
        }
        type string;
        tailf:non-strict-leafref {
          path "/ncs:devices/ncs:device/ncs:config/ios:interface/Serial/name" {
            tailf:xpath-root 3;
          }
        }
      }
      container Serial-subinterface {
        tailf:cli-drop-node-name;
        tailf:cli-flatten-container;
        tailf:cli-compact-syntax;
        leaf Serial {
          tailf:cli-allow-join-with-value {
            tailf:cli-display-joined;
          }
          type string {
            pattern '[0-9]+.*';
          }
          tailf:non-strict-leafref {
            path "/ncs:devices/ncs:device/ncs:config/ios:interface/Serial-subinterface/Serial/name" {
              tailf:xpath-root 3;
            }
          }
        }
      }
      leaf Virtual-Template {
        tailf:info
          "Virtual Template interface";
        tailf:cli-allow-join-with-value {
          tailf:cli-display-joined;
        }
        type uint16 {
          tailf:info
            "<1-4095>;;Virtual-Template interface number";
          range "1..4095";
        }
        tailf:non-strict-leafref {
          path "/ncs:devices/ncs:device/ncs:config/ios:interface/Virtual-Template/name" {
            tailf:xpath-root 3;
          }
        }
      }
      leaf pseudowire {
        tailf:info
          "Pseudowire Interface";
        tailf:cli-allow-join-with-value {
          tailf:cli-display-joined;
        }
        type uint32 {
          tailf:info
            "<1-231072>;;pseudowire interface number";
          range "1..231072";
        }
        tailf:non-strict-leafref {
          path "/ncs:devices/ncs:device/ncs:config/ios:interface/pseudowire/name" {
            tailf:xpath-root 3;
          }
        }
      }
      leaf LISP {
        tailf:info
          "Locator/ID Separation Protocol Virtual Interface";
        tailf:cli-allow-join-with-value {
          tailf:cli-display-joined;
        }
        type uint16 {
          tailf:info
            "<0-1999>;;LISP interface number";
          range "0..1999";
        }
        tailf:non-strict-leafref {
          path "/ncs:devices/ncs:device/ncs:config/ios:interface/LISP/name" {
            tailf:xpath-root 3;
          }
        }
      }
      container LISP-subinterface {
        tailf:cli-drop-node-name;
        tailf:cli-flatten-container;
        tailf:cli-compact-syntax;
        leaf LISP {
          tailf:cli-allow-join-with-value {
            tailf:cli-display-joined;
          }
          type string {
            pattern '[0-9]+\.[0-9]+';
          }
          tailf:non-strict-leafref {
            path "/ncs:devices/ncs:device/ncs:config/ios:interface/LISP-subinterface/LISP/name" {
              tailf:xpath-root 3;
            }
          }
        }
      }
    }
  }

  grouping ip-community-list-standard-grouping {
    container deny {
      tailf:info
        "Specify community to reject";
      tailf:cli-delete-when-empty;
      presence "true";
      list deny-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local\-AS)|(no\-advertise)|(no\-export)|(\d+:\d+)|(\d+))( (internet)|(local\-AS)|(no\-advertise)|(no\-export)|(\d+:\d+)|(\d+))*';
          }
        }
      }
    }
    container permit {
      tailf:info
        "Specify community to accept";
      tailf:cli-delete-when-empty;
      presence "true";
      list permit-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local-AS)|(no-advertise)|(no-export)|(\d+:\d+)|(\d+))( (internet)|(local-AS)|(no-advertise)|(no-export)|(\d+:\d+)|(\d+))*';
          }
        }
      }
    }
  }

  grouping ip-community-list-expanded-grouping {
    container deny {
      tailf:info
        "Specify community to reject";
      tailf:cli-delete-when-empty;
      presence "true";
      list deny-list {
        tailf:cli-drop-node-name;
        tailf:cli-suppress-mode;
        tailf:cli-delete-when-empty;
        key "expr";
        leaf expr {
          tailf:cli-multi-word-key {
            tailf:cli-max-words 10;
          }
          type string {
            tailf:info
              "LINE;;An ordered list as a regular-expression";
          }
        }
      }
    }
    container permit {
      tailf:info
        "Specify community to accept";
      tailf:cli-delete-when-empty;
      presence "true";
      list permit-list {
        tailf:cli-drop-node-name;
        tailf:cli-suppress-mode;
        tailf:cli-delete-when-empty;
        key "expr";
        leaf expr {
          tailf:cli-multi-word-key {
            tailf:cli-max-words 10;
          }
          type string {
            tailf:info
              "LINE;;An ordered list as a regular-expression";
          }
        }
      }
    }
  }

  grouping ip-route-options-grouping {
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf dhcp {
      tailf:info
        "Default Gateway obtained from DHCP";
      tailf:cli-case-insensitive;
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-500>;;tracked object number";
        range "1..500";
      }
    }
  }

  grouping ip-route-grouping {
    list ip-route-interface-forwarding-list {
      tailf:cli-drop-node-name;
      tailf:cli-suppress-mode;
      tailf:cli-delete-when-empty;
      tailf:cli-compact-syntax;
      tailf:cli-sequence-commands {
        tailf:cli-reset-all-siblings;
      }
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ip-route-options-grouping;
    }
    list ip-route-forwarding-list {
      tailf:cli-drop-node-name;
      tailf:cli-suppress-mode;
      tailf:cli-delete-when-empty;
      tailf:cli-compact-syntax;
      tailf:cli-sequence-commands {
        tailf:cli-reset-all-siblings;
      }
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ip-route-options-grouping;
    }
    list ip-route-interface-list {
      tailf:cli-drop-node-name;
      tailf:cli-suppress-mode;
      tailf:cli-delete-when-empty;
      tailf:cli-compact-syntax;
      tailf:cli-sequence-commands {
        tailf:cli-reset-all-siblings;
      }
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-case-insensitive;
        tailf:cli-diff-dependency "/ios:interface" {
          tailf:xpath-root 3;
        }
        type union {
          type string {
            tailf:info
              "WORD;;Interface name";
          }
          type enumeration {
            enum "dhcp" {
              tailf:info
                "Default Gateway obtained from DHCP";
            }
          }
        }
      }
      uses ip-route-options-grouping;
    }
  }

  grouping ipv6-route-options-grouping {
    leaf distance {
      tailf:cli-drop-node-name;
      tailf:cli-break-sequence-commands;
      type uint8 {
        tailf:info
          "<1-254>;;Administrative distance";
        range "1..254";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>;;Tag value";
      }
    }
  }

  grouping ipv6-route-grouping {
    list ipv6-route-interface-destination-list {
      tailf:cli-drop-node-name;
      tailf:cli-suppress-mode;
      tailf:cli-delete-when-empty;
      tailf:cli-compact-syntax;
      tailf:cli-sequence-commands {
        tailf:cli-reset-all-siblings;
      }
      key "prefix interface destination";
      leaf prefix {
        tailf:cli-disallow-value "vrf";
        type ipv6-prefix {
          tailf:info
            "X:X:X:X::X/<0-128>;;IPv6 prefix x:x::y/<z>";
        }
      }
      leaf interface {
        tailf:cli-diff-dependency "/ios:interface" {
          tailf:xpath-root 3;
        }
        type string {
          tailf:info
            "WORD;;Interface name";
        }
      }
      leaf destination {
        type inet:ipv6-address {
          tailf:info
            "X:X:X:X::X;;IPv6 address of next-hop";
        }
      }
      uses ipv6-route-options-grouping;
    }
    list ipv6-route-destination-list {
      tailf:cli-drop-node-name;
      tailf:cli-suppress-mode;
      tailf:cli-delete-when-empty;
      tailf:cli-compact-syntax;
      tailf:cli-sequence-commands {
        tailf:cli-reset-all-siblings;
      }
      key "prefix destination";
      leaf prefix {
        tailf:cli-disallow-value "vrf";
        type ipv6-prefix {
          tailf:info
            "X:X:X:X::X/<0-128>;;IPv6 prefix x:x::y/<z>";
        }
      }
      leaf destination {
        type inet:ipv6-address {
          tailf:info
            "X:X:X:X::X;;IPv6 address of next-hop";
        }
      }
      uses ipv6-route-options-grouping;
    }
    list ipv6-route-interface-list {
      tailf:cli-drop-node-name;
      tailf:cli-suppress-mode;
      tailf:cli-delete-when-empty;
      tailf:cli-compact-syntax;
      tailf:cli-sequence-commands {
        tailf:cli-reset-all-siblings;
      }
      key "prefix interface";
      leaf prefix {
        tailf:cli-disallow-value "vrf";
        type ipv6-prefix {
          tailf:info
            "X:X:X:X::X/<0-128>;;IPv6 prefix x:x::y/<z>";
        }
      }
      leaf interface {
        tailf:cli-diff-dependency "/ios:interface" {
          tailf:xpath-root 3;
        }
        type string {
          tailf:info
            "WORD;;Interface name";
        }
      }
      uses ipv6-route-options-grouping;
    }
  }

  grouping random-detect-grouping {
    leaf min-threshold {
      tailf:cli-drop-node-name;
      tailf:cli-incomplete-command;
      type uint32 {
        tailf:info
          "<1-262143>;;minimum threshold (in packet by default)";
      }
    }
    leaf min-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf max-threshold {
      tailf:cli-drop-node-name;
      type uint32 {
        tailf:info
          "<1-262143>;;maximum threshold (number of packets)";
      }
    }
    leaf max-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf denominator {
      tailf:cli-drop-node-name;
      type uint32 {
        tailf:info
          "<1-65535>;;mark probability denominator";
      }
    }
  }

  grouping class-map-match-grouping {
    container access-group {
      tailf:info
        "Access group";
      leaf index {
        tailf:cli-drop-node-name;
        type uint32 {
          tailf:info
            "<1-2799>;;Access list index";
          range "1..2699";
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      type string {
        tailf:info
          "WORD;;Match class-map name";
      }
      tailf:non-strict-leafref {
        path "/ncs:devices/ncs:device/ncs:config/ios:class-map/name" {
          tailf:xpath-root 3;
        }
      }
    }
    leaf-list cos {
      tailf:info
        "IEEE 802.1Q/ISL class of service/user priority values";
      tailf:cli-flat-list-syntax;
      max-elements 4;
      type uint16 {
        range "0..7";
        tailf:info
          "<0-7>;;Enter up to 4 class-of-service values separated by white-spaces";
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint8 {
        tailf:info
          "<0-7>;;Discard Class value";
        range "0..7";
      }
    }
    leaf-list dscp {
      tailf:info
        "Match DSCP in IP(v4) and IPv6 packets";
      tailf:cli-flat-list-syntax;
      tailf:cli-full-command;
      type dscp-type;
    }
    leaf fr-de {
      tailf:info
        "Match on Frame-relay DE bit";
      type empty;
    }
    leaf-list fr-dlci {
      tailf:info
        "Match on fr-dlci";
      tailf:cli-list-syntax;
      type uint16 {
        tailf:info
          "<16-1007>;;frame-relay dlci number";
        range "16..1007";
      }
    }
    leaf-list input-interface {
      tailf:info
        "Select an input interface to match";
      tailf:cli-list-syntax;
      type string {
        tailf:info
          "WORD;;Interface name";
      }
    }
    container ip {
      tailf:info
        "IP specific values";
      leaf-list dscp {
        tailf:info
          "Match IP DSCP (DiffServ CodePoints)";
        tailf:cli-flat-list-syntax;
        type dscp-type;
      }
      leaf-list precedence {
        tailf:info
          "Match IP precedence";
        tailf:cli-flat-list-syntax;
        type precedence-type;
      }
      list rtp {
        tailf:info
          "Match RTP port nos";
        tailf:cli-suppress-mode;
        tailf:cli-delete-when-empty;
        key "port1 port2";
        leaf port1 {
          type uint16 {
            tailf:info
              "<2000-65535>;;Lower bound of UDP destination port";
            range "2000..65535";
          }
        }
        leaf port2 {
          type uint16 {
            tailf:info
              "<0-16383>;;Range of UDP ports";
            range "0..16383";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            range "0..7";
            tailf:info
              "<0-7>;;Enter up to 8 experimental values separated by white-spaces";
          }
        }
      }
    }
    container packet {
      tailf:info
        "Layer 3 Packet length";
      container length {
        tailf:info
          "Layer 3 Packet length";
        leaf max {
          tailf:info
            "Maximum length of packet";
          type uint16 {
            range "1..2000";
            tailf:info
              "<1-2000>;;Packet length in bytes";
          }
        }
        leaf min {
          tailf:info
            "Minimum length of packet";
          type uint16 {
            range "1..2000";
            tailf:info
              "<1-2000>;;Packet length in bytes";
          }
        }
      }
    }
    leaf-list precedence {
      tailf:info
        "Match Precedence in IP(v4) and IPv6 packets";
      tailf:cli-flat-list-syntax;
      type precedence-type;
    }
    container protocol {
      tailf:info
        "Protocol";
      leaf x802-11-iapp {
        tailf:info
          "IEEE 802.11 WLANs WG IAPP";
        tailf:alt-name "802-11-iapp";
        type empty;
      }
      leaf ace-svr {
        tailf:info
          "ACE Server/Propagation";
        type empty;
      }
      leaf aol {
        tailf:info
          "America-Online Instant Messenger";
        type empty;
      }
      leaf appleqtc {
        tailf:info
          "Apple QuickTime";
        type empty;
      }
      leaf biff {
        tailf:info
          "Bliff mail notification";
        type empty;
      }
      leaf bittorrent {
        tailf:info
          "bittorrent";
        type empty;
      }
      leaf bootpc {
        tailf:info
          "Bootstrap Protocol Client";
        type empty;
      }
      leaf bootps {
        tailf:info
          "Bootstrap Protocol Server";
        type empty;
      }
      leaf cddbp {
        tailf:info
          "CD Database Protocol";
        type empty;
      }
      leaf cifs {
        tailf:info
          "CIFS";
        type empty;
      }
      leaf cisco-fna {
        tailf:info
          "Cisco FNATIVE";
        type empty;
      }
      leaf cisco-net-mgmt {
        tailf:info
          "cisco-net-mgmt";
        type empty;
      }
      leaf cisco-svcs {
        tailf:info
          "cisco license/perf/GDP/X.25/ident svcs";
        type empty;
      }
      leaf cisco-sys {
        tailf:info
          "Cisco SYSMAINT";
        type empty;
      }
      leaf cisco-tdp {
        tailf:info
          "Cisco TDP";
        type empty;
      }
      leaf cisco-tna {
        tailf:info
          "Cisco TNATIVE";
        type empty;
      }
      leaf citriximaclient {
        tailf:info
          "Citrix IMA Client";
        type empty;
      }
      leaf clp {
        tailf:info
          "Cisco Line Protocol";
        type empty;
      }
      leaf creativepartnr {
        tailf:info
          "Creative Partnr";
        type empty;
      }
      leaf creativeserver {
        tailf:info
          "Creative Server";
        type empty;
      }
      leaf daytime {
        tailf:info
          "Daytime (RFC 867)";
        type empty;
      }
      leaf dbase {
        tailf:info
          "dBASE Unix";
        type empty;
      }
      leaf dbcontrol_agent {
        tailf:info
          "Oracle dbControl Agent po";
        type empty;
      }
      leaf ddns-v3 {
        tailf:info
          "Dynamic DNS Version 3";
        type empty;
      }
      leaf dhcp-failover {
        tailf:info
          "DHCP Failover";
        type empty;
      }
      leaf directconnect {
        tailf:info
          "Direct Connect Version 2.0";
        type empty;
      }
      leaf discard {
        tailf:info
          "Discard port";
        type empty;
      }
      leaf dnsix {
        tailf:info
          "DNSIX Securit Attribute Token Map";
        type empty;
      }
      leaf echo {
        tailf:info
          "Echo port";
        type empty;
      }
      leaf entrust-svc-hdlr {
        tailf:info
          "Entrust KM/Admin Service Handler";
        type empty;
      }
      leaf entrust-svcs {
        tailf:info
          "Entrust sps/aaas/aams";
        type empty;
      }
      leaf exec {
        tailf:info
          "Remote Process Execution";
        type empty;
      }
      leaf fcip-port {
        tailf:info
          "FCIP";
        type empty;
      }
      leaf ftps {
        tailf:info
          "FTP over TLS/SSL";
        type empty;
      }
      leaf gdoi {
        tailf:info
          "GDOI";
        type empty;
      }
      leaf giop {
        tailf:info
          "Oracle GIOP/SSL";
        type empty;
      }
      leaf gtpv0 {
        tailf:info
          "GPRS Tunneling Protocol Version 0";
        type empty;
      }
      leaf gtpv1 {
        tailf:info
          "GPRS Tunneling Protocol Version 1";
        type empty;
      }
      leaf h225ras {
        tailf:info
          "H225 RAS over Unicast";
        type empty;
      }
      leaf h323callsigalt {
        tailf:info
          "h323 Call Signal Alternate";
        type empty;
      }
      leaf hp-alarm-mgr {
        tailf:info
          "HP Performance data alarm manager";
        type empty;
      }
      leaf hp-collector {
        tailf:info
          "HP Performance data collector";
        type empty;
      }
      leaf hp-managed-node {
        tailf:info
          "HP Performance data managed node";
        type empty;
      }
      leaf hsrp {
        tailf:info
          "Hot Standby Router Protocol";
        type empty;
      }
      leaf https {
        tailf:info
          "Secure Hypertext Transfer Protocol";
        type empty;
      }
      leaf ica {
        tailf:info
          "ica (Citrix)";
        type empty;
      }
      leaf icabrowser {
        tailf:info
          "icabrowser (Citrix)";
        type empty;
      }
      leaf ident {
        tailf:info
          "Authentication Service";
        type empty;
      }
      leaf igmpv3lite {
        tailf:info
          "IGMP over UDP for SSM";
        type empty;
      }
      leaf imap3 {
        tailf:info
          "Interactive Mail Access Protocol 3";
        type empty;
      }
      leaf imaps {
        tailf:info
          "IMAP over TLS/SSL";
        type empty;
      }
      leaf ipass {
        tailf:info
          "IPASS";
        type empty;
      }
      leaf ipsec-msft {
        tailf:info
          "Microsoft IPsec NAT-T";
        type empty;
      }
      leaf irc-serv {
        tailf:info
          "IRC-SERV";
        type empty;
      }
      leaf ircs {
        tailf:info
          "IRC over TLS/SSL";
        type empty;
      }
      leaf ircu {
        tailf:info
          "IRCU";
        type empty;
      }
      leaf isakmp {
        tailf:info
          "ISAKMP";
        type empty;
      }
      leaf iscsi {
        tailf:info
          "iSCSI";
        type empty;
      }
      leaf iscsi-target {
        tailf:info
          "iSCSI port";
        type empty;
      }
      leaf kermit {
        tailf:info
          "kermit";
        type empty;
      }
      leaf ldap-admin {
        tailf:info
          "LDAP admin server port";
        type empty;
      }
      leaf ldaps {
        tailf:info
          "LDAP over TLS/SSL";
        type empty;
      }
      leaf login {
        tailf:info
          "Remote login";
        type empty;
      }
      leaf lotusmtap {
        tailf:info
          "Lotus Mail Tracking Agent Protocol";
        type empty;
      }
      leaf lotusnote {
        tailf:info
          "Lotus Note";
        type empty;
      }
      leaf microsoft-ds {
        tailf:info
          "Microsoft-DS";
        type empty;
      }
      leaf ms-cluster-net {
        tailf:info
          "MS Cluster Net";
        type empty;
      }
      leaf ms-dotnetster {
        tailf:info
          "Microsoft .NETster Port";
        type empty;
      }
      leaf ms-sna {
        tailf:info
          "Microsoft SNA Server/Base";
        type empty;
      }
      leaf ms-sql {
        tailf:info
          "Microsoft SQL";
        type empty;
      }
      leaf ms-sql-m {
        tailf:info
          "Microsoft SQL Monitor";
        type empty;
      }
      leaf msexch-routing {
        tailf:info
          "Microsoft Exchange Routing";
        type empty;
      }
      leaf msnmsgr {
        tailf:info
          "MSN Instant Messenger";
        type empty;
      }
      leaf msrpc {
        tailf:info
          "Microsoft Remote Procedure Call";
        type empty;
      }
      leaf mysql {
        tailf:info
          "MySQL";
        type empty;
      }
      leaf n2h2server {
        tailf:info
          "N2H2 Filter Service Port";
        type empty;
      }
      leaf ncp {
        tailf:info
          "NCP (Novell)";
        type empty;
      }
      leaf net8-cman {
        tailf:info
          "Oracle Net8 Cman/Admin";
        type empty;
      }
      leaf netbios-dgm {
        tailf:info
          "NETBIOS Datagram Service";
        type empty;
      }
      leaf netbios-ns {
        tailf:info
          "NETBIOS Name Service";
        type empty;
      }
      leaf netbios-ssn {
        tailf:info
          "NETBIOS Session Service";
        type empty;
      }
      leaf netstat {
        tailf:info
          "Variant of systat";
        type empty;
      }
      leaf oem-agent {
        tailf:info
          "OEM Agent (Oracle)";
        type empty;
      }
      leaf oracle {
        tailf:info
          "Oracle";
        type empty;
      }
      leaf oracle-em-vp {
        tailf:info
          "Oracle EM/VP";
        type empty;
      }
      leaf oraclenames {
        tailf:info
          "Oracle Names";
        type empty;
      }
      leaf orasrv {
        tailf:info
          "Oracle SQL*Net v1/v2";
        type empty;
      }
      leaf pcanywheredata {
        tailf:info
          "pcANYWHEREdata";
        type empty;
      }
      leaf pcanywherestat {
        tailf:info
          "pcANYWHEREstat";
        type empty;
      }
      leaf pop3s {
        tailf:info
          "POP3 over TLS/SSL";
        type empty;
      }
      leaf pwdgen {
        tailf:info
          "Password  Generator Protocol";
        type empty;
      }
      leaf qmtp {
        tailf:info
          "Quick Mail Transfer Protocol";
        type empty;
      }
      leaf r-winsock {
        tailf:info
          "remote-winsock";
        type empty;
      }
      leaf radius {
        tailf:info
          "RADIUS & Accounting";
        type empty;
      }
      leaf rdb-dbs-disp {
        tailf:info
          "Oracle RDB";
        type empty;
      }
      leaf realmedia {
        tailf:info
          "RealNetwork's Realmedia Protocol";
        type empty;
      }
      leaf realsecure {
        tailf:info
          "ISS Real Secure Console Service Port";
        type empty;
      }
      leaf router {
        tailf:info
          "Local Routing Process";
        type empty;
      }
      leaf rsvp-encap {
        tailf:info
          "RSVP ENCAPSULATION-1/2";
        type empty;
      }
      leaf rsvp_tunnel {
        tailf:info
          "RSVP Tunnel";
        type empty;
      }
      leaf rtc-pm-port {
        tailf:info
          "Oracle RTC-PM port";
        type empty;
      }
      leaf rtelnet {
        tailf:info
          "Remote Telnet Service";
        type empty;
      }
      leaf send {
        tailf:info
          "SEND";
        type empty;
      }
      leaf shell {
        tailf:info
          "Remote command";
        type empty;
      }
      leaf sip-tls {
        tailf:info
          "SIP-TLS";
        type empty;
      }
      leaf sms {
        tailf:info
          "SMS RCINFO/XFER/CHAT";
        type empty;
      }
      leaf snmptrap {
        tailf:info
          "SNMP Trap";
        type empty;
      }
      leaf sql-net {
        tailf:info
          "SQL-NET";
        type empty;
      }
      leaf sqlserv {
        tailf:info
          "SQL Services";
        type empty;
      }
      leaf sqlsrv {
        tailf:info
          "SQL Service";
        type empty;
      }
      leaf sshell {
        tailf:info
          "SSLshell";
        type empty;
      }
      leaf ssp {
        tailf:info
          "State Sync Protocol";
        type empty;
      }
      leaf syslog-conn {
        tailf:info
          "Reliable Syslog Service";
        type empty;
      }
      leaf tacacs {
        tailf:info
          "Login Host Protocol (TACACS)";
        type empty;
      }
      leaf tacacs-ds {
        tailf:info
          "TACACS-Database Service";
        type empty;
      }
      leaf tarantella {
        tailf:info
          "Tarantella";
        type empty;
      }
      leaf tcp {
        tailf:info
          "TCP";
        type empty;
      }
      leaf telnets {
        tailf:info
          "Telnet over TLS/SSL";
        type empty;
      }
      leaf time {
        tailf:info
          "Time";
        type empty;
      }
      leaf timed {
        tailf:info
          "Time server";
        type empty;
      }
      leaf tr-rsrb {
        tailf:info
          "cisco RSRB";
        type empty;
      }
      leaf ttc {
        tailf:info
          "Oracle TTC/SSL";
        type empty;
      }
      leaf udp {
        tailf:info
          "UDP";
        type empty;
      }
      leaf uucp {
        tailf:info
          "UUCPD/UUCP-RLOGIN";
        type empty;
      }
      leaf vqp {
        tailf:info
          "VQP";
        type empty;
      }
      leaf webster {
        tailf:info
          "Network Disctionary";
        type empty;
      }
      leaf who {
        tailf:info
          "Who's service";
        type empty;
      }
      leaf wins {
        tailf:info
          "Microsoft WINS";
        type empty;
      }
      leaf x11 {
        tailf:info
          "X Window System";
        type empty;
      }
      leaf xdmcp {
        tailf:info
          "XDM Control Protocol";
        type empty;
      }
      leaf ymsgr {
        tailf:info
          "Yahoo! Instant Messenger";
        type empty;
      }
      leaf aarp {
        tailf:info
          "AppleTalk ARP";
        type empty;
      }
      leaf appletalk {
        tailf:info
          "AppleTalk";
        type empty;
      }
      leaf arp {
        tailf:info
          "IP ARP";
        type empty;
      }
      leaf bgp {
        tailf:info
          "Border Gateway Protocol";
        type empty;
      }
      leaf bridge {
        tailf:info
          "Bridging";
        type empty;
      }
      leaf bstun {
        tailf:info
          "Block Serial Tunnel";
        type empty;
      }
      leaf cdp {
        tailf:info
          "Cisco Discovery Protocol";
        type empty;
      }
      container citrix {
        tailf:info
          "Citrix Systems ICA protocol";
        presence "enable citrix system protocol matching";
        leaf ica-tag {
          tailf:info
            "Citrix ICA tag 0-high 1-medium 2-low 3-background";
          type string {
            tailf:info
              "WORD;;Enter a string as the sub-protocol parameter";
          }
        }
      }
      leaf clns {
        tailf:info
          "ISO CLNS";
        type empty;
      }
      leaf clns_es {
        tailf:info
          "ISO CLNS End System";
        type empty;
      }
      leaf clns_is {
        tailf:info
          "ISO CLNS Intermediate System";
        type empty;
      }
      leaf cmns {
        tailf:info
          "ISO CMNS";
        type empty;
      }
      leaf compressedtcp {
        tailf:info
          "Compressed TCP (VJ";
        type empty;
      }
      leaf cuseeme {
        tailf:info
          "CU-SeeMe desktop video conference";
        type empty;
      }
      leaf decnet {
        tailf:info
          "DECnet";
        type empty;
      }
      leaf decnet_node {
        tailf:info
          "DECnet Node";
        type empty;
      }
      leaf decnet_router-l1 {
        tailf:info
          "DECnet Router L1";
        type empty;
      }
      leaf decnet_router-l2 {
        tailf:info
          "DECnet Router L2";
        type empty;
      }
      leaf dhcp {
        tailf:info
          "Dynamic Host Configuration";
        type empty;
      }
      leaf dlsw {
        type empty;
        tailf:info
          "Data Link Switching (Direct encapsulation only";
      }
      leaf dns {
        type empty;
        tailf:info
          "Domain Name Server lookup";
      }
      leaf edonkey {
        type empty;
        tailf:info
          "eDonkey";
      }
      leaf egp {
        type empty;
        tailf:info
          "Exterior Gateway Protocol";
      }
      leaf eigrp {
        type empty;
        tailf:info
          "Enhanced Interior Gateway Routing Protocol";
      }
      leaf exchange {
        type empty;
        tailf:info
          "MS-RPC for Exchange";
      }
      container fasttrack {
        tailf:info
          "FastTrack Traffic - KaZaA, Morpheus, Grokster";
        presence "enable fasttrack matching";
        leaf file-transfer {
          tailf:info
            "File transfer stream";
          type string {
            tailf:info
              "WORD;;Enter a string as the sub-protocol parameter";
          }
        }
      }
      leaf finger {
        type empty;
        tailf:info
          "Finger";
      }
      leaf ftp {
        type empty;
        tailf:info
          "File Transfer Protocol";
      }
      container gnutella {
        tailf:info
          "Gnutella Version2 Traffic - BearShare, Shareeza, Morpheus";
        presence "enable gnutella matching";
        leaf file-transfer {
          tailf:info
            "File transfer stream";
          type string {
            tailf:info
              "WORD;;Enter a string as the sub-protocol parameter";
          }
        }
      }
      leaf gopher {
        type empty;
        tailf:info
          "Gopher";
      }
      leaf gre {
        type empty;
        tailf:info
          "Generic Routing Encapsulation";
      }
      leaf h323 {
        type empty;
        tailf:info
          "H323 Protocol";
      }
      container http {
        tailf:info
          "World Wide Web traffic";
        presence "enable http traffic matching";
        leaf c-header-field {
          tailf:info
            "Client general Header Field";
          type string {
            tailf:info
              "WORD;;Enter a string as the sub-protocol parameter";
          }
        }
        leaf host {
          tailf:info
            "Server Host Name";
          type string {
            tailf:info
              "WORD;;Enter a string as the sub-protocol parameter";
          }
        }
        leaf mime {
          tailf:info
            "Match MIME Type";
          type string {
            tailf:info
              "WORD;;Enter a string as the sub-protocol parameter";
          }
        }
        leaf s-header-field {
          tailf:info
            "Server general Header Field";
          type string {
            tailf:info
              "WORD;;Enter a string as the sub-protocol parameter";
          }
        }
        leaf url {
          tailf:info
            "Match URL String";
          type string {
            tailf:info
              "WORD;;Enter a string as the sub-protocol parameter";
          }
        }
      }
      leaf icmp {
        tailf:info
          "Internet Control Message";
        type empty;
      }
      leaf imap {
        tailf:info
          "Internet Message Access Protocol";
        type empty;
      }
      leaf ip {
        tailf:info
          "IP";
        type empty;
      }
      leaf ipinip {
        tailf:info
          "IP in IP (encapsulation";
        type empty;
      }
      leaf ipsec {
        tailf:info
          "IP Security Protocol (ESP/AH";
        type empty;
      }
      leaf ipv6 {
        tailf:info
          "IPV6";
        type empty;
      }
      leaf ipx {
        tailf:info
          "Novell IPX";
        type empty;
      }
      leaf irc {
        type empty;
        tailf:info
          "Internet Relay Chat";
      }
      container kazaa2 {
        tailf:info
          "Kazaa Version 2";
        presence "enable kazaa version 2 matching";
        leaf file-transfer {
          tailf:info
            "File transfer stream";
          type string {
            tailf:info
              "WORD;;Enter a string as the sub-protocol parameter";
          }
        }
      }
      leaf kerberos {
        tailf:info
          "Kerberos";
        type empty;
      }
      leaf l2tp {
        tailf:info
          "L2F/L2TP tunnel";
        type empty;
      }
      leaf ldap {
        tailf:info
          "Lightweight Directory Access Protocol";
        type empty;
      }
      leaf llc2 {
        tailf:info
          "llc2";
        type empty;
      }
      leaf mgcp {
        tailf:info
          "Media Gateway Control Protocol";
        type empty;
      }
      container napster {
        tailf:info
          "Napster Traffic";
        presence "enable napster matching";
        leaf non-std {
          tailf:info
            "Non-standard port advertizements";
          type empty;
        }
      }
      leaf netbios {
        tailf:info
          "NetBIOS";
        type empty;
      }
      leaf netshow {
        tailf:info
          "Microsoft Netshow";
        type empty;
      }
      leaf nfs {
        tailf:info
          "Network File System";
        type empty;
      }
      leaf nntp {
        tailf:info
          "Network News Transfer Protocol";
        type empty;
      }
      leaf notes {
        tailf:info
          "Lotus Notes(R";
        type empty;
      }
      leaf novadigm {
        tailf:info
          "Novadigm EDM";
        type empty;
      }
      leaf ntp {
        tailf:info
          "Network Time Protocol";
        type empty;
      }
      leaf ospf {
        tailf:info
          "Open Shortest Path First";
        type empty;
      }
      leaf pad {
        tailf:info
          "PAD links";
        type empty;
      }
      leaf pcanywhere {
        tailf:info
          "Symantec pcANYWHERE";
        type empty;
      }
      leaf pop3 {
        tailf:info
          "Post Office Protocol";
        type empty;
      }
      leaf pppoe {
        tailf:info
          "PPP over Ethernet";
        type empty;
      }
      leaf pptp {
        tailf:info
          "Point-to-Point Tunneling Protocol";
        type empty;
      }
      leaf printer {
        tailf:info
          "print spooler/lpd";
        type empty;
      }
      leaf qllc {
        tailf:info
          "qllc protocol";
        type empty;
      }
      leaf rcmd {
        tailf:info
          "BSD r-commands (rsh, rlogin, rexec";
        type empty;
      }
      leaf rip {
        tailf:info
          "Routing Information Protocol";
        type empty;
      }
      leaf rsrb {
        tailf:info
          "Remote Source-Route Bridging";
        type empty;
      }
      leaf rsvp {
        tailf:info
          "Resource Reservation Protocol";
        type empty;
      }
      leaf rtcp {
        tailf:info
          "Real Time Control Protocol";
        type empty;
      }
      container rtp {
        tailf:info
          "Real Time Protocol";
        presence "enable rtp matching";
        leaf audio {
          tailf:info
            "Match voice packets";
          type empty;
        }
        leaf payload-type {
          tailf:info
            "Match an explicit PT";
          type string {
            tailf:info
              "WORD;;Enter a string as the sub-protocol parameter";
          }
        }
        leaf video {
          tailf:info
            "Match video packets";
          type empty;
        }
      }
      leaf rtsp {
        tailf:info
          "Real Time Streaming Protocol";
        type empty;
      }
      leaf secure-ftp {
        tailf:info
          "FTP over TLS/SSL";
        type empty;
      }
      leaf secure-http {
        tailf:info
          "Secured HTTP";
        type empty;
      }
      leaf secure-imap {
        tailf:info
          "Internet Message Access Protocol over TLS/SSL";
        type empty;
      }
      leaf secure-irc {
        tailf:info
          "Internet Relay Chat over TLS/SSL";
        type empty;
      }
      leaf secure-ldap {
        tailf:info
          "Lightweight Directory Access Protocol over TLS/SSL";
        type empty;
      }
      leaf secure-nntp {
        tailf:info
          "Network News Transfer Protocol over TLS/SSL";
        type empty;
      }
      leaf secure-pop3 {
        tailf:info
          "Post Office Protocol over TLS/SSL";
        type empty;
      }
      leaf secure-telnet {
        tailf:info
          "Telnet over TLS/SSL";
        type empty;
      }
      leaf sip {
        tailf:info
          "Session Initiation Protocol";
        type empty;
      }
      leaf skinny {
        tailf:info
          "Skinny Protocol";
        type empty;
      }
      leaf smtp {
        tailf:info
          "Simple Mail Transfer Protocol";
        type empty;
      }
      leaf snapshot {
        tailf:info
          "Snapshot routing support";
        type empty;
      }
      leaf snmp {
        tailf:info
          "Simple Network Management Protocol";
        type empty;
      }
      leaf socks {
        tailf:info
          "SOCKS";
        type empty;
      }
      leaf sqlnet {
        tailf:info
          "SQL*NET for Oracle";
        type empty;
      }
      leaf sqlserver {
        tailf:info
          "MS SQL Server";
        type empty;
      }
      leaf ssh {
        tailf:info
          "Secured Shell";
        type empty;
      }
      leaf streamwork {
        tailf:info
          "Xing Technology StreamWorks player";
        type empty;
      }
      leaf stun {
        tailf:info
          "Serial Tunnel";
        type empty;
      }
      leaf sunrpc {
        tailf:info
          "Sun RPC";
        type empty;
      }
      leaf syslog {
        tailf:info
          "System Logging Utility";
        type empty;
      }
      leaf telnet {
        tailf:info
          "Telnet";
        type empty;
      }
      leaf tftp {
        tailf:info
          "Trivial File Transfer Protocol";
        type empty;
      }
      leaf vdolive {
        tailf:info
          "VDOLive streaming video";
        type empty;
      }
      leaf vofr {
        tailf:info
          "voice over Frame Relay packets";
        type empty;
      }
      leaf winmx {
        tailf:info
          "WinMx file-sharing application";
        type empty;
      }
      leaf xwindows {
        tailf:info
          "X-Windows remote access";
        type empty;
      }
      container attribute {
        tailf:info
          "Attribute based protocol match";
        list category {
          tailf:info
            "Category attribute";
          tailf:cli-suppress-mode;
          tailf:cli-delete-when-empty;
          key "category-type";
          leaf category-type {
            type enumeration {
              enum "voice-and-video" {
                tailf:info
                  "Filter incoming connections";
              }
              enum "database" {
                tailf:info
                  "Filter outgoing connections";
              }
              enum "email" {
                tailf:info
                  "Email related applications";
              }
              enum "browsing" {
                tailf:info
                  "Browsing related applications";
              }
              enum "trojan" {
                tailf:info
                  "Trojan related applications";
              }
              enum "gaming" {
                tailf:info
                  "Gaming related applications";
              }
              enum "anonymizers" {
                tailf:info
                  "Anonymizers applications";
              }
              enum "backup-and-storage" {
                tailf:info
                  "Backup and storage related applications";
              }
              enum "business-and-productivity-tools" {
                tailf:info
                  "Business-and-productivity-tools related applications";
              }
              enum "epayement" {
                tailf:info
                  "Epayement related applications";
              }
              enum "file-sharing" {
                tailf:info
                  "File-sharing related applications";
              }
              enum "industrial-protocols" {
                tailf:info
                  "Industrial-protocols related applications";
              }
              enum "instant-messaging" {
                tailf:info
                  "Instant-messaging related applications";
              }
              enum "inter-process-rpc" {
                tailf:info
                  "Inter-process-rpc related applications";
              }
              enum "internet-security" {
                tailf:info
                  "Internet security related applications";
              }
              enum "layer3-over-ip" {
                tailf:info
                  "Layer3-over-IP related applications";
              }
              enum "location-based-services" {
                tailf:info
                  "Location-based-services related applications";
              }
              enum "net-admin" {
                tailf:info
                  "Net-admin related applications";
              }
              enum "newsgroup" {
                tailf:info
                  "Newsgroup related applications";
              }
              enum "other" {
                tailf:info
                  "Other related applications";
              }
              enum "social-networking" {
                tailf:info
                  "Social-networking related applications";
              }
              enum "software-updates" {
                tailf:info
                  "Software updates and downloads related applications";
              }
            }
          }
        }
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-range-list-syntax;
      type uint16 {
        tailf:info
          "<1-4094>;;VLAN id";
        range "1..4094";
      }
    }
  }

  grouping ip-name-server-grouping {
    list name-server-list {
      tailf:cli-drop-node-name;
      tailf:cli-suppress-mode;
      tailf:cli-delete-when-empty;
      max-elements 6;
      key "address";
      leaf address {
        type union {
          type inet:ipv4-address {
            tailf:info
              "A.B.C.D;;Domain server IP address (maximum of 6)";
          }
          type inet:ipv6-address {
            tailf:info
              "X:X:X:X::X;;Domain server IPv6 address (maximum of 6)";
          }
        }
      }
    }
  }

  grouping ip-host-grouping {
    list host-list {
      tailf:cli-drop-node-name;
      tailf:cli-suppress-mode;
      tailf:cli-delete-when-empty;
      tailf:cli-compact-syntax;
      tailf:cli-sequence-commands;
      tailf:cli-incomplete-command;
      key "hostname";
      leaf hostname {
        tailf:cli-disallow-value "vrf";
        type string {
          tailf:info
            "WORD;;Name of host";
        }
      }
      leaf tcp-port-number {
        tailf:cli-drop-node-name;
        tailf:cli-optional-in-sequence;
        tailf:cli-incomplete-command;
        type uint16 {
          tailf:info
            "<0-65535>;;Default telnet port number";
        }
      }
      leaf-list ip-address1 {
        tailf:cli-drop-node-name;
        tailf:cli-flat-list-syntax;
        type inet:ipv4-address {
          tailf:info
            "A.B.C.D;;Host IP address";
        }
      }
    }
  }

  grouping ip-dhcp-excluded-address-grouping {
    list low-list {
      tailf:cli-drop-node-name;
      tailf:cli-suppress-mode;
      tailf:cli-delete-when-empty;
      key "low";
      leaf low {
        tailf:cli-disallow-value "vrf";
        type inet:ipv4-address {
          tailf:info
            "A.B.C.D;;Low IP address";
        }
      }
    }
    list low-high-list {
      tailf:cli-drop-node-name;
      tailf:cli-suppress-mode;
      tailf:cli-delete-when-empty;
      key "low high";
      leaf low {
        tailf:cli-disallow-value "vrf";
        type inet:ipv4-address {
          tailf:info
            "A.B.C.D;;Low IP address";
        }
      }
      leaf high {
        tailf:cli-disallow-value "vrf";
        type inet:ipv4-address {
          tailf:info
            "A.B.C.D;;High IP address";
        }
      }
    }
  }

  grouping ntp-peer-grouping {
    list peer-list {
      tailf:cli-drop-node-name;
      tailf:cli-suppress-mode;
      tailf:cli-delete-when-empty;
      tailf:cli-compact-syntax;
      tailf:cli-reset-container;
      key "name";
      leaf name {
        tailf:cli-disallow-value "vrf";
        tailf:cli-case-sensitive;
        type union {
          type inet:ipv4-address {
            tailf:info
              "A.B.C.D;;IP address of peer";
          }
          type string {
            tailf:info
              "WORD;;Hostname of peer";
          }
          type inet:ipv6-address {
            tailf:info
              "X:X:X:X::X;;IPv6 address of peer";
          }
        }
      }
      leaf burst {
        tailf:info
          "Send a burst when peer is reachable (Default)";
        type empty;
      }
      leaf iburst {
        tailf:info
          "Send a burst when peer is unreachable (Default)";
        type empty;
      }
      leaf key {
        tailf:info
          "Configure peer authentication key";
        type uint32 {
          tailf:info
            "<1-4294967295>;;Peer key number";
          range "1..4294967295";
        }
      }
      leaf maxpoll {
        tailf:info
          "Maximum poll interval";
        type uint8 {
          tailf:info
            "<4-17>;;Poll value in Log2";
          range "4..17";
        }
      }
      leaf minpoll {
        tailf:info
          "Minimum poll interval";
        type uint8 {
          tailf:info
            "<4-17>;;Poll value in Log2";
          range "4..17";
        }
      }
      leaf normal-sync {
        tailf:info
          "Disable rapid sync at startup";
        type empty;
      }
      leaf prefer {
        tailf:info
          "Prefer this peer when possible";
        type empty;
      }
      container source {
        tailf:info
          "Interface for source address";
        tailf:cli-flatten-container;
        tailf:cli-compact-syntax;
        uses interface-name-grouping;
      }
      leaf version {
        tailf:info
          "Configure NTP version";
        type uint8 {
          tailf:info
            "<1-4>;;NTP version number";
        }
      }
    }
  }

  grouping sntp-server-grouping {
    list server-list {
      tailf:cli-drop-node-name;
      tailf:cli-suppress-mode;
      tailf:cli-delete-when-empty;
      tailf:cli-compact-syntax;
      tailf:cli-reset-container;
      key "name";
      leaf name {
        tailf:cli-disallow-value "vrf";
        type union {
          type inet:ipv4-address {
            tailf:info
              "A.B.C.D;;IP address of server";
          }
          type string {
            tailf:info
              "WORD;;Hostname of peer";
          }
          type inet:ipv6-address {
            tailf:info
              "X:X:X:X::X;;IPv6 address of server";
          }
        }
      }
      leaf key {
        tailf:info
          "Configure server authentication key";
        type uint32 {
          tailf:info
            "<1-4294967295>;;Server key number";
          range "1..4294967295";
        }
      }
      leaf version {
        tailf:info
          "Configure NTP version";
        type uint8 {
          tailf:info
            "<1-4>;;NTP version number";
        }
      }
    }
  }

  grouping line-grouping {
    leaf absolute-timeout {
      tailf:info
        "Set absolute timeout for line disconnection";
      tailf:cli-full-command;
      type uint32 {
        tailf:info
          "<0-10000>;;Absolute timeout interval in minutes";
      }
    }
    container access-class {
      tailf:info
        "Filter connections based on an IP access list";
      tailf:cli-flatten-container;
      tailf:cli-compact-syntax;
      tailf:cli-sequence-commands {
        tailf:cli-reset-all-siblings;
      }
      list access-list {
        tailf:cli-drop-node-name;
        tailf:cli-suppress-mode;
        tailf:cli-delete-when-empty;
        tailf:cli-compact-syntax;
        tailf:cli-reset-container;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
          mandatory true;
        }
        leaf vrf-also {
          tailf:info
            "Same access list is applied for all VRFs";
          type empty;
        }
      }
    }
    container activation-character-choice {
      tailf:cli-drop-node-name;
      choice activation-character-choice {
        leaf activation-character {
          tailf:info
            "Define the activation character";
          tailf:cli-boolean-no;
          type boolean;
          default "true";
        }
        container activation-character-conf {
          tailf:cli-drop-node-name;
          tailf:cli-incomplete-command;
          tailf:cli-incomplete-no;
          leaf activation-character {
            type string {
              tailf:info
                "CHAR or <0-127>;;Activation character or its decimal equivalent";
            }
          }
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    container script {
      tailf:info
        "specify event related chat scripts to run on the line";
      leaf dialer {
        tailf:info
          "chat script to run whenever dialer makes an outgoing call";
        type string {
          tailf:info
            "WORD;;chat script name";
        }
        tailf:non-strict-leafref {
          path "/ncs:devices/ncs:device/ncs:config/ios:chat-script/name" {
            tailf:xpath-root 3;
          }
        }
      }
    }
    container modem {
      tailf:info
        "Configure the Modem Control Lines";
      leaf enable {
        tailf:info
          "Console port is used for connecting modem";
        tailf:cli-boolean-no;
        type boolean;
      }
      leaf InOut {
        tailf:info
          "Configure line for incoming AND outgoing use of modem";
        type empty;
      }
      container autoconfigure {
        tailf:info
          "Automatically configure modem on line";
        leaf discovery {
          tailf:info
            "Attempt to determine modem type automatically";
          type empty;
        }
      }
    }
    container exec-choice {
      tailf:cli-drop-node-name;
      choice exec-choice {
        leaf exec {
          tailf:info
            "Configure EXEC";
          tailf:cli-boolean-no;
          type boolean;
          default "true";
        }
        container exec-conf {
          tailf:cli-drop-node-name;
          tailf:cli-incomplete-command;
          tailf:cli-incomplete-no;
          container exec {
            tailf:cli-incomplete-command;
            tailf:cli-incomplete-no;
            container prompt {
              tailf:info
                "EXEC prompt";
              leaf timestamp {
                tailf:info
                  "Print timestamps for show commands";
                type empty;
              }
            }
          }
        }
      }
    }
    container exec-timeout {
      tailf:info
        "Set the EXEC timeout";
      tailf:cli-compact-syntax;
      tailf:cli-sequence-commands;
      leaf minutes {
        tailf:info
          "<0-35791>;;Timeout in minutes";
        tailf:cli-drop-node-name;
        type uint32;
      }
      leaf seconds {
        tailf:info
          "<0-2147483>;;Timeout in seconds";
        tailf:cli-drop-node-name;
        type uint32;
      }
    }
    container session-disconnect-warning {
      tailf:info
        "Set warning countdown for session-timeout";
      tailf:cli-compact-syntax;
      tailf:cli-sequence-commands {
        tailf:cli-reset-siblings;
      }
      leaf seconds {
        tailf:cli-drop-node-name;
        type uint32 {
          tailf:info
            "<0-4294967295>;;Session timeout warning in seconds";
        }
      }
      leaf message {
        tailf:info
          "Optional warning message";
        tailf:cli-multi-value;
        type string {
          tailf:info
            "LINE;;One text line optional warning message";
        }
      }
    }
    container logging {
      tailf:info
        "Modify message logging facilities";
      container synchronous {
        tailf:info
          "Synchronized message output";
        presence "true";
      }
    }
    container login {
      tailf:info
        "Enable password checking";
      tailf:cli-delete-when-empty;
      presence "true";
      leaf local {
        type empty;
      }
      leaf authentication {
        type string;
      }
    }
    leaf logout-warning {
      tailf:info
        "Set Warning countdown for absolute timeout of line";
      tailf:cli-full-command;
      type uint32 {
        tailf:info
          "<0-4294967295>;;Warning time in seconds";
      }
    }
    container ipv6 {
      tailf:info
        "IPv6 options";
      list access-class {
        tailf:info
          "Filter connections based on an IPv6 access list";
        tailf:cli-suppress-mode;
        tailf:cli-delete-when-empty;
        tailf:cli-compact-syntax;
        tailf:cli-sequence-commands;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
      }
    }
    container history {
      tailf:info
        "Enable and control the command history function";
      leaf size {
        tailf:info
          "Set history buffer size";
        type uint16 {
          tailf:info
            "<0-256>;;Size of history buffer";
          range "0..256";
        }
      }
    }
    container password {
      tailf:info
        "Set a password";
      tailf:cli-compact-syntax;
      tailf:cli-sequence-commands {
        tailf:cli-reset-siblings;
      }
      uses password-07-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf-list output {
        tailf:info
          "Define which protocols to use for outgoing connections";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
    leaf rxspeed {
      tailf:info
        "Set the receive speed";
      type uint32 {
        tailf:info
          "<0-4294967295>;;Receive speed";
      }
    }
    leaf txspeed {
      tailf:info
        "Set the transmit speed";
      type uint32 {
        tailf:info
          "<0-4294967295>;;Transmit speed";
      }
    }
    leaf length {
      tailf:info
        "Set number of lines on a screen";
      tailf:cli-full-command;
      type uint16 {
        tailf:info
          "<0-512>;;Number of lines on screen (0 for no pausing)";
        range "0..512";
      }
    }
    leaf width {
      tailf:info
        "Set width of the display terminal";
      tailf:cli-full-command;
      type uint16 {
        tailf:info
          "Number of characters on a screen line";
        range "0..512";
      }
    }
  }

  grouping queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping interface-common-pre-grouping {
    leaf description {
      tailf:info
        "Interface specific description";
      tailf:cli-multi-value;
      tailf:cli-full-command;
      type string {
        length "0..240";
      }
    }
    leaf mac-address {
      tailf:info
        "Manually set interface MAC address";
      type string {
        tailf:info
          "H.H.H;;MAC address";
      }
    }
  }

  grouping interface-common-grouping {
    container authentication {
      tailf:info
        "set the port-control value";
      leaf port-control {
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
    }
    container mab {
      presence "true";
      leaf eap {
        type empty;
      }
    }
    container l2protocol-tunnel {
      tailf:info
        "Tunnel Layer2 protocols";
      tailf:cli-delete-when-empty;
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
        leaf lldp {
          tailf:info
            "Link Layer Discovery Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
      leaf lldp {
        tailf:info
          "Link Layer Discovery Protocol";
        type empty;
      }
      container point-to-point {
        tailf:info
          "point-to-point L2 Protocol";
        leaf lacp {
          tailf:info
            "Link Aggregation Control Protocol";
          type empty;
        }
        leaf pagp {
          tailf:info
            "Port Aggregation Protocol";
          type empty;
        }
        leaf udld {
          tailf:info
            "Unidirectional Link Detection";
          type empty;
        }
      }
    }
    container encapsulation {
      tailf:info
        "Set encapsulation type for an interface";
      container dot1Q {
        tailf:info
          "IEEE 802.1Q Virtual LAN";
        tailf:cli-compact-syntax;
        tailf:cli-sequence-commands;
        leaf vlan-id {
          tailf:cli-drop-node-name;
          type uint16 {
            tailf:info
              "<1-4094>;;IEEE 802.1Q VLAN ID required";
            range "1..4094";
          }
        }
        leaf second-dot1q {
          tailf:info
            "Configure this subinterface as a 1Q-in-1Q subinterface";
          tailf:cli-optional-in-sequence;
          tailf:cli-full-command;
          type union {
            type enumeration {
              enum "any" {
                tailf:info
                  "All Inner VLAN IDs not configured on another subinterface";
              }
            }
            type string {
              tailf:info
                "Second (inner) VLAN IDs e.g. 100,200-300,400,500-600";
            }
          }
        }
        leaf native {
          tailf:info
            "Make this as native vlan";
          type empty;
        }
      }
      container isl {
        tailf:info
          "Inter Switch Link - Virtual LAN encapsulation";
        tailf:cli-compact-syntax;
        tailf:cli-sequence-commands;
        leaf vlan-id {
          tailf:cli-drop-node-name;
          type uint16 {
            tailf:info
              "<1-4095>;;Virtual LAN Identifier.";
            range "1..4095";
          }
        }
      }
      container ppp {
        tailf:info
          "Point-to-Point protocol";
        presence "true";
      }
      container slip {
        tailf:info
          "Serial Line IP";
        presence "true";
      }
      container frame-relay {
        tailf:info
          "Frame Relay networks";
        tailf:cli-delete-when-empty;
        presence "true";
        leaf IETF {
          tailf:info
            "Use RFC1490/RFC2427 encapsulation";
          tailf:cli-full-command;
          type empty;
        }
        leaf MFR {
          tailf:info
            "Multilink Frame Relay bundle interface";
          tailf:cli-allow-join-with-value {
            tailf:cli-display-joined;
          }
          tailf:cli-full-command;
          type uint32;
          tailf:non-strict-leafref {
            path "/ncs:devices/ncs:device/ncs:config/ios:interface/MFR/name" {
              tailf:xpath-root 3;
            }
          }
        }
      }
      container hdlc {
        tailf:cli-delete-when-empty;
        presence "true";
      }
    }
    container frame-relay {
      leaf lmi-type {
        tailf:cli-full-command;
        type enumeration {
          enum "ansi";
          enum "cisco";
          enum "q933a";
        }
      }
      leaf intf-type {
        type enumeration {
          enum "dce";
          enum "dte";
          enum "nni";
        }
      }
      container interface-dlci {
        tailf:info
          "Define a DLCI on an interface/subinterface";
        tailf:cli-add-mode;
        tailf:cli-mode-name "config-fr-dlci";
        tailf:cli-compact-syntax;
        tailf:cli-sequence-commands {
          tailf:cli-reset-siblings;
        }
        leaf dlci {
          tailf:cli-drop-node-name;
          tailf:cli-hide-in-submode;
          type uint16 {
            tailf:info
              "<16-1007>;;Define a switched or locally terminated DLCI";
          }
        }
        leaf encapsulation {
          tailf:cli-drop-node-name;
          tailf:cli-hide-in-submode;
          type enumeration {
            enum "cisco" {
              tailf:info
                "Use CISCO Encapsulation";
            }
            enum "IETF" {
              tailf:info
                "Use RFC1490/RFC2427 Encapsulation";
            }
          }
        }
      }
    }
    container fair-queue {
      tailf:info
        "Enable Fair Queuing on an Interface";
      tailf:cli-compact-syntax;
      tailf:cli-sequence-commands;
      tailf:cli-reset-container;
      tailf:cli-delete-when-empty;
      presence "true";
      leaf congestive-discard-threshold {
        tailf:cli-drop-node-name;
        type uint16 {
          tailf:info
            "<1-4096>;;Congestive Discard Threshold";
        }
      }
      leaf dynamic-queues {
        tailf:cli-drop-node-name;
        type uint16 {
          tailf:info
            "<16-4096>;;Number Dynamic Conversation Queues";
        }
      }
      leaf reservable-queues {
        tailf:cli-drop-node-name;
        type uint16 {
          tailf:info
            "<0-1000>;;Number Reservable Conversation Queues";
        }
      }
    }
    container flowcontrol {
      tailf:info
        "Configure flow operation.";
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    choice keepalive-choice {
      leaf keepalive {
        tailf:info
          "Enable keepalive";
        tailf:cli-boolean-no;
        tailf:cli-full-command;
        type boolean;
        default "true";
      }
      container keepalive-period {
        tailf:cli-drop-node-name;
        leaf keepalive {
          tailf:info
            "Enable keepalive";
          type uint16 {
            tailf:info
              "<0-32767>;;Keepalive period (default 10 seconds)";
            range "0..32767";
          }
          default "10";
        }
      }
      container keepalive-period-retries {
        tailf:cli-drop-node-name;
        container keepalive {
          tailf:cli-compact-syntax;
          tailf:cli-sequence-commands {
            tailf:cli-reset-siblings;
          }
          leaf period {
            tailf:cli-drop-node-name;
            type uint16 {
              tailf:info
                "<0-32767>;;Keepalive period (default 10 seconds)";
              range "0..32767";
            }
          }
          leaf retries {
            tailf:cli-drop-node-name;
            type uint8 {
              range "1..255";
            }
          }
        }
      }
    }
    container snmp {
      tailf:info
        "Modify SNMP interface parameters";
      container ifindex {
        tailf:info
          "Persist ifindex for the interface";
        leaf persist {
          tailf:info
            "Enable/Disable ifIndex persistence ";
          type empty;
        }
      }
      container trap {
        tailf:info
          "Allow a specific SNMP trap";
        leaf link-status {
          tailf:info
            "Allow SNMP LINKUP and LINKDOWN traps";
          tailf:cli-boolean-no;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
      }
    }
    container flow-sampler {
      tailf:info
        "Attach flow sampler to the interface";
      leaf name {
        tailf:cli-drop-node-name;
        type string {
          tailf:info
            "WORD;;Name of the flow sampler";
        }
        tailf:non-strict-leafref {
          path "/ncs:devices/ncs:device/ncs:config/ios:flow-sampler-map/name" {
            tailf:xpath-root 3;
          }
        }
      }
      container egress {
        tailf:cli-drop-node-name;
        tailf:cli-compact-syntax;
        tailf:cli-sequence-commands;
        leaf name {
          tailf:cli-drop-node-name;
          tailf:cli-incomplete-command;
          type string {
            tailf:info
              "WORD;;Name of the flow sampler";
          }
          tailf:non-strict-leafref {
            path "/ncs:devices/ncs:device/ncs:config/ios:flow-sampler-map/name" {
              tailf:xpath-root 3;
            }
          }
        }
        leaf egress {
          tailf:info
            "Egress flow sampler";
          type empty;
        }
      }
    }
    container bfd {
      tailf:info
        "BFD interface configuration commands";
      leaf echo {
        tailf:info
          "Use echo adjunct as bfd detection mechanism";
        type empty;
      }
      container interval {
        tailf:info
          "Transmit interval between BFD packets";
        tailf:cli-compact-syntax;
        tailf:cli-sequence-commands {
          tailf:cli-reset-all-siblings;
        }
        leaf msecs {
          tailf:cli-drop-node-name;
          tailf:cli-incomplete-command;
          type uint16 {
            tailf:info
              "<50-999>;;Milliseconds";
            range "50..999";
          }
        }
        leaf min_rx {
          tailf:info
            "Minimum receive interval capability";
          tailf:cli-incomplete-command;
          type uint16 {
            tailf:info
              "<50-999>;;Milliseconds";
            range "50..999";
          }
        }
        leaf multiplier {
          tailf:info
            "Multiplier value used to compute holddown";
          type uint8 {
            tailf:info
              "<3-50>;;value used to multiply the interval";
            range "3..50";
          }
        }
      }
    }
    container bandwidth {
      tailf:info
        "Set bandwidth informational parameter";
      tailf:cli-compact-syntax;
      tailf:cli-sequence-commands {
        tailf:cli-reset-siblings;
      }
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container mop {
      tailf:info
        "DEC MOP server commands";
      leaf xenabled {
        tailf:alt-name "enabled";
        tailf:info
          "Enable MOP for interface";
        tailf:cli-boolean-no;
        tailf:cli-full-command;
        type boolean;
        default "true";
      }
    }
    container dampening {
      tailf:info
        "Enable event dampening";
      presence "true";
      leaf dampening-time {
        tailf:cli-drop-node-name;
        tailf:cli-delete-container-on-delete;
        tailf:info
          "<1-30>;;Half-life time for penalty";
        type uint16 {
          range "1..30";
        }
      }
    }
    list hold-queue {
      tailf:info
        "Set hold queue depth";
      tailf:cli-suppress-mode;
      tailf:cli-delete-when-empty;
      tailf:cli-compact-syntax;
      tailf:cli-sequence-commands;
      key "direction";
      leaf direction {
        type enumeration {
          enum "in" {
            tailf:info
              "Input queue";
          }
          enum "out" {
            tailf:info
              "Output queue";
          }
        }
      }
      leaf queue-length {
        tailf:cli-drop-node-name;
        tailf:cli-prefix-key;
        type uint16 {
          tailf:info
            "<0-4096>;;Queue length";
          range "0..4096";
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:info
                "Use LDP (default)";
            }
            enum "tdp" {
              tailf:info
                "Use TDP";
            }
          }
        }
      }
      container ldp {
        tailf:info
          "Configure Label Distribution Protocol (LDP) parameters";
        container discovery {
          tailf:info
            "Configure interface LDP Discovery parameters";
          leaf transport-address {
            tailf:info
              "Specify interface LDP transport address";
            type ldp-discovery-address-type;
          }
        }
      }
      leaf mtu {
        tailf:info
          "Set MPLS Maximum Transmission Unit";
        tailf:cli-full-command;
        type union {
          type uint16 {
            tailf:info
              "<1501-1524>;;MTU (baby giants bytes)";
            range "1501..1524";
          }
          type uint16 {
            tailf:info
              "<64-1500>;;MTU (bytes)";
            range "64..1500";
          }
          type uint16 {
            tailf:info
              "<64-9216>;;MTU size in bytes";
            range "64..9216";
          }
        }
        default "1500";
      }
      container traffic-eng {
        tailf:info
          "Configure Traffic Engineering parameters";
        leaf administrative-weight {
          tailf:info
            "Set the administrative weight for the interface";
          tailf:cli-full-command;
          type uint32 {
            tailf:info
              "<0-4294967295>;;Weight";
            range "0..4294967295";
          }
        }
        leaf backup-path {
          tailf:info
            "Configure an MPLS TE backup for this interface";
          type string {
            tailf:info
              "Tunnel;;Tunnel interface";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                tailf:info
                  "<0-100>;;decreased bandwidth usage (percent)";
                range "0..100";
              }
            }
            leaf-list up {
              tailf:info
                "Set the thresholds for increased resource availability";
              tailf:cli-flat-list-syntax;
              type uint8 {
                tailf:info
                  "<0-100>;;increased bandwidth usage (percent)";
                range "0..100";
              }
            }
          }
        }
        leaf tunnels {
          tailf:info
            "enable MPLS Traffic Engineering tunnels";
          tailf:cli-full-command;
          type empty;
        }
      }
      leaf ip {
        tailf:info
          "Configure dynamic MPLS forwarding for IP";
        tailf:cli-full-command;
        type empty;
      }
    }
    container isis {
      tailf:info
        "IS-IS commands";
      container bfd {
        tailf:info
          "Bidirectional Forwarding Protocol";
        presence "true";
      }
      leaf circuit-type {
        tailf:info
          "Configure circuit type for interface";
        type enumeration {
          enum "level-1" {
            tailf:info
              "Level-1 only adjacencies are formed";
          }
          enum "level-1-2" {
            tailf:info
              "Level-1-2 adjacencies are formed";
          }
          enum "level-2-only" {
            tailf:info
              "Level-2 only adjacencies are formed";
          }
        }
        default "level-1-2";
      }
      leaf network {
        tailf:info
          "Network type";
        tailf:cli-full-command;
        type enumeration {
          enum "point-to-point" {
            tailf:info
              "Specify ISIS point-to-point network";
          }
        }
      }
      choice metric-choice {
        case default-case {
          leaf metric {
            tailf:info
              "Configure the metric for interface";
            type uint32 {
              tailf:info
                "<1-16777214>;;Default metric";
              range "1..16777214";
            }
          }
        }
        case level-case {
          container metric-level {
            tailf:cli-drop-node-name;
            list metric {
              tailf:cli-suppress-mode;
              tailf:cli-delete-when-empty;
              tailf:cli-compact-syntax;
              key "level";
              leaf level {
                type enumeration {
                  enum "level-1" {
                    tailf:info
                      "Apply metric to level-1 links";
                  }
                  enum "level-2" {
                    tailf:info
                      "Apply metric to level-2 links";
                  }
                }
              }
              leaf default {
                tailf:cli-drop-node-name;
                tailf:cli-prefix-key;
                type uint32 {
                  tailf:info
                    "<1-16777214>;;Default metric";
                  range "1..16777214";
                }
              }
            }
          }
        }
      }
      uses router-isis-interface-grouping;
      container ipv6 {
        tailf:info
          "IPv6 interface configuration";
        container metric-level {
          tailf:cli-drop-node-name;
          list metric {
            tailf:info
              "Configure the metric for interface";
            tailf:cli-suppress-mode;
            tailf:cli-delete-when-empty;
            tailf:cli-compact-syntax;
            tailf:cli-sequence-commands;
            key "level";
            leaf level {
              type enumeration {
                enum "level-1" {
                  tailf:info
                    "Apply metric to level-1 links";
                }
                enum "level-2" {
                  tailf:info
                    "Apply metric to level-2 links";
                }
              }
            }
            leaf value {
              tailf:cli-drop-node-name;
              tailf:cli-prefix-key;
              type union {
                type uint32 {
                  tailf:info
                    "<1-16777214>;;Default metric";
                  range "1..16777214";
                }
                type enumeration {
                  enum "maximum" {
                    tailf:info
                      "Maximum metric. All routers will exclude this link from their SPF";
                  }
                }
              }
            }
          }
        }
      }
    }
    choice vrf-choice {
      container ip-vrf {
        tailf:cli-drop-node-name;
        container ip {
          container vrf {
            leaf forwarding {
              tailf:info
                "Configure forwarding table";
              tailf:callpoint interface-vrf-hook {
                tailf:set-hook node;
              }
              type string {
                tailf:info
                  "WORD;;VRF name";
              }
              tailf:non-strict-leafref {
                path "/ncs:devices/ncs:device/ncs:config/ios:ip/vrf/name" {
                  tailf:xpath-root 3;
                }
              }
            }
          }
        }
      }
      container vrf {
        tailf:info
          "VPN Routing/Forwarding parameters on the interface";
        leaf forwarding {
          tailf:info
            "Configure forwarding table";
          tailf:callpoint interface-vrf-hook {
            tailf:set-hook node;
          }
          type string {
            tailf:info
              "WORD;;VRF name";
          }
          tailf:non-strict-leafref {
            path "/ncs:devices/ncs:device/ncs:config/ios:vrf/definition/name" {
              tailf:xpath-root 3;
            }
          }
        }
      }
    }
    container ip {
      tailf:info
        "Interface Internet Protocol config commands";
      list access-group {
        tailf:info
          "Specify access control for packets";
        tailf:cli-suppress-mode;
        tailf:cli-delete-when-empty;
        tailf:cli-compact-syntax;
        tailf:cli-sequence-commands;
        key "direction";
        leaf direction {
          type enumeration {
            enum "in" {
              tailf:code-name "access_group_direction_in";
              tailf:info
                "inbound packets";
            }
            enum "out" {
              tailf:code-name "access_group_direction_out";
              tailf:info
                "outbound packets";
            }
          }
        }
        leaf access-list {
          tailf:cli-drop-node-name;
          tailf:cli-prefix-key;
          type exp-ip-acl-type;
        }
      }
      container accounting {
        tailf:info
          "Enable IP accounting on this interface";
        tailf:cli-delete-when-empty;
        presence "true";
        leaf access-violations {
          tailf:info
            "Account for IP packets violating access lists on this interface";
          tailf:cli-full-command;
          type empty;
        }
        leaf output-packets {
          tailf:info
            "Account for IP packets output on this interface";
          tailf:cli-full-command;
          type empty;
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      choice address-choice {
        leaf unnumbered {
          tailf:info
            "Enable IP processing without an explicit address";
          type string;
        }
        container no-address {
          tailf:cli-drop-node-name;
          leaf address {
            tailf:cli-boolean-no;
            tailf:cli-full-command;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-compact-syntax;
                tailf:cli-sequence-commands;
                tailf:cli-incomplete-command;
                tailf:cli-incomplete-no;
                leaf address {
                  tailf:cli-drop-node-name;
                  tailf:cli-incomplete-command;
                  tailf:cli-incomplete-no;
                  tailf:cli-diff-dependency "/ios:vrf/definition" {
                    tailf:xpath-root 3;
                  }
                  tailf:cli-diff-dependency "../../../../vrf/forwarding" {
                    tailf:xpath-root 3;
                  }
                  mandatory true;
                  type inet:ipv4-address {
                    tailf:info
                      "A.B.C.D;;IP address";
                  }
                }
                leaf mask {
                  tailf:cli-drop-node-name;
                  mandatory true;
                  type inet:ipv4-address {
                    tailf:info
                      "A.B.C.D;;IP subnet mask";
                  }
                }
              }
              list secondary {
                tailf:cli-drop-node-name;
                tailf:cli-suppress-mode;
                tailf:cli-delete-when-empty;
                tailf:cli-compact-syntax;
                tailf:cli-incomplete-command;
                tailf:cli-incomplete-no;
                tailf:cli-diff-dependency "../primary/address" {
                  tailf:xpath-root 3;
                }
                key "address mask";
                leaf address {
                  tailf:cli-incomplete-no;
                  type inet:ipv4-address {
                    tailf:info
                      "A.B.C.D;;IP address";
                  }
                }
                leaf mask {
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                tailf:cli-sequence-commands;
                presence "true";
                container client-id {
                  tailf:info
                    "Specify client-id to use";
                  tailf:cli-optional-in-sequence;
                  tailf:cli-flatten-container;
                  tailf:cli-compact-syntax;
                  uses interface-name-grouping;
                }
                leaf hostname {
                  tailf:info
                    "Specify value for hostname option";
                  type string {
                    tailf:info
                      "WORD;;hostname string";
                  }
                }
              }
            }
            case negotiated-case {
              container negotiated {
                tailf:info
                  "IP Address negotiated over PPP";
                tailf:cli-reset-container;
                tailf:cli-delete-when-empty;
                presence "true";
                leaf previous {
                  tailf:info
                    "IPCP attempts to negotiate previous address assigned";
                  type empty;
                }
              }
            }
          }
        }
      }
      container directed-broadcast {
        tailf:info
          "Enable forwarding of directed broadcasts";
        tailf:cli-delete-when-empty;
        presence "true";
        leaf access-list {
          tailf:cli-drop-node-name;
          type union {
            type uint16 {
              tailf:info
                "<1-199>;;A standard IP access list number";
              range "1..199";
            }
            type uint16 {
              tailf:info
                "<1300-2699>;;A standard IP expanded access list number";
              range "1300..2699";
            }
          }
        }
      }
      container router {
        tailf:info
          "IP router interface commands";
        container isis {
          tailf:info
            "IS-IS Routing for IP";
          tailf:cli-delete-when-empty;
          presence "true";
          leaf tag {
            tailf:cli-drop-node-name;
            type string {
              tailf:info
                "WORD;;Routing process tag";
            }
          }
        }
      }
      container flow {
        tailf:info
          "NetFlow related commands";
        leaf ingress {
          tailf:info
            "Enable inbound NetFlow";
          type empty;
        }
        leaf egress {
          tailf:info
            "Enable outbound NetFlow";
          type empty;
        }
      }
      container helper-address {
        tailf:info
          "Specify a destination address for UDP broadcasts";
        tailf:cli-compact-syntax;
        tailf:cli-sequence-commands {
          tailf:cli-reset-siblings;
        }
        choice helper-choice {
          leaf global {
            tailf:info
              "Helper-address is global";
            tailf:cli-optional-in-sequence;
            type empty;
          }
          leaf vrf {
            tailf:info
              "VRF name for helper-address (if different from interface VRF)";
            tailf:cli-optional-in-sequence;
            tailf:cli-diff-dependency "/ios:ip/vrf" {
              tailf:xpath-root 3;
            }
            tailf:cli-diff-dependency "/ios:vrf/definition" {
              tailf:xpath-root 3;
            }
            type string {
              tailf:info
                "WORD;;VPN Routing/Forwarding instance name";
            }
          }
        }
        leaf address {
          tailf:cli-drop-node-name;
          type inet:ipv4-address {
            tailf:info
              "A.B.C.D;;IP destination address";
          }
        }
      }
      container ospf {
        tailf:info
          "OSPF interface commands";
        list process-id {
          tailf:cli-drop-node-name;
          tailf:cli-suppress-mode;
          tailf:cli-delete-when-empty;
          tailf:cli-compact-syntax;
          tailf:cli-sequence-commands {
            tailf:cli-reset-all-siblings;
          }
          tailf:cli-incomplete-command;
          key "id";
          leaf id {
            type uint16 {
              tailf:info
                "<1-65535>;;Process ID";
            }
          }
          leaf area {
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        container authentication {
          tailf:info
            "Enable authentication";
          tailf:cli-delete-when-empty;
          presence "true";
          leaf option {
            tailf:cli-drop-node-name;
            type enumeration {
              enum "message-digest" {
                tailf:info
                  "Use message-digest authentication";
              }
              enum "null" {
                tailf:info
                  "Use no authentication";
              }
            }
          }
        }
        list message-digest-key {
          tailf:info
            "Message digest authentication password (key)";
          tailf:cli-suppress-mode;
          tailf:cli-delete-when-empty;
          tailf:cli-compact-syntax;
          tailf:cli-sequence-commands {
            tailf:cli-reset-siblings;
          }
          key "id";
          leaf id {
            type uint8 {
              tailf:info
                "<1-255>;;Key ID";
              range "1..255";
            }
          }
          leaf md5 {
            tailf:info
              "Use MD5 algorithm";
            type empty;
          }
          leaf enc-type {
            tailf:cli-drop-node-name;
            tailf:cli-incomplete-command;
            tailf:cli-optional-in-sequence;
            type uint8 {
              tailf:info
                "<0-7>;;Encryption type (0 for not yet encrypted, 7 for proprietary)";
              range "0..7";
            }
          }
          leaf password {
            tailf:cli-drop-node-name;
            type string {
              tailf:info
                "LINE;;The OSPF password (key) (maximum 16 characters)";
            }
          }
        }
        leaf network {
          tailf:info
            "Network type";
          tailf:cli-full-command;
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        leaf hello-interval {
          tailf:info
            "Time between HELLO packets";
          type uint16 {
            tailf:info
              "<1-65535>;;Seconds";
            range "1..65535";
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf cost {
          tailf:info
            "Interface cost";
          tailf:cli-full-command;
          type uint16 {
            tailf:info
              "<1-65535>;;Cost";
            range "1..65535";
          }
        }
        leaf priority {
          tailf:info
            "Router priority";
          tailf:cli-full-command;
          type uint8 {
            tailf:info
              "<0-255>;;Priority";
          }
        }
      }
      container pim {
        tailf:info
          "PIM interface commands";
        leaf query-interval {
          tailf:info
            "PIM router query interval";
          type uint16 {
            tailf:info
              "<1-65535>;;Query interval in seconds or milliseconds";
            range "1..65535";
          }
        }
        leaf sparse-mode {
          tailf:info
            "Enable PIM sparse-mode operation";
          tailf:cli-diff-dependency "/ios:ip/multicast-routing" {
            tailf:xpath-root 3;
          }
          type empty;
        }
        leaf dr-priority {
          tailf:info
            "PIM router DR priority";
          type uint32 {
            tailf:info
              "<0-4294967294>;;DR priority, preference given to larger value";
          }
        }
        leaf snooping {
          tailf:info
            "PIM Snooping enable for Catalyst Vlan";
          type empty;
        }
      }
      container multicast {
        tailf:info
          "IP multicast interface commands";
        list boundary {
          tailf:info
            "Boundary for administratively scoped multicast addresses";
          tailf:cli-compact-syntax;
          tailf:cli-sequence-commands {
            tailf:cli-reset-siblings;
          }
          key "access-list";
          leaf access-list {
            type exp-ip-acl-type;
          }
        }
      }
      container policy {
        tailf:info
          "Enable policy routing";
        leaf route-map {
          tailf:info
            "Policy route-map";
          type string {
            tailf:info
              "WORD;;Route map name";
          }
        }
      }
      leaf unreachables {
        tailf:info
          "Enable sending ICMP Unreachable messages";
        tailf:cli-boolean-no;
        type boolean;
        default "true";
      }
      leaf proxy-arp {
        tailf:info
          "Enable proxy ARP";
        tailf:cli-boolean-no;
        type boolean;
        default "true";
      }
      container route-cache-conf {
        tailf:cli-drop-node-name;
        leaf route-cache {
          tailf:cli-boolean-no;
          tailf:cli-full-command;
          type boolean;
          default "true";
        }
      }
      container route-cache {
        tailf:info
          "Enable fast-switching cache for outgoing packets";
        tailf:cli-incomplete-no;
        tailf:cli-incomplete-command;
        leaf cef {
          tailf:info
            "Enable Cisco Express Forwarding";
          tailf:cli-boolean-no;
          type boolean;
          default "true";
        }
        leaf flow {
          tailf:info
            "Enable Flow fast-switching cache";
          tailf:cli-boolean-no;
          type boolean;
          default "false";
        }
        leaf policy {
          tailf:info
            "Enable fast-switching policy cache for outgoing packets";
          tailf:cli-boolean-no;
          type boolean;
          default "false";
        }
        leaf same-interface {
          tailf:info
            "Enable fast-switching on the same interface";
          tailf:cli-boolean-no;
          type boolean;
          default "false";
        }
      }
      container igmp {
        tailf:info
          "IGMP interface commands";
        list join-group {
          tailf:info
            "IGMP join multicast group";
          tailf:cli-suppress-mode;
          tailf:cli-delete-when-empty;
          tailf:cli-compact-syntax;
          key "address";
          leaf address {
            type inet:ipv4-address {
              tailf:info
                "A.B.C.D;;IP group address";
            }
          }
          leaf source {
            tailf:info
              "Include SSM source";
            type inet:ipv4-address {
              tailf:info
                "A.B.C.D;;IP source address";
            }
          }
        }
        container static-group {
          tailf:info
            "IGMP static multicast group";
          list groups {
            tailf:cli-suppress-mode;
            tailf:cli-delete-when-empty;
            tailf:cli-drop-node-name;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            key "id";
            leaf id {
              type string {
                tailf:info
                  "WORD;;Name of class-map of type multicast-flows";
              }
              tailf:non-strict-leafref {
                path "/ncs:devices/ncs:device/ncs:config/ios:class-map/name" {
                  tailf:xpath-root 3;
                }
              }
            }
          }
        }
        leaf version {
          tailf:info
            "IGMP version";
          type uint8 {
            tailf:info
              "<1-3>;;version number";
            range "1..3";
          }
        }
        leaf access-group {
          tailf:info
            "IGMP group access group";
          type exp-ip-acl-type;
        }
      }
      leaf redirects {
        tailf:info
          "Enable sending ICMP Redirect messages";
        type empty;
      }
      container nhrp {
        tailf:info
          "NHRP interface subcommands";
        leaf network-id {
          tailf:info
            "NBMA network identifier";
          type uint32 {
            tailf:info
              "<1-4294967295>;;Network identifier";
          }
        }
        container shortcut {
          tailf:info
            "Enable shortcut switching";
          tailf:cli-delete-when-empty;
          presence "true";
          leaf virtual-template {
            type uint16;
          }
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container tcp {
        tailf:info
          "TCP header compression and other parameters";
        leaf adjust-mss {
          tailf:info
            "Adjust the mss of transit packets";
          type uint16 {
            tailf:info
              "<500-1460>;;Maximum segment size in bytes";
            range "500..1460";
          }
        }
        container header-compression {
          tailf:info
            "Enable TCP header compression";
          tailf:cli-delete-when-empty;
          presence "true";
          leaf type {
            tailf:cli-drop-node-name;
            type enumeration {
              enum "ietf-format" {
                tailf:info
                  "Compressing using IETF format";
              }
              enum "iphc-format" {
                tailf:info
                  "Using PPP  IPHC compression for TCP/UDP/RTP";
              }
              enum "passive" {
                tailf:info
                  "Compress only for destinations which send compressed headers";
              }
            }
          }
        }
      }
      container rtp {
        tailf:info
          "RTP parameters";
        container header-compression {
          tailf:info
            "Enable RTP header compression";
          tailf:cli-compact-syntax;
          tailf:cli-sequence-commands {
            tailf:cli-reset-siblings;
          }
          leaf type {
            tailf:cli-drop-node-name;
            tailf:cli-optional-in-sequence;
            type enumeration {
              enum "ietf-format" {
                tailf:info
                  "Compressing using IETF format";
              }
              enum "iphc-format" {
                tailf:info
                  "Compress using IPHC format";
              }
              enum "passive" {
                tailf:info
                  "Compress only for destinations which send compressed headers";
              }
            }
          }
          leaf periodic-refresh {
            tailf:info
              "Periodic context refresh";
            type empty;
          }
        }
        leaf compression-connections {
          tailf:info
            "Maximum number of compressed connections";
          type uint16 {
            tailf:info
              "<1-1000>;;Number of connections";
            range "1..1000";
          }
        }
      }
      container mobile {
        tailf:info
          "Mobile IP support";
        container router-service {
          tailf:info
            "Mobile router support";
          container roam {
            tailf:info
              "Roaming interface";
            tailf:cli-diff-dependency "/ios:router/mobile" {
              tailf:xpath-root 3;
            }
            presence "true";
            leaf priority {
              tailf:info
                "Priority level";
              type uint8 {
                tailf:info
                  "<0-255>;;Priority level";
              }
            }
          }
          leaf description {
            tailf:info
              "roaming interface description";
            tailf:cli-multi-value;
            tailf:cli-full-command;
            type string {
              tailf:info
                "LINE;;roaming interface description";
            }
          }
          leaf link-type {
            tailf:info
              "Link type of the roaming interface";
            type string;
          }
          container tunnel {
            tailf:info
              "Tunnel parameters";
            leaf mode {
              tailf:info
                "Tunnel encapsulation mode";
              type enumeration {
                enum "gre" {
                  tailf:info
                    "Generic Routing Encapsulation";
                }
                enum "ipip" {
                  tailf:info
                    "IP-in-IP Encapsulation";
                }
              }
            }
          }
          container collocated {
            tailf:info
              "Collocated care-of address options";
            tailf:cli-compact-syntax;
            tailf:cli-sequence-commands;
            leaf gateway {
              tailf:info
                "Default gateway for static collocated care-of address";
              tailf:cli-optional-in-sequence;
              type inet:ipv4-address {
                tailf:info
                  "A.B.C.D;;IP address to use as the default gateway";
              }
            }
            leaf ccoa-only {
              tailf:info
                "Only register a collocated CoA";
              tailf:cli-optional-in-sequence;
              type empty;
            }
            container registration {
              tailf:info
                "Registration options";
              tailf:cli-break-sequence-commands;
              leaf retry {
                tailf:info
                  "Retry interval in seconds (1-65535)";
                type uint16 {
                  tailf:info
                    "<1-65535>;;Seconds (default 60; 65535 = never)";
                  range "1..65535";
                }
                default "60";
              }
              container nat {
                tailf:info
                  "NAT traversal settings";
                container traversal {
                  tailf:info
                    "Enable NAT traversal support";
                  tailf:cli-compact-syntax;
                  presence "true";
                  leaf keepalive {
                    tailf:info
                      "Keepalive message frequency (sec)";
                    type uint16 {
                      tailf:info
                        "<0-65535>;;keepalive value";
                    }
                  }
                  leaf force {
                    tailf:info
                      "Force home agent to use UDP encapsulation for the tunnel";
                    type empty;
                  }
                }
              }
            }
            leaf encapsulation {
              type enumeration {
                enum "slip";
                enum "ppp";
              }
            }
          }
        }
      }
      container virtual-reassembly {
        tailf:info
          "Enable Virtual Fragment Reassembly";
        tailf:cli-compact-syntax;
        leaf max-reassemblies {
          type uint32;
        }
        leaf max-fragments {
          tailf:info
            "<1-64>;;Number of fragments per datagram";
          type uint8 {
            tailf:info
              "<1-64>;;Number of fragments per datagram";
            range "1..64";
          }
        }
        leaf timeout {
          type uint32;
        }
        leaf drop-fragments {
          tailf:info
            "Drop all the incoming fragments";
          type empty;
        }
        leaf in {
          type empty;
        }
        leaf out {
          type empty;
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            tailf:cli-suppress-mode;
            tailf:cli-delete-when-empty;
            tailf:cli-compact-syntax;
            key "id";
            leaf id {
              type uint16 {
                tailf:info
                  "<1-4094>;;DHCP Snooping vlan";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
          list bridge-domain {
            tailf:info
              "DHCP Snooping bridge-domain";
            tailf:cli-suppress-mode;
            tailf:cli-delete-when-empty;
            tailf:cli-compact-syntax;
            key "id";
            leaf id {
              type uint16 {
                tailf:info
                  "<1-4094>;;DHCP Snooping bridge-domain number";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id";
                      }
                    }
                  }
                }
              }
            }
          }
        }
      }
      leaf mtu {
        tailf:info
          "Set IP Maximum Transmission Unit";
        type uint16 {
          tailf:info
            "<68-9198>;;MTU (bytes)";
          range "68..9198";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
      container rsvp {
        tailf:info
          "RSVP Interface Commands";
        container bandwidth {
          tailf:info
            "RSVP Reservable Bandwidth (kbps)";
          tailf:cli-reset-container;
          presence "true";
        }
        container signalling {
          tailf:info
            "RSVP signalling";
          container hello {
            tailf:info
              "Enable neighbor-down detection";
            presence "true";
            container graceful-restart {
              tailf:info
                "Configure RSVP Graceful Restart";
              presence "true";
            }
          }
        }
        container resource-provider {
          tailf:info
            "RSVP resource provider";
          choice resource-provider-choice {
            leaf none {
              tailf:info
                "Associates NO resources with reservations";
              type empty;
            }
            leaf wfq {
              tailf:info
                "Associates WFQ resources with reservations";
              type enumeration {
                enum "interface" {
                  tailf:info
                    "Associates WFQ queues and bandwidth at the interface level with reservations";
                }
                enum "pvc" {
                  tailf:info
                    "Associates WFQ queues and bandwidth at the PVC level with reservations";
                }
              }
            }
          }
        }
      }
      container verify {
        tailf:info
          "Enable per packet validation";
        container unicast {
          tailf:info
            "Enable per packet validation for unicast";
          container reverse-path {
            tailf:info
              "Reverse path validation of source address (old command format)";
            presence "true";
          }
          container source {
            tailf:info
              "Validation of source address";
            tailf:cli-compact-syntax;
            tailf:cli-sequence-commands {
              tailf:cli-reset-all-siblings;
            }
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
            leaf allow-self-ping {
              tailf:cli-break-sequence-commands;
              tailf:info
                "Allow router to ping itself (opens vulnerability in verification)";
              type empty;
            }
            leaf allow-default {
              tailf:info
                "Allow default route to match when checking source address";
              type empty;
            }
          }
        }
      }
      container rip {
        tailf:info
          "Router Information Protocol";
        container receive {
          tailf:info
            "advertisement reception";
          leaf version {
            tailf:info
              "version control";
            type enumeration {
              enum "1" {
                tailf:info
                  "RIP version 1";
              }
              enum "2" {
                tailf:info
                  "RIP version 2";
              }
            }
          }
        }
        container authentication {
          tailf:info
            "Authentication control";
          leaf mode {
            tailf:info
              "Authentication mode";
            type enumeration {
              enum "md5" {
                tailf:info
                  "Keyed message digest";
              }
              enum "text" {
                tailf:info
                  "Clear text authentication";
              }
            }
          }
          leaf key-chain {
            tailf:info
              "Authentication key-chain";
            type string {
              tailf:info
                "LINE;;name of key-chain";
            }
            tailf:non-strict-leafref {
              path "/ncs:devices/ncs:device/ncs:config/ios:key/chain/name" {
                tailf:xpath-root 3;
              }
            }
          }
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case manual-case {
            list prefix-list {
              tailf:cli-drop-node-name;
              tailf:cli-suppress-mode;
              tailf:cli-delete-when-empty;
              key "prefix";
              leaf prefix {
                type ios:ipv6-prefix {
                  tailf:info
                    "X:X:X:X::X/<0-128>;;IPv6 prefix";
                }
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      list traffic-filter {
        tailf:info
          "Access control list for packets";
        tailf:cli-suppress-mode;
        tailf:cli-delete-when-empty;
        tailf:cli-compact-syntax;
        tailf:cli-sequence-commands;
        key "direction";
        leaf direction {
          type enumeration {
            enum "in" {
              tailf:info
                "inbound packets";
            }
            enum "out" {
              tailf:info
                "outbound packets";
            }
          }
        }
        leaf access-list {
          tailf:cli-drop-node-name;
          tailf:cli-prefix-key;
          type string {
            tailf:info
              "WORD;;Access-list name";
          }
        }
      }
      container nd {
        tailf:info
          "IPv6 interface Neighbor Discovery subcommands";
        container dad {
          tailf:info
            "Duplicate Address Detection";
          leaf attempts {
            tailf:info
              "Set IPv6 Duplicate Address Detection Transmits";
            type uint16 {
              tailf:info
                "<0-600>;;Number of attempts";
              range "0..600";
            }
          }
        }
        container prefix {
          tailf:info
            "Configure IPv6 Routing Prefix Advertisement";
          list prefix-list {
            tailf:cli-drop-node-name;
            tailf:cli-suppress-mode;
            tailf:cli-delete-when-empty;
            tailf:cli-compact-syntax;
            tailf:cli-sequence-commands {
              tailf:cli-reset-all-siblings;
            }
            tailf:cli-incomplete-command;
            key "ipv6-prefix";
            leaf ipv6-prefix {
              type union {
                type inet:ipv6-prefix {
                  tailf:info
                    "X:X:X:X::X/<0-128>;;IPv6 prefix x:x::y/<z>";
                }
                type enumeration {
                  enum "default" {
                    tailf:info
                      "Specify prefix default parameters";
                  }
                }
              }
            }
            choice advertise-choice {
              case no-advertise {
                leaf no-advertise {
                  tailf:info
                    "Do not advertise prefix";
                  tailf:cli-full-command;
                  type empty;
                }
              }
              case advertise {
                leaf valid-lifetime {
                  tailf:cli-drop-node-name;
                  tailf:cli-incomplete-command;
                  type union {
                    type enumeration {
                      enum "infinite" {
                        tailf:info
                          "Infinite Valid Lifetime";
                      }
                    }
                    type uint32 {
                      tailf:info
                        "<0-4294967295>;;Valid Lifetime (secs)";
                    }
                  }
                }
                leaf preferred-lifetime {
                  tailf:cli-drop-node-name;
                  type union {
                    type enumeration {
                      enum "infinite" {
                        tailf:info
                          "Infinite Preferred Lifetime";
                      }
                    }
                    type uint32 {
                      tailf:info
                        "<0-4294967295>;;Preferred Lifetime (secs)";
                    }
                  }
                }
                leaf off-link {
                  tailf:cli-break-sequence-commands;
                  tailf:info
                    "Prefix is offlink";
                  type empty;
                }
                leaf no-autoconfig {
                  tailf:info
                    "Do not use prefix for autoconfiguration";
                  type empty;
                }
                leaf no-rtr-address {
                  tailf:info
                    "Do not send full router address in prefix advert";
                  type empty;
                }
                leaf no-onlink {
                  tailf:info
                    "Do not use prefix for onlink determination";
                  type empty;
                }
              }
            }
          }
        }
        leaf managed-config-flag {
          tailf:info
            "Hosts should use DHCP for address config";
          type empty;
        }
        leaf other-config-flag {
          tailf:info
            "Hosts should use DHCP for non-address config";
          type empty;
        }
        container ra {
          tailf:info
            "Router Advertisement control";
          container suppress {
            tailf:info
              "Suppress IPv6 Router Advertisements";
            tailf:cli-delete-when-empty;
            presence "true";
            leaf all {
              tailf:info
                "Suppress all ipv6 Router advertisements";
              type empty;
            }
          }
          container interval {
            choice interval-choice {
              leaf seconds {
                tailf:cli-drop-node-name;
                type uint16 {
                  tailf:info
                    "<4-1800>;;RA Interval (sec)";
                  range "4..1800";
                }
              }
              leaf msec {
                tailf:info
                  "Interval in milliseconds";
                type uint32 {
                  tailf:info
                    "<70-1800000>;;RA Interval (msec)";
                  range "70..1800000";
                }
              }
            }
          }
        }
      }
      container mld {
        tailf:info
          "interface commands";
        leaf access-group {
          tailf:info
            "source, group membership access";
          type string {
            tailf:info
              "WORD;;Named access list specifying access group range";
          }
        }
      }
      leaf redirects {
        tailf:info
          "Enable sending of ICMP Redirect messages";
        tailf:cli-boolean-no;
        tailf:cli-full-command;
        type boolean;
        default "true";
      }
      leaf unreachables {
        tailf:info
          "Enable sending of ICMP Unreachable messages";
        tailf:cli-boolean-no;
        tailf:cli-full-command;
        type boolean;
        default "true";
      }
      container router {
        tailf:info
          "IPv6 Router interface commands";
        container isis {
          tailf:info
            "isis  IS-IS Routing for IPv6";
          tailf:cli-delete-when-empty;
          presence "true";
          leaf tag {
            tailf:cli-drop-node-name;
            type string {
              tailf:info
                "WORD;;Routing process tag";
            }
          }
        }
      }
      container ospf {
        tailf:info
          "OSPF interface commands";
        list process {
          tailf:cli-drop-node-name;
          tailf:cli-suppress-mode;
          tailf:cli-delete-when-empty;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf mtu {
        tailf:info
          "Set IPv6 Maximum Transmission Unit";
        type uint16 {
          tailf:info
            "<1280-9198>;;MTU (bytes)";
          range "1280..9198";
        }
      }
      container crypto {
        tailf:info
          "Encryption/Decryption commands";
        container map {
          tailf:info
            "Assign a Crypto Map";
          tailf:cli-compact-syntax;
          tailf:cli-sequence-commands {
            tailf:cli-reset-siblings;
          }
          leaf map-name {
            tailf:cli-drop-node-name;
            type string {
              tailf:info
                "WORD;;Crypto Map tag";
            }
            tailf:non-strict-leafref {
              path "/ncs:devices/ncs:device/ncs:config/ios:crypto/map/name" {
                tailf:xpath-root 3;
              }
            }
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
      }
      container verify {
        tailf:info
          "Enable per packet validation";
        container unicast {
          tailf:info
            "Enable per packet validation for unicast";
          container reverse-path {
            tailf:info
              "Reverse path validation of source address (old command format)";
            tailf:cli-delete-when-empty;
            presence "true";
            leaf access-list {
              tailf:cli-drop-node-name;
              type string {
                tailf:info
                  "WORD;;Access-list name";
              }
            }
          }
        }
      }
      container dhcp {
        tailf:info
          "IPv6 DHCP interface subcommands";
        container relay {
          tailf:info
            "Act as an IPv6 DHCP relay agent";
          list destination {
            tailf:info
              "Configure relay destination";
            tailf:cli-suppress-mode;
            tailf:cli-delete-when-empty;
            tailf:cli-compact-syntax;
            tailf:cli-sequence-commands {
              tailf:cli-reset-siblings;
            }
            key "ipv6-address";
            leaf ipv6-address {
              type inet:ipv6-address {
                tailf:info
                  "X:X:X:X::X;;IPv6 address";
              }
            }
            leaf source-address {
              tailf:info
                "Configure source address to use for relay-forward";
              type inet:ipv6-address {
                tailf:info
                  "X:X:X:X::X;;IPv6 src address";
              }
            }
            leaf link-address {
              tailf:info
                "Configure link-address to use for relay-forward";
              type inet:ipv6-address {
                tailf:info
                  "X:X:X:X::X;;IPv6 link address";
              }
            }
          }
        }
      }
    }
    leaf delay {
      tailf:info
        "Specify interface throughput delay";
      type uint32 {
        tailf:info
          "<1-16777215>;;Throughput delay (tens of microseconds)";
      }
    }
    leaf load-interval {
      tailf:info
        "Specify interval for load calculation for an interface";
      type uint16 {
        tailf:info
          "<30-600>;;Load interval delay in seconds";
        range "0..600";
      }
    }
    container logging {
      tailf:info
        "Configure logging for interface";
      container event {
        tailf:info
          "Interface events";
        leaf link-status {
          tailf:info
            "UPDOWN and CHANGE messages";
          tailf:cli-full-command;
          type empty;
        }
        leaf subif-link-status {
          tailf:info
            "Sub-interface UPDOWN and CHANGE messages";
          tailf:cli-full-command;
          type empty;
        }
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container qos {
        tailf:info
          "qos command keyword";
        leaf channel-consistency {
          tailf:info
            "enable or disable qos consistency checks";
          tailf:cli-boolean-no;
          tailf:cli-full-command;
          type boolean;
          default "true";
        }
        leaf trust {
          tailf:info
            "trust keyword";
          tailf:cli-full-command;
          type enumeration {
            enum "cos" {
              tailf:info
                "cos keyword";
            }
            enum "dscp" {
              tailf:info
                "dscp keyword";
            }
            enum "ip-precedence" {
              tailf:info
                "ip-precedence keyword";
            }
          }
        }
        leaf vlan-based {
          tailf:info
            "vlan-based keyword";
          tailf:cli-full-command;
          type empty;
        }
      }
    }
    leaf mtu {
      tailf:info
        "Set the interface Maximum Transmission Unit (MTU)";
      tailf:cli-full-command;
      type uint16 {
        tailf:info
          "<64-18000>;;MTU size in bytes";
        range "64..18000";
      }
    }
    container ntp {
      tailf:info
        "Configure NTP";
      container broadcast {
        tailf:info
          "Configure NTP broadcast service";
        presence "true";
        container client {
          tailf:info
            "Listen to NTP broadcasts";
          tailf:cli-full-command;
          presence "true";
        }
        list destination {
          tailf:info
            "Configure broadcast destination address";
          tailf:cli-suppress-mode;
          tailf:cli-delete-when-empty;
          tailf:cli-compact-syntax;
          tailf:cli-reset-container;
          key "address";
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
          leaf address {
            type inet:ipv4-address {
              tailf:info
                "A.B.C.D;;Destination broadcast IP address";
            }
          }
        }
        container version-key {
          tailf:cli-drop-node-name;
          tailf:cli-compact-syntax;
          tailf:cli-reset-container;
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
        }
      }
      leaf disable {
        tailf:info
          "Disable NTP traffic (both IP and IPv6)";
        tailf:cli-full-command;
        type empty;
      }
      container multicast {
        tailf:info
          "Configure NTP multicast service";
        tailf:cli-display-separated;
        tailf:cli-compact-syntax;
        presence "true";
        list address-list {
          tailf:cli-drop-node-name;
          tailf:cli-suppress-mode;
          tailf:cli-delete-when-empty;
          tailf:cli-compact-syntax;
          key "group-address";
          leaf group-address {
            type union {
              type inet:ipv4-address {
                tailf:info
                  "A.B.C.D;;Multicast group IP address";
              }
              type inet:ipv6-address {
                tailf:info
                  "X:X:X:X::X;;Multicast group IPv6 address";
              }
            }
          }
          leaf version {
            tailf:info
              "Configure NTP version";
            type uint8 {
              tailf:info
                "<1-4>;;NTP version number";
              range "1..4";
            }
          }
          leaf key {
            tailf:info
              "Configure multicast authentication key";
            type uint32 {
              tailf:info
                "<0-4294967295>;;Multicast key number";
            }
          }
          leaf ttl {
            tailf:info
              "TTL of the multicast packet";
            type uint8 {
              tailf:info
                "<1-255>;;TTL";
              range "1..255";
            }
          }
        }
        leaf version {
          tailf:info
            "Configure NTP version";
          type uint8 {
            tailf:info
              "<1-4>;;NTP version number";
            range "1..4";
          }
        }
        leaf key {
          tailf:info
            "Configure multicast authentication key";
          type uint32 {
            tailf:info
              "<0-4294967295>;;Multicast key number";
          }
        }
        leaf ttl {
          tailf:info
            "TTL of the multicast packet";
          type uint8 {
            tailf:info
              "<1-255>;;TTL";
            range "1..255";
          }
        }
        container client-list {
          tailf:cli-drop-node-name;
          leaf-list client {
            tailf:info
              "Listen to NTP multicasts";
            tailf:cli-list-syntax;
            tailf:cli-suppress-list-no;
            tailf:cli-incomplete-no;
            type union {
              type inet:ipv4-address {
                tailf:info
                  "A.B.C.D;;Multicast client IP address";
              }
              type inet:ipv6-address {
                tailf:info
                  "X:X:X:X::X;;Multicast client IPv6 address";
              }
            }
          }
        }
        leaf client {
          tailf:info
            "Listen to NTP multicasts";
          tailf:cli-full-command;
          type empty;
        }
      }
    }
    container power {
      container inline {
        leaf consumption {
          tailf:cli-full-command;
          type uint16 {
            range "4000..15400";
          }
        }
      }
    }
    list rate-limit {
      tailf:info
        "Rate Limit";
      tailf:cli-suppress-mode;
      tailf:cli-delete-when-empty;
      tailf:cli-compact-syntax;
      key "dir bps bc be conform-action exceed-action";
      leaf dir {
        type enumeration {
          enum "input" {
            tailf:info
              "Rate limit on input";
          }
          enum "output" {
            tailf:info
              "Rate limit on output";
          }
        }
      }
      leaf dscp {
        tailf:info
          "Match dscp value";
        type uint8 {
          tailf:info
            "<0-63>;;dscp";
          range "0..63";
        }
      }
      leaf bps {
        tailf:info
          "<8000-2000000000>;;Bits per second";
        type police-bps-type;
      }
      leaf bc {
        type uint32 {
          tailf:info
            "<1000-512000000>;;Normal burst bytes";
          range "1000..512000000";
        }
      }
      leaf be {
        type uint32 {
          tailf:info
            "<2000-1024000000>;;Maximum burst bytes";
          range "2000..1024000000";
        }
      }
      leaf conform-action {
        tailf:cli-expose-key-name;
        type enumeration {
          enum "transmit";
        }
      }
      leaf exceed-action {
        tailf:cli-expose-key-name;
        type enumeration {
          enum "drop";
        }
      }
    }
    container service-policy {
      tailf:info
        "Configure QoS Service Policy";
      leaf history {
        tailf:cli-full-command;
        tailf:info
          "Keep history of QoS metrics";
        type empty;
      }
      uses service-policy-grouping;
      container type {
        tailf:info
          "Configure CPL Service Policy";
        container performance-monitor {
          tailf:info
            "Configure media monitor service-policy type";
          tailf:cli-sequence-commands;
          tailf:cli-compact-syntax;
          leaf direction {
            tailf:cli-drop-node-name;
            type enumeration {
              enum "input" {
                tailf:info
                  "Assign policy-map to the input of an interfcae";
              }
              enum "output" {
                tailf:info
                  "Assign policy-map to the output of an interfcae";
              }
            }
          }
          leaf name {
            tailf:cli-drop-node-name;
            type string {
              tailf:info
                "WORD;;policy-map name";
            }
            tailf:non-strict-leafref {
              path "/ncs:devices/ncs:device/ncs:config/ios:policy-map/name" {
                tailf:xpath-root 3;
              }
            }
          }
        }
      }
    }
    leaf shutdown {
      tailf:info
        "Shutdown the selected interface";
      tailf:cli-full-command;
      tailf:cli-show-no;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        type empty;
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        key "group-number";
        leaf group-number {
          tailf:cli-suppress-range;
          type uint16 {
            tailf:info
              "<0-255>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-compact-syntax;
                tailf:cli-sequence-commands {
                  tailf:cli-reset-siblings;
                }
                leaf encrypt {
                  tailf:cli-drop-node-name;
                  type enumeration {
                    enum "0" {
                      tailf:info
                        "Specifies an UNENCRYPTED key string will follow";
                    }
                    enum "7" {
                      tailf:info
                        "Specifies a HIDDEN key string will follow";
                    }
                  }
                }
                leaf string {
                  tailf:cli-drop-node-name;
                  type string {
                    tailf:info
                      "WORD;;Key string (64 chars max)";
                  }
                }
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-sequence-commands;
          tailf:cli-compact-syntax;
          tailf:cli-delete-when-empty;
          presence "true";
          leaf address {
            tailf:cli-drop-node-name;
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container preempt {
          tailf:info
            "Overthrow lower priority Active routers";
          tailf:cli-delete-when-empty;
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        leaf priority {
          tailf:info
            "Priority level";
          tailf:cli-full-command;
          type uint8 {
            tailf:info
              "<0-255>;;Priority value";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-compact-syntax;
                  tailf:cli-sequence-commands {
                    tailf:cli-reset-siblings;
                  }
                  leaf encrypt {
                    tailf:cli-drop-node-name;
                    type enumeration {
                      enum "0" {
                        tailf:info
                          "Specifies an UNENCRYPTED key string will follow";
                      }
                      enum "7" {
                        tailf:info
                          "Specifies a HIDDEN key string will follow";
                      }
                    }
                  }
                  leaf string {
                    tailf:cli-drop-node-name;
                    type string {
                      tailf:info
                        "WORD;;Key string (64 chars max)";
                    }
                  }
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
        list track {
          tailf:info
            "Priority tracking";
          tailf:cli-suppress-mode;
          tailf:cli-delete-when-empty;
          tailf:cli-incomplete-command;
          tailf:cli-compact-syntax;
          key "name";
          leaf name {
            tailf:cli-suppress-range;
            type union {
              type uint16 {
                tailf:info
                  "<0-500>;;Tracked object number";
              }
              type string {
                tailf:info
                  "WORD;;Interface name";
              }
            }
          }
          choice options {
            case interface {
              leaf priority-decrement {
                tailf:cli-drop-node-name;
                type uint16 {
                  tailf:info
                    "<1-255>;;Decrement value";
                }
              }
            }
            case group-number {
              leaf decrement {
                tailf:info
                  "Priority decrement";
                tailf:cli-full-command;
                type uint16 {
                  tailf:info
                    "<1-255>;;Decrement value";
                }
              }
              leaf shutdown {
                tailf:info
                  "Shutdown group";
                tailf:cli-full-command;
                type empty;
              }
            }
          }
        }
      }
    }
    container storm-control {
      tailf:info
        "storm configuration";
      container action {
        tailf:info
          "Action to take for storm-control";
        leaf shutdown {
          tailf:info
            "Shutdown this interface if a storm occurs";
          tailf:cli-full-command;
          type empty;
        }
        leaf trap {
          tailf:info
            "Send SNMP trap if a storm occurs";
          tailf:cli-full-command;
          type empty;
        }
        leaf level {
          tailf:info
            "Set storm suppression level on this interface";
          tailf:cli-full-command;
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
        container include {
          tailf:info
            "include other traffic types";
          leaf multicast {
            tailf:info
              "Suppress broadcast and multicast traffic";
            type empty;
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list dscp-map {
        tailf:info
          "Configure dscp-map for a queue threshold";
        tailf:cli-suppress-mode;
        tailf:cli-delete-when-empty;
        tailf:cli-compact-syntax;
        key "queue threshold";
        leaf queue {
          type uint8 {
            tailf:info
              "<1-7>;;enter dscp-map queue id";
          }
        }
        leaf threshold {
          type uint8 {
            tailf:info
              "<1-4>;;enter dscp-map threshold id";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
        leaf weight-d {
          tailf:cli-drop-node-name;
          type uint8 {
            tailf:info
              "<0-100>;;enter queue size weight";
            range "0..100";
          }
        }
        leaf weight-e {
          tailf:cli-drop-node-name;
          type uint8 {
            tailf:info
              "<0-100>;;enter queue size weight";
            range "0..100";
          }
        }
        leaf weight-f {
          tailf:cli-drop-node-name;
          type uint8 {
            tailf:info
              "<0-100>;;enter queue size weight";
            range "0..100";
          }
        }
        leaf weight-g {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses queue-size-grouping;
      }
    }
    container priority-queue {
      tailf:info
        "Configure priority scheduling";
      leaf queue-limit {
        tailf:info
          "configure priority queue limit";
        tailf:cli-full-command;
        type uint8 {
          tailf:info
            "<0-100>;;enter queue size weight";
          range "0..100";
        }
      }
      list dscp-map {
        tailf:info
          "Configure dscp-map for a queue threshold";
        tailf:cli-suppress-mode;
        tailf:cli-delete-when-empty;
        tailf:cli-compact-syntax;
        tailf:cli-incomplete-command;
        key "id";
        leaf id {
          type uint8 {
            tailf:info
              "<1-1>;;enter priority queue id";
            range "1";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      container cos-map {
        tailf:info
          "Configure cos-map for a queue";
        tailf:cli-compact-syntax;
        tailf:cli-sequence-commands;
        leaf id {
          tailf:cli-drop-node-name;
          tailf:cli-incomplete-command;
          type uint8 {
            tailf:info
              "<1-1>;;enter cos-map queue id";
            range "1";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf primary {
          tailf:info
            "Primary Edge Port";
          tailf:cli-optional-in-sequence;
          when '../edge' {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
    container clns {
      tailf:info
        "CLNS interface subcommands";
      leaf route-cache {
        tailf:cli-boolean-no;
        tailf:cli-full-command;
        type boolean;
        default "true";
      }
    }
    container dsu {
      leaf bandwidth {
        tailf:cli-full-command;
        type uint32;
      }
    }
    container isdn {
      tailf:info
        "ISDN Interface configuration commands";
      leaf switch-type {
        tailf:info
          "Select the Interface ISDN switch type";
        tailf:cli-full-command;
        type string {
          pattern 'primary.*';
        }
      }
      leaf protocol-emulate {
        tailf:info
          "Protocol (L2/L3) emulation network/user side";
        tailf:cli-full-command;
        type enumeration {
          enum "network" {
            tailf:info
              "ISDN protocol emulation network side";
          }
          enum "user" {
            tailf:info
              "ISDN protocol emulation user side (default)";
          }
        }
      }
      container incoming-voice {
        tailf:info
          "Specify options for incoming calls.";
        choice incoming-voice-choice {
          leaf voice {
            tailf:info
              "Incoming voice calls will be handled as voice.";
            type empty;
          }
          container data {
            tailf:info
              "Incoming voice calls will be handled as data.";
            tailf:cli-delete-when-empty;
            presence "true";
            leaf kbps {
              tailf:cli-drop-node-name;
              type enumeration {
                enum "56" {
                  tailf:info
                    "56  B Channel Bandwidth of 56Kb/s";
                }
                enum "64" {
                  tailf:info
                    "64  B Channel Bandwidth of 64Kb/s";
                }
              }
            }
          }
          container modem {
            tailf:info
              "Incoming voice calls will be handled as modems.";
            tailf:cli-delete-when-empty;
            presence "true";
            leaf kbps {
              tailf:cli-drop-node-name;
              type enumeration {
                enum "56" {
                  tailf:info
                    "56  B Channel Bandwidth of 56Kb/s  ";
                }
                enum "64" {
                  tailf:info
                    "64  B Channel Bandwidth of 64Kb/s";
                }
              }
            }
          }
        }
      }
      container supp-service {
        tailf:info
          "Specify the subscribed supplementary service";
        container name {
          tailf:info
            "Specify the subscribed name service";
          container calling {
            tailf:info
              "calling name service";
            tailf:cli-delete-when-empty;
            presence "true";
          }
        }
      }
    }
    leaf trunk-group {
      tailf:info
        "Configure interface to be in a trunk group";
      type string {
        tailf:info
          "WORD;;Trunk group label";
      }
      tailf:non-strict-leafref {
        path "/ncs:devices/ncs:device/ncs:config/ios:trunk/group/name" {
          tailf:xpath-root 3;
        }
      }
    }
    container crypto {
      tailf:info
        "Encryption/Decryption commands";
      container map {
        tailf:info
          "Assign a Crypto Map";
        container ipv4 {
          tailf:cli-drop-node-name;
          tailf:cli-compact-syntax;
          tailf:cli-sequence-commands {
            tailf:cli-reset-siblings;
          }
          leaf map-name {
            tailf:cli-drop-node-name;
            tailf:cli-disallow-value "ipv6";
            type string {
              tailf:info
                "WORD;;Crypto Map tag";
            }
            tailf:non-strict-leafref {
              path "/ncs:devices/ncs:device/ncs:config/ios:crypto/map/name" {
                tailf:xpath-root 3;
              }
            }
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
        container ipv6 {
          tailf:cli-compact-syntax;
          tailf:cli-sequence-commands {
            tailf:cli-reset-siblings;
          }
          leaf map-name {
            tailf:cli-drop-node-name;
            type string {
              tailf:info
                "WORD;;Crypto Map tag";
            }
            tailf:non-strict-leafref {
              path "/ncs:devices/ncs:device/ncs:config/ios:crypto/map/name" {
                tailf:xpath-root 3;
              }
            }
          }
          leaf redundancy {
            tailf:info
              "enable redundancy";
            type string {
              tailf:info
                "WORD;;Name of IP Redundancy Group";
            }
          }
          leaf stateful {
            tailf:info
              "enable stateful failover";
            when '../redundancy' {
              tailf:xpath-root 3;
            }
            type empty;
          }
        }
      }
    }
    container routing {
      tailf:info
        "Per-interface routing configuration";
      leaf dynamic {
        tailf:info
          "participates in routing protocols";
        tailf:cli-boolean-no;
        tailf:cli-full-command;
        type boolean;
        default "true";
      }
    }
  }

  grouping interface-tunnel-grouping {
    container tunnel {
      tailf:info
        "protocol-over-protocol tunneling";
      leaf source {
        tailf:info
          "source of tunnel packets";
        type string;
      }
      leaf destination {
        tailf:info
          "destination of tunnel";
        type host-v4v6-type;
      }
      container mode {
        tailf:info
          "tunnel encapsulation method";
        choice mode-choice {
          container ipsec {
            tailf:info
              "IPSec tunnel encapsulation";
            container ipv4 {
              tailf:info
                "over IPv4";
              tailf:cli-delete-when-empty;
              presence "true";
            }
          }
          container mpls {
            container traffic-eng {
              tailf:cli-delete-when-empty;
              presence "true";
              leaf gre-ip {
                type empty;
              }
            }
          }
        }
      }
      container path-mtu-discovery {
        tailf:info
          "Enable Path MTU Discovery on tunnel";
        presence "true";
      }
      container protection {
        tailf:info
          "Enable tunnel protection";
        container ipsec {
          tailf:info
            "Use ipsec to protect this tunnel interface";
          leaf profile {
            tailf:info
              "Determine the ipsec policy profile to use.";
            type string {
              tailf:info
                "WORD;;IPSec policy profile";
            }
            tailf:non-strict-leafref {
              path "/ncs:devices/ncs:device/ncs:config/ios:crypto/ipsec/profile/name" {
                tailf:xpath-root 3;
              }
            }
          }
        }
      }
      container mpls {
        container traffic-eng {
          container affinity {
            tailf:cli-sequence-commands {
              tailf:cli-reset-siblings;
            }
            tailf:cli-compact-syntax;
            leaf attributes {
              tailf:cli-drop-node-name;
              type string;
            }
            leaf mask {
              type string;
            }
          }
          container autoroute {
            leaf announce {
              tailf:cli-full-command;
              type empty;
            }
          }
          container priority {
            tailf:cli-sequence-commands {
              tailf:cli-reset-siblings;
            }
            tailf:cli-compact-syntax;
            leaf setup-priority {
              tailf:cli-drop-node-name;
              type uint8 {
                range "0..7";
              }
            }
            leaf hold-priority {
              tailf:cli-drop-node-name;
              type uint8 {
                range "0..7";
              }
            }
          }
          leaf bandwidth {
            tailf:cli-full-command;
            type uint32;
          }
          list path-option {
            tailf:cli-suppress-mode;
            tailf:cli-delete-when-empty;
            tailf:cli-sequence-commands {
              tailf:cli-reset-siblings;
            }
            tailf:cli-compact-syntax;
            key "id";
            leaf id {
              type uint32;
            }
            choice path-option-choice {
              container dynamic {
                presence "true";
              }
              container explicit {
                tailf:cli-compact-syntax;
                choice explicit-choice {
                  leaf name {
                    type string;
                  }
                  leaf identifier {
                    type uint32;
                  }
                }
              }
            }
            container lockdown {
              presence "true";
            }
          }
          container fast-reroute {
            presence "true";
          }
        }
      }
    }
  }

  grouping interface-ethernet-pre-grouping {
    leaf port-type {
      tailf:info
        "Set port type";
      type enumeration {
        enum "eni" {
          tailf:info
            "Set port-type to ENI";
        }
        enum "nni" {
          tailf:info
            "Set port-type to NNI";
        }
        enum "uni" {
          tailf:info
            "Set port-type to UNI";
        }
      }
    }
  }

  grouping interface-ethernet-grouping {
    leaf media-type {
      tailf:info
        "Media type";
      tailf:cli-full-command;
      type enumeration {
        enum "rj45" {
          tailf:info
            "Copper";
        }
        enum "sfp" {
          tailf:info
            "Fiber";
        }
        enum "auto-select" {
          tailf:info
            "Auto Select";
        }
      }
    }
    container carrier-delay {
      tailf:info
        "Specify delay for interface transitions";
      choice delay-choice {
        leaf seconds {
          tailf:cli-drop-node-name;
          type uint8 {
            tailf:info
              "<0-60>;;Carrier Transitions delay seconds";
            range "0..60";
          }
        }
        leaf msec {
          tailf:info
            "delay specified in milliseconds";
          type uint16 {
            tailf:info
              "<0-1000>;;Carrier Transitions delay milliseconds";
            range "0..1000";
          }
        }
      }
    }
    container channel-group {
      tailf:info
        "Add this interface to an Etherchannel group";
      tailf:cli-sequence-commands {
        tailf:cli-reset-siblings;
      }
      tailf:cli-compact-syntax;
      leaf number {
        tailf:cli-drop-node-name;
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container ethernet {
      tailf:info
        "Ethernet interface parameters";
      container oam {
        tailf:info
          "To enable Ethernet Link OAM";
        presence "true";
        leaf max-rate {
          type uint8 {
            tailf:info
              "Maximum number of OAM PDUs sent per second";
            range "1..10";
          }
        }
        leaf min-rate {
          type uint8 {
            tailf:info
              "Minimum transmission rate in seconds";
            range "1..10";
          }
        }
        leaf mode {
          type enumeration {
            enum "active" {
              tailf:info
                "Active OAM client mode";
            }
            enum "passive" {
              tailf:info
                "Passive OAM client mode";
            }
          }
        }
        leaf timeout {
          type uint8 {
            tailf:info
              "OAM client timeout in seconds";
            range "2..30";
          }
        }
      }
      container dot1ad {
        tailf:info
          "dot1ad port";
        choice dot1ad-choice {
          leaf nni {
            tailf:info
              "dot1ad nni port";
            type empty;
          }
          container uni {
            tailf:info
              "dot1ad uni";
            choice uni-choice {
              container c-port {
                tailf:info
                  "dot1ad uni customer bridge port";
                tailf:cli-delete-when-empty;
                presence "true";
                leaf isolate {
                  tailf:info
                    "split horizon";
                  type empty;
                }
              }
              container s-port {
                tailf:info
                  "dot1ad uni s bridge port";
                tailf:cli-delete-when-empty;
                presence "true";
                leaf isolate {
                  tailf:info
                    "split horizon";
                  type empty;
                }
              }
            }
          }
        }
      }
      container cfm {
        tailf:info
          "Ethernet CFM interface commands";
        container mep {
          tailf:info
            "Maintenance End Point";
          list mep-list {
            tailf:cli-drop-node-name;
            tailf:cli-suppress-mode;
            tailf:cli-delete-when-empty;
            tailf:cli-compact-syntax;
            tailf:cli-sequence-commands;
            key "mpid";
            leaf mpid {
              tailf:info
                "Maintenance End Point Identifier";
              tailf:cli-expose-key-name;
              type uint16 {
                tailf:info
                  "<1-8191>;;Maintenance End Point Identifier";
                range "1..8191";
              }
            }
            leaf domain {
              tailf:info
                "maintenance domain";
              tailf:cli-prefix-key;
              type string {
                tailf:info
                  "WORD;;maintenance domain name";
              }
            }
            container service {
              tailf:info
                "Maintenance Association within Domain";
              tailf:cli-flatten-container;
              tailf:cli-compact-syntax;
              choice service-choice {
                leaf short-ma-name {
                  tailf:cli-drop-node-name;
                  type string {
                    tailf:info
                      "WORD;;service instance id - short MA name";
                  }
                }
                leaf number {
                  tailf:info
                    "Maintenance Association number value";
                  type uint16 {
                    tailf:info
                      "<0-65535>;;Maintenance Association number";
                  }
                }
              }
            }
          }
        }
      }
    }
    container negotiation {
      tailf:info
        "Select autonegotiation mode";
      leaf auto {
        tailf:info
          "Enable link autonegotiation";
        tailf:cli-boolean-no;
        type boolean;
      }
    }
    container synchronous {
      tailf:info
        "Synchronous";
      leaf mode {
        tailf:info
          "Mode";
        type empty;
      }
    }
    leaf duplex {
      tailf:info
        "Configure duplex operation.";
      tailf:cli-no-value-on-delete;
      tailf:cli-diff-dependency "../media-type" {
        tailf:xpath-root 3;
      }
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
    }
    leaf full-duplex {
      tailf:info
        "Configure full-duplex operational mode";
      tailf:cli-full-command;
      type empty;
    }
    leaf speed {
      tailf:info
        "Configure speed operation.";
      tailf:cli-diff-dependency "../media-type" {
        tailf:xpath-root 3;
      }
      type enumeration {
        enum "10" {
          tailf:info
            "Force 10 Mbps operation";
        }
        enum "100" {
          tailf:info
            "Force 100 Mbps operation";
        }
        enum "1000" {
          tailf:info
            "Force 1000 Mbps operation";
        }
        enum "auto" {
          tailf:info
            "Enable AUTO speed configuration";
        }
        enum "nonegotiate";
      }
    }
    uses interface-xconnect-grouping;
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
    container service {
      tailf:info
        "Configure Ether Service";
      tailf:cli-diff-dependency "../switchport" {
        tailf:xpath-root 3;
      }
      list instance {
        tailf:info
          "Configure Ether Service Instance";
        tailf:cli-mode-name "config-if-srv";
        tailf:cli-compact-syntax;
        tailf:cli-sequence-commands;
        tailf:cli-incomplete-command;
        tailf:cli-diff-dependency "../../switchport" {
          tailf:xpath-root 3;
        }
        key "id";
        leaf id {
          type uint32 {
            tailf:info
              "<1-4294967295>;;Service Instance Identifier";
            range "1..4294967295";
          }
        }
        leaf trunk {
          tailf:cli-optional-in-sequence;
          tailf:cli-prefix-key;
          type empty;
        }
        leaf ethernet {
          tailf:info
            "Configure an Ethernet Instance";
          tailf:cli-hide-in-submode;
          type empty;
        }
        leaf ethernet-evc-name {
          tailf:cli-drop-node-name;
          tailf:cli-hide-in-submode;
          type string {
            tailf:info
              "WORD;;Attach an EVC to the service instance";
          }
          tailf:non-strict-leafref {
            path "/ncs:devices/ncs:device/ncs:config/ios:ethernet/evc/name" {
              tailf:xpath-root 3;
            }
          }
        }
        leaf description {
          tailf:cli-break-sequence-commands;
          tailf:info
            "Service instance specific description";
          tailf:cli-multi-value;
          tailf:cli-full-command;
          type string {
            tailf:info
              "LINE;;Up to 240 characters describing this service instance";
            length "0..240";
          }
        }
        leaf evc-name {
          tailf:cli-drop-node-name;
          tailf:cli-hide-in-submode;
          type string {
            tailf:info
              "WORD;;Attach an EVC to the service instance";
            length "1..100";
          }
        }
        container encapsulation {
          tailf:info
            "Configure ethernet frame match criteria";
          container dot1q {
            tailf:info
              "IEEE 802.1Q Virtual LAN or S-VLAN";
            tailf:cli-compact-syntax;
            tailf:cli-sequence-commands {
              tailf:cli-reset-siblings;
            }
            leaf-list id {
              tailf:cli-drop-node-name;
              tailf:cli-replace-all;
              tailf:cli-range-list-syntax;
              type union {
                type uint16 {
                  tailf:info
                    "<1-4094>;;VLAN id";
                  range "1..4094";
                }
                type enumeration {
                  enum "any" {
                    tailf:info
                      "For all VLANS [1-4094]";
                  }
                }
              }
            }
            leaf second-dot1q {
              tailf:cli-break-sequence-commands;
              tailf:info
                "inner 802.1Q Virtual LAN or C-VLAN";
              type union {
                type uint16 {
                  tailf:info
                    "<1-4094>;;VLAN id";
                  range "1..4094";
                }
                type enumeration {
                  enum "any" {
                    tailf:info
                      "For all VLANS [1-4094]";
                  }
                }
              }
            }
            leaf cos {
              tailf:info
                "cos Vlan";
              type uint8 {
                tailf:info
                  "<0-7>;;cos values";
                range "0..7";
              }
            }
            leaf etype {
              tailf:info
                "payload ethertype after Vlan Field";
              type enumeration {
                enum "ipv4" {
                  tailf:info
                    "IPv4";
                }
                enum "ipv6" {
                  tailf:info
                    "IPv6";
                }
                enum "pppoe-all" {
                  tailf:info
                    "PPPoE ALL";
                }
                enum "pppoe-discovery" {
                  tailf:info
                    "PPPoE Discovery Stage";
                }
                enum "pppoe-session" {
                  tailf:info
                    "PPPoE Session Stage";
                }
              }
            }
          }
          container dot1ad {
            tailf:cli-compact-syntax;
            tailf:cli-sequence-commands {
              tailf:cli-reset-siblings;
            }
            leaf-list id {
              tailf:cli-drop-node-name;
              tailf:cli-replace-all;
              tailf:cli-range-list-syntax;
              type union {
                type uint16 {
                  tailf:info
                    "<1-4094>;;VLAN id";
                  range "1..4094";
                }
              }
            }
          }
          container untagged {
            tailf:info
              "Untagged encapsulation";
            presence "true";
          }
          container default {
            tailf:info
              "catch-all unconfigured encapsulation";
            presence "true";
          }
        }
        container rewrite {
          tailf:info
            "Configure ethernet rewrite criteria";
          container ingress {
            tailf:info
              "Ingress Rewrite";
            container tag {
              tailf:info
                "Configure Rewrite Tag";
              tailf:cli-compact-syntax;
              tailf:cli-sequence-commands {
                tailf:cli-reset-siblings;
              }
              choice tag-choice {
                leaf pop {
                  tailf:info
                    "Pop the tag";
                  type enumeration {
                    enum "1" {
                      tailf:info
                        "Pop the outermost tag";
                    }
                    enum "2" {
                      tailf:info
                        "Pop two outermost tags";
                    }
                  }
                }
                case push {
                  leaf push {
                    tailf:info
                      "Rewrite Operation of push";
                    type enumeration {
                      enum "dot1ad" {
                        tailf:info
                          "Push dot1ad tag";
                      }
                      enum "dot1q" {
                        tailf:info
                          "Push dot1q tag";
                      }
                    }
                  }
                  leaf vlan-id {
                    tailf:cli-drop-node-name;
                    type uint16 {
                      tailf:info
                        "<1-4094>;;VLAN id";
                      range "1..4094";
                    }
                  }
                }
              }
              leaf mode {
                tailf:cli-drop-node-name;
                type enumeration {
                  enum "symmetric" {
                    tailf:info
                      "Tag egress packets as specified in encapsulation";
                  }
                }
              }
            }
          }
        }
        leaf group {
          tailf:info
            "Join a service group";
          tailf:cli-full-command;
          type uint16 {
            tailf:info
              "<1-65532>;;Service group ID number";
            range "1..65532";
          }
        }
        container errdisable {
          tailf:info
            "Configure error disable";
          container recovery {
            tailf:info
              "enable auto recovery";
            container cause {
              tailf:info
                "error disable cause";
              leaf mac-security {
                tailf:info
                  "mac-security violation";
                type uint32 {
                  tailf:info
                    "<30-86400>;;timer interval(sec)";
                  range "30..86400";
                }
              }
            }
          }
        }
        container snmp {
          tailf:info
            "Modify SNMP service instance parameters";
          container trap {
            tailf:info
              "Allow a specific SNMP trap";
            leaf link-status {
              tailf:info
                "Allow SNMP LINKUP and LINKDOWN traps";
              type empty;
            }
          }
          container ifindex {
            tailf:info
              "Persist ifindex for the service instance";
            leaf persist {
              tailf:info
                "Enable/Disable ifIndex persistence";
              type empty;
            }
          }
        }
        leaf shutdown {
          tailf:info
            "Take the Service Instance out of Service";
          type empty;
        }
        container bridge-domain {
          tailf:info
            "Bridge-domain";
          tailf:cli-compact-syntax;
          tailf:cli-sequence-commands {
            tailf:cli-reset-all-siblings;
          }
          leaf from-encapsulation {
            tailf:info
              "Derive bridge domains from encapsulation vlan list,";
            tailf:cli-optional-in-sequence;
            tailf:cli-full-command;
            type empty;
          }
          leaf bridge-id {
            tailf:cli-drop-node-name;
            type uint16 {
              tailf:info
                "<1-16384>;;Bridge-domain number";
            }
          }
          container split-horizon {
            tailf:info
              "Configure this port as a member of a split horizon group";
            tailf:cli-flatten-container;
            leaf group {
              tailf:info
                "Split-horizon group";
              type uint8 {
                tailf:info
                  "<0-2>;;Split-horizon group number";
                range "0..2";
              }
            }
          }
        }
        container mac {
          tailf:info
            "Commands for MAC Address-based features";
          container security {
            tailf:info
              "MAC Security commands";
            tailf:cli-display-separated;
            tailf:cli-delete-when-empty;
            presence "true";
            list address {
              tailf:info
                "MAC Address";
              tailf:cli-suppress-mode;
              tailf:cli-delete-when-empty;
              key "operation mac-address";
              leaf operation {
                type enumeration {
                  enum "deny" {
                    tailf:info
                      "Specify an address that must not be learnt";
                  }
                  enum "permit" {
                    tailf:info
                      "Specify an address to statically configure in the MAC table";
                  }
                }
              }
              leaf mac-address {
                type string {
                  tailf:info
                    "H.H.H;;Specify the 48-bit MAC Address to deny/permit";
                }
              }
            }
            container maximum {
              tailf:info
                "Configure an upper bound";
              leaf addresses {
                tailf:info
                  "Maximum addresses that can be learnt on this service instance";
                type uint16 {
                  tailf:info
                    "<1-1000>;;Address count";
                  range "1..1000";
                }
              }
            }
            leaf violation {
              tailf:info
                "Configure the response when a MAC security policy is violated";
              tailf:cli-full-command;
              type enumeration {
                enum "protect" {
                  tailf:info
                    "Protect mode - don't report violations, drop violating frames";
                }
                enum "restrict" {
                  tailf:info
                    "Restrict mode - report violations, drop violating frames";
                }
              }
            }
          }
          container static {
            tailf:info
              "static MAC address";
            list address {
              tailf:info
                "MAC Address";
              tailf:cli-suppress-mode;
              tailf:cli-delete-when-empty;
              key "mac-addr";
              leaf mac-addr {
                type string {
                  tailf:info
                    "H.H.H;;Specify the 48-bit Static MAC Address";
                }
              }
            }
          }
          list access-group {
            tailf:info
              "Specify access control for packets";
            tailf:cli-suppress-mode;
            tailf:cli-delete-when-empty;
            tailf:cli-compact-syntax;
            tailf:cli-sequence-commands;
            key "direction";
            leaf direction {
              type enumeration {
                enum "in" {
                  tailf:info
                    "Apply to Ingress";
                }
                enum "out" {
                  tailf:info
                    "Apply to Egress";
                }
              }
            }
            leaf access-list {
              tailf:cli-drop-node-name;
              tailf:cli-prefix-key;
              type string {
                tailf:info
                  "WORD;;ACL name";
              }
            }
          }
        }
        container l2protocol {
          tailf:info
            "Configure l2 control protocol processing";
          container peer {
            tailf:info
              "peer L2 control protocol packets as data";
            presence "true";
            leaf-list protocol {
              tailf:cli-drop-node-name;
              tailf:cli-flat-list-syntax;
              type enumeration {
                enum "cdp" {
                  tailf:info
                    "Cisco Discovery Protocol";
                }
                enum "dtp" {
                  tailf:info
                    "Dynamic Trunking Protocol";
                }
                enum "lacp" {
                  tailf:info
                    "LACP Protocol";
                }
                enum "lldp" {
                  tailf:info
                    "Link Layer Discovery Protocol";
                }
                enum "pagp" {
                  tailf:info
                    "Port Aggregation Protocol";
                }
                enum "stp" {
                  tailf:info
                    "Spanning Tree Protocol";
                }
                enum "udld" {
                  tailf:info
                    "UDLD Protocol";
                }
                enum "vtp" {
                  tailf:info
                    "Vlan Trunking Protocol";
                }
              }
            }
          }
          container forward {
            tailf:info
              "forward L2 control protocol packets as data";
            presence "true";
            leaf-list protocol {
              tailf:cli-drop-node-name;
              tailf:cli-flat-list-syntax;
              type enumeration {
                enum "cdp" {
                  tailf:info
                    "Cisco Discovery Protocol";
                }
                enum "dtp" {
                  tailf:info
                    "Dynamic Trunking Protocol";
                }
                enum "lacp" {
                  tailf:info
                    "LACP Protocol";
                }
                enum "lldp" {
                  tailf:info
                    "Link Layer Discovery Protocol";
                }
                enum "pagp" {
                  tailf:info
                    "Port Aggregation Protocol";
                }
                enum "stp" {
                  tailf:info
                    "Spanning Tree Protocol";
                }
                enum "udld" {
                  tailf:info
                    "UDLD Protocol";
                }
                enum "vtp" {
                  tailf:info
                    "Vlan Trunking Protocol";
                }
              }
            }
          }
          container tunnel {
            tailf:info
              "tunnel L2 control protocol packets as data";
            presence "true";
          }
        }
        container service-policy {
          tailf:info
            "Attach a policy-map to an EFP";
          tailf:cli-diff-dependency "/ios:policy-map" {
            tailf:xpath-root 3;
          }
          list input {
            tailf:info
              "service policy input";
            tailf:cli-suppress-mode;
            tailf:cli-delete-when-empty;
            max-elements 1;
            key "name";
            leaf name {
              type string {
                tailf:info
                  "WORD;;input Policy-map name";
              }
              tailf:non-strict-leafref {
                path "/ncs:devices/ncs:device/ncs:config/ios:policy-map/name" {
                  tailf:xpath-root 3;
                }
              }
            }
          }
          list output {
            tailf:info
              "service policy output";
            tailf:cli-suppress-mode;
            tailf:cli-delete-when-empty;
            max-elements 1;
            key "name";
            leaf name {
              type string {
                tailf:info
                  "WORD;;output Policy-map name";
              }
              tailf:non-strict-leafref {
                path "/ncs:devices/ncs:device/ncs:config/ios:policy-map/name" {
                  tailf:xpath-root 3;
                }
              }
            }
          }
        }
        uses interface-xconnect-grouping;
        container cfm {
          tailf:info
            "Ethernet CFM EFP subcommands";
          container mep {
            tailf:info
              "Maintenance End Point";
            tailf:cli-add-mode;
            tailf:cli-mode-name "config-if-srv-ecfm-mep";
            tailf:cli-compact-syntax;
            tailf:cli-sequence-commands;
            leaf domain {
              tailf:info
                "Configure a domain for this mep";
              tailf:cli-hide-in-submode;
              tailf:cli-incomplete-command;
              type string {
                tailf:info
                  "WORD;;maintenance domain name";
              }
            }
            leaf mpid {
              tailf:info
                "Maintenance End Point Identifier";
              tailf:cli-hide-in-submode;
              type uint16 {
                tailf:info
                  "<1-8191>;;Maintenance End Point Identifier";
                range "1..8191";
              }
            }
            container continuity-check {
              tailf:info
                "Enable Continuity Check for this local MEP";
              tailf:cli-break-sequence-commands;
              container static {
                tailf:info
                  "Verify MEP in received CCM is valid";
                leaf rmep {
                  tailf:info
                    "MEP defined using rmep mpid";
                  type empty;
                }
              }
            }
            container rmep {
              tailf:info
                "Static Remote MEP associated with this DOWN MEP";
              leaf mpid {
                tailf:info
                  "Maintenance End Point Identifier";
                type uint16 {
                  tailf:info
                    "<1-8191>;;Identifier value";
                  range "1..8191";
                }
              }
            }
            leaf cos {
              tailf:info
                "Specify Class of Service sent in CFM mssages for EFP MEP";
              type uint8 {
                tailf:info
                  "<0-7>;;CoS value";
                range "0..7";
              }
            }
          }
        }
        container ethernet-if-srv {
          tailf:cli-drop-node-name;
          container ethernet {
            tailf:info
              "ethernet";
            container lmi {
              tailf:info
                "Configure ether lmi parameters";
              container ce-vlan {
                tailf:info
                  "Configure ether lmi customer vlans";
                leaf-list map {
                  tailf:info
                    "Configure ether lmi ce-vlan/evc map";
                  tailf:cli-replace-all;
                  tailf:cli-range-list-syntax;
                  type union {
                    type uint16 {
                      tailf:info
                        "<1-4094>;;VLAN id";
                      range "1..4094";
                    }
                    type enumeration {
                      enum "default" {
                        tailf:info
                          "Default EFP";
                      }
                      enum "untagged" {
                        tailf:info
                          "Untagged frames";
                      }
                    }
                  }
                }
              }
            }
            container loopback {
              tailf:info
                "Ethernet Dataplane Loopback";
              container permit {
                tailf:info
                  "Allow data plane loopback to be activated";
                leaf external {
                  tailf:info
                    "Allow to loopback the traffic from the wire";
                  type empty;
                }
                leaf internal {
                  tailf:info
                    "Allow to loopback the traffic from the relay";
                  type empty;
                }
              }
            }
          }
        }
      }
    }
  }

  grouping interface-zone-member-grouping {
    container zone-member {
      tailf:info
        "Apply zone name";
      leaf security {
        tailf:info
          "Security zone";
        type string;
        tailf:non-strict-leafref {
          path "/ncs:devices/ncs:device/ncs:config/ios:zone/security/id" {
            tailf:xpath-root 3;
          }
        }
      }
    }
  }

  grouping interface-pointtopoint-grouping {
    container ppp {
      tailf:info
        "Point-to-Point Protocol";
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container ipcp {
        tailf:info
          "Set IPCP negotiation options";
        container dns {
          tailf:info
            "Specify DNS negotiation options";
          tailf:cli-compact-syntax;
          tailf:cli-sequence-commands;
          leaf primary {
            tailf:cli-drop-node-name;
            type inet:ipv4-address {
              tailf:info
                "A.B.C.D;;Primary DNS IP address";
            }
          }
        }
      }
      container multilink {
        tailf:info
          "Make interface multilink capable";
        tailf:cli-display-separated;
        presence "true";
        leaf interleave {
          tailf:info
            "Allow interleaving of small packets with fragments";
          type empty;
        }
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          leaf disable {
            tailf:info
              "Suppress multilink fragmentation when possible";
            tailf:cli-full-command;
            type empty;
          }
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
        container queue {
          tailf:info
            "Specify link queuing parameters";
          container depth {
            tailf:info
              "Specify maximum depth for link transmit queues";
            leaf fifo {
              tailf:info
                "Set max depth for link queues when bundle has FIFO queuing";
              type uint8 {
                tailf:info
                  "<2-255>;;Max queue depth for link";
                range "2..255";
              }
            }
            leaf qos {
              tailf:info
                "Set max depth for link queues when bundle has non-FIFO queuing";
              type uint8 {
                tailf:info
                  "<2-255>;;Max queue depth for link";
                range "2..255";
              }
            }
          }
        }
      }
    }
    container dialer {
      tailf:info
        "Dial-on-demand routing (DDR) commands";
      container in-band {
        tailf:info
          "Set v.25bis dialing for interface";
        tailf:cli-delete-when-empty;
        presence "true";
        leaf parity {
          tailf:cli-drop-node-name;
          type enumeration {
            enum "no-parity" {
              tailf:info
                "No parity";
            }
            enum "odd-parity" {
              tailf:info
                "Odd parity";
            }
          }
        }
      }
      container idle-timeout {
        tailf:info
          "Specify idle timeout before disconnecting line";
        tailf:cli-compact-syntax;
        tailf:cli-sequence-commands {
          tailf:cli-reset-siblings;
        }
        leaf seconds {
          tailf:cli-drop-node-name;
          type uint32 {
            tailf:info
              "<0-2147483>;;Idle timeout before disconnecting a call";
          }
        }
        leaf direction {
          tailf:cli-drop-node-name;
          type enumeration {
            enum "either" {
              tailf:info
                "Reset idle timer based on both inbound and outbound traffic";
            }
            enum "inbound" {
              tailf:info
                "Reset idle timer based on inbound traffic only";
            }
          }
        }
      }
      leaf enable-timeout {
        tailf:info
          "Set length of time an interface stays down before it is available for dialing";
        type uint32 {
          tailf:info
            "<1-2147483>;;Enable timeout in seconds";
          range "1..2147483";
        }
      }
      leaf string {
        tailf:info
          "Specify telephone number to be passed to DCE device";
        type string {
          tailf:info
            "WORD;;Dialer string (quote strings containing #)";
        }
      }
      leaf watch-group {
        tailf:info
          "Assign interface to dialer-watch-list";
        type uint16 {
          tailf:info
            "<1-255>;;Dialer watch group number";
          range "1..255";
        }
        tailf:non-strict-leafref {
          path "/ncs:devices/ncs:device/ncs:config/ios:dialer/watch-list/id" {
            tailf:xpath-root 3;
          }
        }
      }
    }
    leaf physical-layer {
      tailf:info
        "Configure sync or async physical layer on serial interface";
      type enumeration {
        enum "async" {
          tailf:info
            "Configure asynchronous physical layer on serial interface";
        }
        enum "sync" {
          tailf:info
            "Configure synchronous physical layer on serial interface";
        }
      }
    }
    container async {
      tailf:info
        "Async interface parameters";
      container mode {
        tailf:info
          "Specify line mode (interactive or dedicated interface use)";
        leaf dedicated {
          tailf:info
            "Line is dedicated as an async interface";
          type empty;
        }
        leaf interactive {
          tailf:info
            "Line may be switched between interactive use and async interface";
          type empty;
        }
      }
    }
    container pulse-time {
      tailf:info
        "Force DTR low during resets";
      choice pulse-time-choice {
        leaf seconds {
          tailf:cli-drop-node-name;
          type uint8 {
            tailf:info
              "<0-60>;;DTR low time in seconds";
            range "0..60";
          }
        }
        leaf msec {
          tailf:info
            "millisecond (resolution)";
          type uint16 {
            tailf:info
              "<1-59999>;;DTR low time in milliseconds";
            range "1..59999";
          }
        }
      }
    }
  }

  grouping crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping router-bgp-max-path-grouping {
    container paths {
      tailf:cli-drop-node-name;
      tailf:cli-compact-syntax;
      tailf:cli-sequence-commands {
        tailf:cli-reset-siblings;
      }
      leaf number-of-paths {
        tailf:cli-drop-node-name;
        type uint16 {
          tailf:info
            "<1-16>;;Number of paths";
          range "1..16";
        }
        default "1";
      }
      leaf import {
        tailf:info
          "Maximum import paths";
        type uint16 {
          tailf:info
            "<1-16>;;Number of import paths";
          range "1..16";
        }
      }
    }
  }

  grouping router-bgp-redistribute-grouping {
    leaf metric {
      tailf:cli-break-sequence-commands;
      tailf:info
        "Metric for redistributed routes";
      type uint32 {
        tailf:info
          "<0-4294967295>;;Default metric";
        range "0..4294967295";
      }
    }
    leaf route-map {
      tailf:info
        "Route map reference";
      type string {
        tailf:info
          "WORD;;Pointer to route-map entries";
      }
    }
  }

  grouping route-map-metric-grouping {
    leaf route-map {
      tailf:info
        "Route map reference";
      type string {
        tailf:info
          "WORD;;Pointer to route-map entries";
      }
    }
    leaf metric {
      tailf:info
        "Metric for redistributed routes";
      type uint32 {
        tailf:info
          "<0-4294967295>;;Default metric";
        range "0..4294967295";
      }
    }
  }

  grouping redistribute-isis-grouping {
    choice osi-ip-choice {
      leaf ip {
        tailf:info
          "Redistribution of IP dynamic routes";
        type empty;
      }
      leaf clns {
        tailf:info
          "Redistribution of OSI dynamic routes";
        type empty;
      }
    }
    leaf level {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    uses router-bgp-redistribute-grouping;
  }

  grouping router-bgp-grouping {
    container bgp-top {
      tailf:cli-drop-node-name;
      container bgp {
        container bestpath {
          tailf:info
            "Change the default bestpath selection";
          container as-path {
            leaf multipath-relax {
              type empty;
            }
          }
        }
      }
    }
    container timers {
      tailf:info
        "Adjust routing timers";
      container bgp {
        tailf:info
          "BGP timers";
        tailf:cli-compact-syntax;
        tailf:cli-sequence-commands {
          tailf:cli-reset-siblings;
        }
        leaf keepalive {
          tailf:cli-drop-node-name;
          tailf:cli-incomplete-command;
          type uint16 {
            tailf:info
              "<0-65535>;;Keepalive interval";
            range "0..65535";
          }
        }
        leaf holdtime {
          tailf:cli-drop-node-name;
          type uint16 {
            tailf:info
              "<0-65535>;;Holdtime";
            range "0..65535";
          }
        }
        leaf min-holdtime {
          tailf:cli-drop-node-name;
          type uint16 {
            tailf:info
              "<0-65535>;;Minimum hold time from neighbor";
            range "0..65535";
          }
        }
      }
    }
  }

  grouping router-bgp-peer-policy-grouping {
    leaf advertisement-interval {
      tailf:info
        "Minimum interval between sending BGP routing updates";
      tailf:cli-full-command;
      type uint16 {
        tailf:info
          "<0-600>;;time in seconds";
        range "0..600";
      }
    }
    container send-community {
      tailf:info
        "Send Community attribute to this neighbor";
      tailf:cli-delete-when-empty;
      presence "true";
      leaf send-community-where {
        tailf:cli-drop-node-name;
        type enumeration {
          enum "both" {
            tailf:info
              "Send Standard and Extended Community attributes";
          }
          enum "extended" {
            tailf:info
              "Send Extended Community attribute";
          }
          enum "standard" {
            tailf:code-name "send_standard";
            tailf:info
              "Send Standard Community attribute";
          }
        }
      }
    }
    container maximum-prefix {
      tailf:info
        "Maximum number of prefixes accepted from this peer";
      tailf:cli-compact-syntax;
      tailf:cli-sequence-commands {
        tailf:cli-reset-all-siblings;
      }
      leaf max-prefix-no {
        tailf:cli-drop-node-name;
        type uint32 {
          tailf:info
            "<1-2147483647>;;maximum no. of prefix limit";
          range "1..2147483647";
        }
      }
      leaf threshold {
        tailf:cli-drop-node-name;
        tailf:cli-break-sequence-commands;
        type uint8 {
          tailf:info
            "<1-100>;;Threshold value (%) at which to generate a warning msg";
          range "1..100";
        }
      }
      leaf restart {
        tailf:cli-full-command;
        tailf:info
          "Restart bgp connection after limit is exceeded";
        type uint16 {
          tailf:info
            "<1-65535>;;Restart interval in minutes";
          range "1..65535";
        }
      }
      leaf warning-only {
        tailf:cli-full-command;
        tailf:info
          "Only give warning message when limit is exceeded";
        type empty;
      }
    }
    container allowas-in {
      tailf:info
        "Accept as-path with my AS present in it";
      tailf:cli-delete-when-empty;
      presence "accept as-paths";
      leaf as-number {
        tailf:cli-drop-node-name;
        type uint8 {
          tailf:info
            "<1-10>;;Number of occurances of AS number";
          range "1..10";
        }
      }
    }
    container as-override {
      tailf:info
        "Override matching AS-number while sending update";
      tailf:cli-delete-when-empty;
      presence "true";
      leaf disable {
        type empty;
      }
    }
  }

  grouping router-bgp-peer-session-grouping {
    leaf remote-as {
      tailf:info
        "Specify a BGP neighbor";
      tailf:cli-delete-container-on-delete;
      tailf:cli-full-command;
      type string {
        tailf:info
          "AS of remote neighbor";
      }
    }
    container password {
      tailf:info
        "Set a password";
      tailf:cli-compact-syntax;
      tailf:cli-sequence-commands {
        tailf:cli-reset-siblings;
      }
      leaf enctype {
        tailf:cli-optional-in-sequence;
        tailf:cli-drop-node-name;
        tailf:cli-incomplete-command;
        type uint8 {
          tailf:info
            "<0-7>;;Encryption type (0 to disable encryption, 7 for proprietary)";
          range "0..7";
        }
      }
      leaf text {
        tailf:cli-drop-node-name;
        tailf:cli-multi-value;
        tailf:cli-full-command;
        tailf:cli-disallow-value "0|1|2|3|4|5|6|7";
        type string {
          tailf:info
            "LINE;;The password";
        }
      }
    }
    container ttl-security {
      tailf:info
        "BGP ttl security check";
      leaf hops {
        tailf:info
          "IP hops";
        type uint8 {
          tailf:info
            "<1-254>;;maximum number of hops";
          range "1..254";
        }
      }
    }
    container timers {
      tailf:info
        "BGP per neighbor timers";
      tailf:cli-compact-syntax;
      tailf:cli-sequence-commands {
        tailf:cli-reset-siblings;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          range "0..65535";
          tailf:info
            "<0-65535>;;Holdtime";
        }
      }
      leaf minimum-neighbor-hold {
        tailf:cli-drop-node-name;
        type uint16 {
          tailf:info
            "<0-65535>;;Minimum hold time from neighbor";
          range "0..65535";
        }
      }
    }
    container fall-over {
      tailf:info
        "session fall on peer route lost";
      presence "true";
      leaf bfd {
        tailf:info
          "Use BFD to detect failure";
        tailf:cli-full-command;
        type empty;
      }
      leaf route-map {
        tailf:info
          "Route map for peer route";
        tailf:cli-full-command;
        type string {
          tailf:info
            "WORD;;Name of the route map";
        }
      }
    }
  }

  grouping router-bgp-neighbor-grouping {
    container peer-group {
      tailf:info
        "Member of the peer-group";
      tailf:cli-delete-when-empty;
      presence "true";
      leaf peer-group-name {
        tailf:info
          "WORD;;peer-group name";
        tailf:cli-drop-node-name;
        tailf:cli-delete-container-on-delete;
        tailf:cli-full-command;
        type string;
      }
    }
    container local-as {
      tailf:info
        "Specify a local-as number";
      tailf:cli-compact-syntax;
      tailf:cli-sequence-commands {
        tailf:cli-reset-siblings;
      }
      tailf:cli-delete-when-empty;
      presence "Specify a local-as number";
      leaf as-no {
        tailf:cli-drop-node-name;
        type uint16 {
          range "1..65535";
          tailf:info
            "<1-65535>;;AS number used as local AS";
        }
      }
      leaf no-prepend {
        tailf:info
          "Do not prepend local-as to updates from ebgp peers";
        type empty;
      }
      leaf replace-as {
        tailf:info
          "Replace real AS with local AS in the EBGP updates";
        type empty;
      }
      leaf dual-as {
        tailf:info
          "Accept either real AS or local AS from the ebgp peer";
        type empty;
      }
    }
    uses router-bgp-peer-session-grouping;
    leaf activate {
      tailf:info
        "Enable the Address Family for this Neighbor";
      tailf:cli-full-command;
      type empty;
    }
    uses router-bgp-peer-policy-grouping;
    leaf soo {
      tailf:info
        "Site-of-Origin extended community";
      tailf:cli-full-command;
      type string {
        tailf:info
          "ASN:nn or IP-address:nn;;VPN extended community";
      }
    }
    container capability {
      tailf:info
        "Advertise capability to the peer";
      container orf {
        tailf:info
          "Advertise ORF capability to the peer";
        leaf-list prefix-list {
          tailf:cli-flat-list-syntax;
          tailf:info
            "Advertise prefixlist ORF capability to this neighbor";
          max-elements 1;
          type enumeration {
            enum "both" {
              tailf:info
                "Capability to SEND and RECEIVE the ORF to/from this neighbor";
            }
            enum "receive" {
              tailf:info
                "Capability to RECEIVE the ORF from this neighbor";
            }
            enum "send" {
              tailf:info
                "Capability to SEND the ORF to this neighbor";
            }
          }
        }
      }
    }
    container default-originate {
      tailf:info
        "Originate default route to this neighbour";
      tailf:cli-delete-when-empty;
      presence "enable originate default route to this neighbour";
      leaf route-map {
        tailf:info
          "Route-map to specify criteria to originate default";
        type string {
          tailf:info
            "WORD;;route-map name";
        }
      }
    }
    leaf description {
      tailf:info
        "Neighbor specific description";
      tailf:cli-full-command;
      tailf:cli-multi-value;
      type string {
        tailf:info
          "LINE;;Up to 80 characters describing this neighbor";
      }
    }
    leaf disable-connected-check {
      tailf:info
        "One-hop away EBGP peer using loopback address";
      tailf:cli-full-command;
      type empty;
    }
    uses router-distribute-list-grouping;
    leaf dmzlink-bw {
      tailf:info
        "Propagate the DMZ link bandwidth";
      tailf:cli-full-command;
      type empty;
    }
    container ebgp-multihop {
      tailf:info
        "Allow EBGP neighbors not on directly connected networks";
      tailf:cli-delete-when-empty;
      presence "Allow EBGP neighbors not on directly connected networks";
      leaf max-hop {
        tailf:cli-drop-node-name;
        type uint8 {
          range "1..255";
          tailf:info
            "<1-255>;;maximum hop count";
        }
      }
    }
    list filter-list {
      tailf:info
        "Establish BGP filters";
      tailf:cli-suppress-mode;
      tailf:cli-delete-when-empty;
      key "inout";
      leaf inout {
        type enumeration {
          enum "in" {
            tailf:code-name "filter_in";
            tailf:info
              "Filter incoming routes";
          }
          enum "out" {
            tailf:code-name "filter_out";
            tailf:info
              "Filter outgoing routes";
          }
        }
      }
      leaf as-path-list {
        tailf:cli-drop-node-name;
        tailf:cli-prefix-key;
        type uint16 {
          range "1..500";
          tailf:info
            "<1-500>;;AS path access list";
        }
        mandatory true;
      }
    }
    container inherit {
      tailf:info
        "Inherit a template";
      leaf peer-policy {
        tailf:info
          "Inherit a peer-policy template";
        tailf:cli-full-command;
        type string {
          tailf:info
            "WORD;;Template name";
        }
      }
      leaf peer-session {
        tailf:info
          "Inherit a peer-session template";
        tailf:cli-full-command;
        type string {
          tailf:info
            "WORD;;Template name";
        }
      }
    }
    leaf next-hop-self {
      tailf:cli-full-command;
      tailf:info
        "Disable the next hop calculation for this neighbor";
      type empty;
    }
    container next-hop-self-arg {
      tailf:cli-drop-node-name;
      leaf next-hop-self {
        type string;
      }
    }
    leaf next-hop-unchanged {
      tailf:cli-full-command;
      tailf:info
        "Propagate the iBGP paths's next hop unchanged for this neighbor";
      type empty;
    }
    list prefix-list {
      tailf:info
        "Filter updates to/from this neighbor";
      tailf:cli-suppress-mode;
      tailf:cli-delete-when-empty;
      key "direction";
      leaf direction {
        type enumeration {
          enum "in" {
            tailf:info
              "Filter incoming updates";
          }
          enum "out" {
            tailf:info
              "Filter outgoing updates";
          }
        }
      }
      leaf prefix-list-name {
        tailf:cli-drop-node-name;
        tailf:cli-prefix-key;
        type string {
          tailf:info
            "WORD;;Name of a prefix list";
        }
        mandatory true;
      }
    }
    leaf remove-private-as {
      tailf:info
        "Remove private AS number from outbound updates";
      tailf:cli-full-command;
      type empty;
    }
    list route-map {
      tailf:info
        "Apply route map to neighbor";
      tailf:cli-suppress-mode;
      tailf:cli-delete-when-empty;
      key "direction";
      leaf direction {
        type enumeration {
          enum "in" {
            tailf:info
              "Apply map to incoming routes";
          }
          enum "out" {
            tailf:info
              "Apply map to outbound routes";
          }
        }
      }
      leaf route-map-name {
        tailf:cli-drop-node-name;
        tailf:cli-prefix-key;
        type string {
          tailf:info
            "WORD;;Name of route map";
        }
        mandatory true;
      }
    }
    leaf route-reflector-client {
      tailf:cli-full-command;
      tailf:info
        "Configure a neighbor as Route Reflector client";
      type empty;
    }
    container send-label {
      tailf:info
        "Send NLRI + MPLS Label to this peer";
      tailf:cli-delete-when-empty;
      presence "true";
      leaf explicit-null {
        tailf:info
          "Advertise Explicit Null label in place of Implicit Null";
        type empty;
      }
    }
    leaf shutdown {
      tailf:cli-full-command;
      tailf:info
        "Administratively shut down this neighbor";
      type empty;
    }
    leaf soft-reconfiguration {
      tailf:cli-full-command;
      tailf:info
        "Per neighbor soft reconfiguration";
      type enumeration {
        enum "inbound" {
          tailf:info
            "Allow inbound soft reconfiguration for this neighbor";
        }
      }
    }
    container translate-update {
      tailf:info
        "Translate Update to MBGP format";
      container ipv4 {
        tailf:info
          "Address Family";
        container multicast {
          tailf:info
            "Address Family modifier";
          tailf:cli-delete-when-empty;
          presence "Address Family modifier";
          leaf unicast {
            tailf:info
              "Address Family modifier";
            type empty;
          }
        }
      }
    }
    container transport {
      tailf:info
        "Transport options";
      leaf connection-mode {
        tailf:info
          "Specify passive or active connection";
        type enumeration {
          enum "active" {
            tailf:info
              "Actively establish the TCP session";
          }
          enum "passive" {
            tailf:info
              "Passively establish the TCP session";
          }
        }
      }
    }
    leaf unsuppress-map {
      tailf:info
        "Route-map to selectively unsuppress suppressed routes";
      tailf:cli-full-command;
      type string {
        tailf:info
          "WORD;;Name of route map";
      }
    }
    container update-source {
      tailf:info
        "Source of routing updates";
      uses interface-name-grouping;
    }
    leaf version {
      tailf:cli-full-command;
      tailf:info
        "Set the BGP version to match a neighbor";
      type uint16 {
        range "4";
        tailf:info
          "<4-4>;;Neighbor's BGP version";
      }
    }
    leaf weight {
      tailf:info
        "Set default weight for routes from this neighbor";
      tailf:cli-full-command;
      type uint16 {
        tailf:info
          "<0-65535>;;default weight";
        range "0..65535";
      }
    }
    container ha-mode {
      tailf:info
        "high availability mode";
      container graceful-restart {
        tailf:info
          "graceful-restart for this peer";
        presence "true";
        leaf disable {
          tailf:info
            "disable graceful-restart";
          type empty;
        }
      }
      container sso {
        tailf:info
          "stateful-switchover support for this peer";
        presence "true";
        leaf disable {
          tailf:info
            "disable stateful-switchover";
          type empty;
        }
      }
    }
    container suppress-signaling-protocol {
      tailf:info
        "suppress VPLS signaling protocol";
      leaf ldp {
        tailf:info
          "suppress ldp signaling, enable bgp signaling";
        tailf:cli-full-command;
        type empty;
      }
    }
    leaf prefix-length-size {
      tailf:info
        "Packet Level storage size for Prefixes";
      type uint8 {
        tailf:info
          "<1-2>;;Storage size in bytes";
        range "1..2";
      }
    }
  }

  grouping router-bgp-af-grouping {
    container aggregate-address {
      tailf:info
        "Configure BGP aggregate entries";
      tailf:cli-compact-syntax;
      tailf:cli-sequence-commands {
        tailf:cli-reset-all-siblings;
      }
      leaf address {
        tailf:cli-drop-node-name;
        type inet:ipv4-address {
          tailf:info
            "A.B.C.D;;Aggregate address";
        }
      }
      leaf mask {
        tailf:cli-drop-node-name;
        type inet:ipv4-address {
          tailf:info
            "A.B.C.D;;Aggregate mask";
        }
      }
      leaf advertise-map {
        tailf:cli-break-sequence-commands;
        tailf:info
          "Set condition to advertise attribute";
        type string {
          tailf:info
            "WORD;;Route map to control attribute advertisement";
        }
      }
      leaf as-set {
        tailf:info
          "Generate AS set path information";
        type empty;
      }
      leaf attribute-map {
        type string {
          tailf:info
            "WORD;;Route map for parameter control";
        }
      }
      leaf as-override {
        tailf:info
          "Override matching AS-number while sending update";
        type empty;
      }
      leaf route-map {
        type string {
          tailf:info
            "WORD;;Route map for parameter control";
        }
      }
      leaf summary-only {
        tailf:info
          "Filter more specific routes from updates";
        type empty;
      }
      leaf suppress-map {
        tailf:info
          "Conditionally filter more specific routes from updates";
        type string {
          tailf:info
            "WORD;;Route map for suppression";
        }
      }
    }
    container bgp {
      tailf:info
        "BGP specific commands";
      leaf router-id {
        tailf:cli-full-command;
        tailf:info
          "Override configured router identifier (peers will reset)";
        type inet:ipv4-address {
          tailf:info
            "A.B.C.D;;Manually configured router identifier";
        }
      }
      leaf always-compare-med {
        tailf:info
          "Allow comparing MED from different neighbors";
        tailf:cli-full-command;
        type empty;
      }
      container bestpath {
        tailf:info
          "Change the default bestpath selection";
        leaf compare-routerid {
          tailf:info
            "Compare router-id for identical EBGP paths";
          tailf:cli-full-command;
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
      }
      container client-to-client {
        tailf:info
          "Configure client to client route reflection";
        leaf reflection {
          tailf:info
            "reflection of routes allowed";
          type empty;
        }
      }
      leaf cluster-id {
        tailf:cli-full-command;
        type union {
          type uint32 {
            range "1..4294967295";
            tailf:info
              "<1-4294967295>;;Route-Reflector Cluster-id as 32 bit quantity";
          }
          type inet:ipv4-address {
            tailf:info
              "A.B.C.D;;Route-Reflector Cluster-id in IP address format";
          }
        }
      }
      container confederation {
        tailf:info
          "AS confederation parameters";
        leaf identifier {
          tailf:cli-full-command;
          tailf:info
            "as number";
          type uint16 {
            range "1..65535";
            tailf:info
              "<1-65535>;;Set routing domain confederation AS";
          }
        }
        container peers {
          tailf:info
            "Peer ASs in BGP confederation";
          presence "Peer ASs in BGP confederation";
          leaf-list peers-as {
            tailf:cli-drop-node-name;
            tailf:cli-flat-list-syntax;
            type uint16 {
              range "1..65535";
              tailf:info
                "AS number";
            }
          }
        }
      }
      container dampening {
        tailf:info
          "Enable route-flap dampening";
        presence "true";
        choice dampening-choice {
          leaf route-map {
            tailf:info
              "Route-map to specify criteria for dampening";
            type string {
              tailf:info
                "WORD;;route-map name";
            }
          }
          container dampen {
            tailf:cli-drop-node-name;
            tailf:cli-compact-syntax;
            tailf:cli-sequence-commands;
            leaf half-life-time {
              tailf:cli-drop-node-name;
              tailf:cli-incomplete-command;
              type uint8 {
                tailf:info
                  "<1-45>;;Half-life time for the penalty";
                range "1..45";
              }
            }
            leaf reuse-time {
              tailf:cli-drop-node-name;
              tailf:cli-incomplete-command;
              type uint16 {
                tailf:info
                  "<1-20000>;;Value to start reusing a route";
                range "1..20000";
              }
            }
            leaf suppress-time {
              tailf:cli-drop-node-name;
              tailf:cli-incomplete-command;
              type uint16 {
                tailf:info
                  "<1-20000>;;Value to start suppressing a route";
                range "1..20000";
              }
            }
            leaf max-suppress-time {
              tailf:cli-drop-node-name;
              type uint8 {
                tailf:info
                  "<1-255>;;Maximum duration to suppress a stable route";
                range "1..255";
              }
            }
          }
        }
      }
      container default {
        tailf:info
          "Configure BGP defaults";
        leaf ipv4-unicast {
          tailf:info
            "Activate ipv4-unicast for a peer by default";
          tailf:cli-boolean-no;
          type boolean;
          default "true";
        }
        leaf ipv4-activate {
          tailf:cli-boolean-no;
          type boolean;
          default "true";
        }
        leaf local-preference {
          tailf:info
            "local preference (higher=more preferred)";
          type uint32 {
            tailf:info
              "<0-4294967295>;;Configure default local preference value";
            range "1..4294967295";
          }
        }
        container route-target {
          tailf:info
            "Control behavior based on Route-Target attributes";
          leaf filter {
            tailf:info
              "Control automatic VPN Route-Target filtering";
            tailf:cli-boolean-no;
            type boolean;
            default "true";
          }
        }
      }
      leaf deterministic-med {
        tailf:cli-full-command;
        tailf:info
          "Pick the best-MED path among paths advertised from the neighboring AS";
        type empty;
      }
      leaf dmzlink-bw {
        tailf:cli-full-command;
        tailf:info
          "Use DMZ Link Bandwidth as weight for BGP multipaths";
        type empty;
      }
      leaf enforce-first-as {
        tailf:info
          "Enforce the first AS for EBGP routes(default)";
        tailf:cli-full-command;
        type empty;
      }
      leaf fast-external-fallover {
        tailf:info
          "Immediately reset session if a link to a directly connected external peer goes down";
        tailf:cli-full-command;
        type empty;
      }
      container graceful-restart {
        tailf:info
          "Graceful restart capability parameters";
        tailf:cli-display-separated;
        tailf:cli-delete-when-empty;
        presence "true";
        leaf restart-time {
          tailf:cli-full-command;
          tailf:info
            "Set the max time needed to restart and come back up";
          type uint16 {
            tailf:info
              "<1-3600>;;Delay value (seconds)";
            range "1..3600";
          }
        }
        leaf stalepath-time {
          tailf:info
            "Set the max time to hold onto restarting peer's stale paths";
          type uint16 {
            tailf:info
              "<1-3600>;;Delay value (seconds)";
            range "1..3600";
          }
        }
      }
      list inject-map {
        tailf:info
          "Routemap which specifies prefixes to inject";
        tailf:cli-compact-syntax;
        tailf:cli-sequence-commands;
        tailf:cli-incomplete-command;
        tailf:cli-delete-when-empty;
        key "name";
        leaf name {
          type string {
            tailf:info
              "WORD;;route-map name";
          }
        }
        leaf exist-map {
          tailf:info
            "Routemap which specifies exist condition";
          type string {
            tailf:info
              "WORD;;route-map name";
          }
        }
        leaf copy-attributes {
          tailf:info
            "Copy attributes from aggregate";
          type empty;
        }
      }
      container transport {
        tailf:info
          "global enable/disable transport session parameters";
        leaf path-mtu-discovery {
          tailf:info
            "transport path MTU discovery";
          tailf:cli-boolean-no;
          tailf:cli-full-command;
          type boolean;
          default "true";
        }
      }
      leaf log-neighbor-changes {
        tailf:info
          "Log neighbor up/down and reset reason";
        tailf:cli-full-command;
        type empty;
      }
      container listen {
        tailf:info
          "Neighbor subnet range listener";
        tailf:cli-delete-when-empty;
        presence "true";
        container range {
          tailf:cli-compact-syntax;
          tailf:cli-sequence-commands {
            tailf:cli-reset-siblings;
          }
          leaf network-length {
            tailf:cli-drop-node-name;
            tailf:cli-incomplete-command;
            type ios:ipv4-prefix {
              tailf:info
                "A.B.C.D/nn;;Subnet range <network>/<length>, e.g., 10.0.0.0/24";
            }
          }
          leaf peer-group {
            tailf:info
              "Member of the peer-group";
            type string {
              tailf:info
                "WORD;;peer-group name";
            }
          }
        }
        leaf limit {
          tailf:info
            "Set the max limit for the dynamic subnet range neighbors";
          type uint32 {
            tailf:info
              "<1-5000>;;max number";
            range "1..5000";
          }
        }
      }
      leaf maxas-limit {
        tailf:info
          "Allow AS-PATH attribute from any neighbor imposing a limit on number of ASes";
        tailf:cli-full-command;
        type uint16 {
          range "1..2000";
          tailf:info
            "<1-2000>;;Number of ASes in the AS-PATH attribute";
        }
      }
      container additional-paths {
        tailf:info
          "Additional paths in the BGP table";
        choice send-receive-choice {
          leaf receive {
            tailf:info
              "Receive additional paths from neighbors";
            tailf:cli-full-command;
            type empty;
          }
          container send {
            tailf:info
              "Send additional paths to neighbors";
            tailf:cli-delete-when-empty;
            presence "true";
            leaf receive {
              tailf:info
                "Receive additional paths from neighbors";
              type empty;
            }
          }
        }
        leaf install {
          tailf:info
            "Additional paths to install into RIB";
          tailf:cli-full-command;
          type empty;
        }
      }
      container nexthop {
        tailf:info
          "Nexthop tracking commands";
        container trigger {
          tailf:info
            "Nexthop triggering";
          leaf delay {
            tailf:cli-full-command;
            tailf:info
              "Set the delay to tigger nexthop tracking";
            type uint8 {
              tailf:info
                "<0-100>;;Delay value (seconds)";
              range "0..100";
            }
          }
          leaf enable {
            tailf:info
              "Enable nexthop tracking";
            tailf:cli-full-command;
            tailf:cli-boolean-no;
            type boolean;
            default "true";
          }
        }
      }
      leaf redistribute-internal {
        tailf:info
          "Allow redistribution of iBGP into IGPs (dangerous)";
        tailf:cli-full-command;
        type empty;
      }
      container regexp {
        tailf:info
          "Select regular expression engine";
        leaf deterministic {
          tailf:info
            "Enable bounded-execution-time regular expression engine";
          type empty;
        }
      }
      leaf scan-time {
        tailf:cli-full-command;
        tailf:info
          "Configure background scanner interval";
        type uint8 {
          range "5..60";
          tailf:info
            "<5-60>;;Scanner interval (seconds)";
        }
      }
      leaf soft-reconfig-backup {
        tailf:info
          "Use soft-reconfiguration inbound only when route-refresh is not negotiated";
        tailf:cli-full-command;
        type empty;
      }
      leaf suppress-inactive {
        tailf:info
          "Suppress routes that are not in the routing table";
        tailf:cli-full-command;
        type empty;
      }
      leaf update-delay {
        tailf:cli-full-command;
        tailf:info
          "Set the max initial delay for sending update";
        type uint16 {
          range "1..3600";
          tailf:info
            "<1-3600>;;Delay value (seconds)";
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      container bgp {
        tailf:info
          "BGP distance";
        tailf:cli-compact-syntax;
        tailf:cli-sequence-commands;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "distance srcip wildbits";
        leaf distance {
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf access-list {
          tailf:cli-drop-node-name;
          type std-ip-acl-type;
        }
      }
    }
    uses router-distribute-list-grouping;
    container maximum-paths {
      tailf:info
        "Forward packets over multiple paths";
      uses router-bgp-max-path-grouping;
      container eibgp {
        tailf:info
          "Both eBGP and iBGP paths as multipath";
        uses router-bgp-max-path-grouping;
      }
      container ibgp {
        tailf:info
          "iBGP-multipath";
        choice ibgp-choice {
          default "b";
          case a {
            container unequal-cost {
              tailf:info
                "Perform Un-Equal cost multipath selection";
              uses router-bgp-max-path-grouping;
            }
          }
          case b {
            uses router-bgp-max-path-grouping;
          }
        }
      }
      leaf import {
        tailf:info
          "Maximum import paths";
        type uint16 {
          tailf:info
            "<1-16>;;Number of import paths";
          range "1..16";
        }
      }
    }
    container import {
      tailf:info
        "Configure path import";
      container path {
        tailf:info
          "Path selection and path limit";
        container selection {
          tailf:info
            "Path selection policy";
          choice selection-choice {
            leaf all {
              tailf:info
                "Import all available paths";
              type empty;
            }
            container bestpath {
              tailf:info
                "Import the best available path.";
              tailf:cli-delete-when-empty;
              presence "true";
              leaf strict {
                tailf:info
                  "Do not fallback to best available path";
                type empty;
              }
            }
            container multipaths {
              tailf:info
                "Import all multipaths.";
              tailf:cli-delete-when-empty;
              presence "true";
              leaf strict {
                tailf:info
                  "Do not fallback to best available path";
                type empty;
              }
            }
          }
        }
        leaf limit {
          tailf:info
            "Per net imported path limit";
          type uint8 {
            tailf:info
              "<2-255>;;Maximum number of paths that can be imported into a net";
            range "2..255";
          }
        }
      }
    }
    container redistribute {
      tailf:info
        "Redistribute information from another routing protocol";
      container bgp {
        tailf:info
          "Border Gateway Protocol (BGP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses router-bgp-redistribute-grouping;
      }
      container connected {
        tailf:info
          "Connected";
        tailf:cli-compact-syntax;
        tailf:cli-delete-when-empty;
        presence "Connected";
        uses router-bgp-redistribute-grouping;
      }
      container static {
        tailf:info
          "Static routes";
        tailf:cli-compact-syntax;
        tailf:cli-delete-when-empty;
        presence "true";
        uses router-bgp-redistribute-grouping;
      }
      container dvmrp {
        tailf:info
          "Redistribution of DVMRP into BGP IPv4 Multicast";
        tailf:cli-compact-syntax;
        tailf:cli-sequence-commands {
          tailf:cli-reset-siblings;
        }
        tailf:cli-delete-when-empty;
        presence "true";
        uses route-map-metric-grouping;
      }
      list eigrp {
        tailf:info
          "Enhanced Interior Gateway Routing Protocol (EIGRP)";
        tailf:cli-suppress-mode;
        tailf:cli-delete-when-empty;
        tailf:cli-compact-syntax;
        key "as-number";
        leaf as-number {
          type uint32 {
            tailf:info
              "<1-65535>;;Autonomous system number";
            range "1..65535";
          }
        }
        uses router-bgp-redistribute-grouping;
      }
      container isis {
        tailf:info
          "ISO IS-IS";
        tailf:cli-compact-syntax;
        presence "true";
        uses redistribute-isis-grouping;
        list isis-list {
          tailf:cli-drop-node-name;
          tailf:cli-compact-syntax;
          tailf:cli-suppress-mode;
          tailf:cli-delete-when-empty;
          key "name";
          leaf name {
            type string {
              tailf:info
                "WORD;;ISO routing area tag";
              pattern '^([^mlir].*)|(i[^p].*)|(ip..*)|(l[^e].*)|(le[^v].*)|(lev[^e].*)|(leve[^l].*)|(level[^\-].*)|(m[^e].*)|(me[^t].*)|(met[^r].*)|(metr[^i].*)|(metri[^c].*)|(metric..*)*(r[^o].*)|(ro[^u].*)|(rou[^t].*)|(rout[^e].*)|(route[^\-].*)|(route-[^m].*)|(route-m[^a].*)|(route-ma[^p].*)|(route-map..*)$';
            }
          }
          uses redistribute-isis-grouping;
        }
      }
      container iso-igrp {
        tailf:info
          "IGRP for OSI networks";
        tailf:cli-compact-syntax;
        uses route-map-metric-grouping;
        list iso-igrp-area {
          tailf:cli-drop-node-name;
          tailf:cli-suppress-mode;
          tailf:cli-delete-when-empty;
          tailf:cli-compact-syntax;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses route-map-metric-grouping;
        }
      }
      container mobile {
        presence "Mobile routes";
        tailf:info
          "Mobile routes";
        tailf:cli-compact-syntax;
        uses router-bgp-redistribute-grouping;
      }
      container odr {
        presence "On Demand stub Routes";
        tailf:info
          "On Demand stub Routes";
        tailf:cli-compact-syntax;
        uses router-bgp-redistribute-grouping;
      }
      list ospf {
        tailf:info
          "Open Shortest Path First (OSPF)";
        tailf:cli-suppress-mode;
        tailf:cli-delete-when-empty;
        tailf:cli-compact-syntax;
        key "id";
        leaf id {
          type uint16 {
            tailf:info
              "<1-65535>;;Process ID";
            range "1..65535";
          }
        }
        list vrf {
          tailf:info
            "VPN Routing/Forwarding Instance";
          tailf:cli-suppress-mode;
          tailf:cli-delete-when-empty;
          tailf:cli-compact-syntax;
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding Instance (VRF) name";
            }
          }
          container match {
            tailf:info
              "Redistribution of OSPF routes";
            tailf:cli-flatten-container;
            tailf:cli-compact-syntax;
            uses redistribute-ospf-match-grouping;
            uses router-bgp-redistribute-grouping;
          }
        }
        container non-vrf {
          tailf:cli-drop-node-name;
          tailf:cli-flatten-container;
          tailf:cli-compact-syntax;
          container match {
            tailf:info
              "Redistribution of OSPF routes";
            tailf:cli-flatten-container;
            tailf:cli-compact-syntax;
            uses redistribute-ospf-match-grouping;
            uses router-bgp-redistribute-grouping;
          }
        }
      }
      container rip {
        tailf:info
          "Routing Information Protocol (RIP)";
        tailf:cli-compact-syntax;
        presence "true";
        uses router-bgp-redistribute-grouping;
      }
    }
    container neighbor-tag {
      tailf:cli-drop-node-name;
      list neighbor {
        tailf:info
          "Specify a neighbor router";
        tailf:cli-suppress-mode;
        tailf:cli-delete-when-empty;
        tailf:cli-incomplete-command;
        ordered-by user;
        key "id";
        leaf id {
          type string {
            tailf:info
              "WORD;;Neighbor tag";
          }
        }
        uses router-bgp-neighbor-grouping;
      }
    }
    list neighbor {
      tailf:info
        "Specify a neighbor router";
      tailf:cli-suppress-mode;
      tailf:cli-delete-when-empty;
      tailf:cli-incomplete-command;
      key "id";
      leaf id {
        type union {
          type inet:ipv4-address {
            tailf:info
              "A.B.C.D;;Neighbor address";
          }
          type inet:ipv6-address {
            tailf:info
              "X:X:X:X::X;;Neighbor IPv6 address";
          }
        }
      }
      uses router-bgp-neighbor-grouping;
    }
    list network {
      tailf:info
        "Specify a network to announce via BGP";
      tailf:cli-suppress-mode;
      tailf:cli-delete-when-empty;
      tailf:cli-compact-syntax;
      tailf:cli-reset-container;
      key "number";
      leaf number {
        type inet:ipv4-address {
          tailf:info
            "A.B.C.D;;Network number";
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    leaf synchronization {
      tailf:info
        "Perform IGP synchronization";
      tailf:cli-full-command;
      type empty;
    }
    leaf auto-summary {
      tailf:info
        "Enable automatic network number summarization";
      tailf:cli-boolean-no;
      tailf:cli-full-command;
      type boolean;
    }
    leaf table-map {
      tailf:info
        "Map external entry attributes into routing table";
      tailf:cli-full-command;
      type string {
        tailf:info
          "WORD;;route-map name";
      }
    }
  }

  grouping router-ospf-af-grouping;

  grouping router-ospfv3-af-grouping {
    container discard-route {
      tailf:info
        "Enable or disable discard-route installation";
      leaf external {
        tailf:info
          "Discard route for summarised redistributed routes";
        tailf:cli-boolean-no;
        tailf:cli-full-command;
        type boolean;
        default "true";
      }
      leaf internal {
        tailf:info
          "Discard route for summarised inter-area routes";
        tailf:cli-boolean-no;
        tailf:cli-full-command;
        type boolean;
        default "true";
      }
    }
  }

  grouping router-ospf-common-af-grouping {
    container default-information {
      tailf:info
        "Control distribution of default information";
      container originate {
        tailf:info
          "Distribute a default route";
        tailf:cli-compact-syntax;
        tailf:cli-delete-when-empty;
        presence "true";
        leaf always {
          tailf:info
            "Always advertise default route";
          type empty;
        }
        leaf metric {
          tailf:info
            "OSPF default metric";
          type uint32 {
            tailf:info
              "<0-16777214>;;OSPF metric";
            range "0..16777214";
          }
        }
        leaf metric-type {
          tailf:info
            "OSPF metric type for default routes";
          type ospf-metric-type;
          default "2";
        }
        leaf route-map {
          tailf:info
            "Route map reference";
          type string {
            tailf:info
              "WORD;;Route map name";
          }
        }
      }
    }
    leaf default-metric {
      tailf:info
        "Set metric of redistributed routes";
      tailf:cli-full-command;
      type uint32 {
        tailf:info
          "<1-16777214>;;OSPF default metric";
        range "1..16777214";
      }
    }
    container distance {
      tailf:info
        "Define an administrative distance";
      leaf weight {
        tailf:cli-drop-node-name;
        type uint8 {
          tailf:info
            "<1-255>;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container ospf {
        tailf:info
          "OSPF routes Administrative distance";
        tailf:cli-compact-syntax;
        leaf intra-area {
          tailf:info
            "Intra-area routes";
          type uint32 {
            tailf:info
              "<1-255>;;Distance for intra-area routes";
            range "1..255";
          }
        }
        leaf inter-area {
          tailf:info
            "Inter-area routes";
          type uint32 {
            tailf:info
              "<1-255>;;Distance for inter-area routes";
            range "1..255";
          }
        }
        leaf external {
          tailf:info
            "External routes";
          type uint32 {
            tailf:info
              "<1-255>;;Distance for external routes";
            range "1..255";
          }
        }
      }
    }
    leaf maximum-paths {
      tailf:info
        "Forward packets over multiple paths";
      tailf:cli-full-command;
      type uint32 {
        range "1..32";
        tailf:info
          "<1-32>;;Number of paths";
      }
    }
    container redistribute {
      tailf:info
        "Redistribute information from another routing protocol";
      container bgp {
        tailf:info
          "Border Gateway Protocol (BGP)";
        tailf:cli-compact-syntax;
        leaf as-number {
          tailf:cli-drop-node-name;
          type uint32 {
            tailf:info
              "<1-65535>;;Autonomous system number";
            range "1..65535";
          }
        }
        uses router-ospf-redistribute-grouping;
      }
      container connected {
        tailf:info
          "Connected";
        tailf:cli-compact-syntax;
        tailf:cli-delete-when-empty;
        presence "Connected";
        uses router-ospf-redistribute-grouping;
      }
      list eigrp {
        tailf:info
          "Enhanced Interior Gateway Routing Protocol (EIGRP)";
        tailf:cli-suppress-mode;
        tailf:cli-delete-when-empty;
        tailf:cli-compact-syntax;
        key "as-number";
        leaf as-number {
          type uint32 {
            tailf:info
              "<1-65535>;;Autonomous system number";
            range "1..65535";
          }
        }
        uses router-ospf-redistribute-grouping;
      }
      container isis {
        tailf:info
          "ISO IS-IS";
        tailf:cli-compact-syntax;
        presence "true";
        list isis-area {
          tailf:cli-drop-node-name;
          tailf:cli-suppress-mode;
          tailf:cli-delete-when-empty;
          tailf:cli-compact-syntax;
          key "name";
          leaf name {
            tailf:cli-disallow-value "level-1|level-2|level-1-2|metric|metric-type|route-map|subnets|tag";
            type string {
              tailf:info
                "WORD;;ISO routing area tag";
            }
          }
          uses router-ospf-redistribute-grouping;
        }
        uses router-ospf-redistribute-grouping;
      }
      container iso-igrp {
        tailf:info
          "IGRP for OSI networks";
        tailf:cli-compact-syntax;
        tailf:cli-sequence-commands;
        presence "true";
        leaf area-tag {
          tailf:cli-drop-node-name;
          tailf:cli-disallow-value "route-map";
          tailf:cli-optional-in-sequence;
          type string {
            tailf:info
              "WORD;;ISO routing area tag";
          }
        }
        leaf route-map {
          tailf:info
            "Route map reference";
          type string {
            tailf:info
              "WORD;;Pointer to route-map entries";
          }
        }
        uses ospf-iso-igrp-redistribute-grouping;
      }
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        container threshold-warning-only-container {
          tailf:cli-drop-node-name;
          tailf:cli-flatten-container;
          tailf:cli-compact-syntax;
          leaf threshold {
            tailf:cli-drop-node-name;
            type uint32 {
              tailf:info
                "<1-100>;;Threshold value (%) at which to generate a warning message";
              range "1..100";
            }
          }
          leaf warning-only {
            tailf:info
              "Only give warning message when limit is exceeded";
            tailf:cli-full-command;
            type empty;
          }
        }
      }
      container mobile {
        tailf:info
          "Mobile routes";
        tailf:cli-compact-syntax;
        presence "true";
        uses router-ospf-redistribute-grouping;
      }
      container odr {
        tailf:info
          "On Demand stub Routes";
        tailf:cli-compact-syntax;
        presence "true";
        uses router-ospf-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint32 {
            tailf:info
              "<1-65535>;;Process ID";
            range "1..65535";
          }
        }
        uses router-ospf-redistribute-grouping;
        container match {
          tailf:info
            "Redistribution of OSPF routes";
          tailf:cli-flatten-container;
          tailf:cli-compact-syntax;
          uses redistribute-ospf-match-grouping;
          uses ospf-redistribute-match-grouping;
        }
      }
      container rip {
        tailf:info
          "Routing Information Protocol (RIP)";
        tailf:cli-compact-syntax;
        presence "true";
        uses router-ospf-redistribute-grouping;
        list redistribute-list-rip {
          tailf:cli-drop-node-name;
          tailf:cli-suppress-mode;
          tailf:cli-delete-when-empty;
          tailf:cli-compact-syntax;
          key "name";
          leaf name {
            type string {
              tailf:info
                "WORD;;User selected string identifying this process";
            }
          }
          uses router-ospf-redistribute-grouping;
        }
      }
      container static {
        tailf:info
          "Static routes";
        tailf:cli-compact-syntax;
        tailf:cli-delete-when-empty;
        presence "Static routes";
        uses router-ospf-redistribute-grouping;
      }
    }
  }

  grouping router-ospf-common-grouping {
    list area {
      tailf:cli-break-sequence-commands;
      tailf:info
        "OSPF area parameters";
      tailf:cli-suppress-mode;
      tailf:cli-delete-when-empty;
      tailf:cli-incomplete-command;
      key "id";
      leaf id {
        tailf:cli-suppress-range;
        type ospf-area-type;
      }
      container authentication {
        tailf:info
          "Enable authentication";
        presence "true";
        leaf message-digest {
          tailf:info
            "Use message-digest authentication";
          type empty;
        }
      }
      container nssa {
        tailf:info
          "Specify a NSSA area";
        tailf:cli-compact-syntax;
        tailf:cli-delete-when-empty;
        presence "true";
        leaf no-redistribution {
          tailf:info
            "No redistribution into this NSSA area";
          type empty;
        }
        leaf default-information-originate {
          tailf:info
            "Originate Type 7 default into NSSA area";
          type empty;
        }
        leaf metric {
          tailf:info
            "OSPF default metric";
          when '../default-information-originate' {
            tailf:xpath-root 3;
          }
          type int32 {
            tailf:info
              "<0-16777214>;;OSPF metric";
            range "0..16777214";
          }
        }
        leaf metric-type {
          tailf:info
            "OSPF metric type for default routes";
          when '../default-information-originate' {
            tailf:xpath-root 3;
          }
          type ospf-metric-type;
          default "2";
        }
        leaf nssa-only {
          tailf:info
            "Limit default advertisement to this NSSA area";
          type empty;
        }
        leaf no-ext-capability {
          tailf:info
            "Do not send domain specific capabilities into NSSA";
          type empty;
        }
        leaf no-summary {
          tailf:info
            "Do not send summary LSA into NSSA";
          type empty;
        }
        container translate {
          tailf:info
            "Translate LSA";
          container type7 {
            tailf:info
              "From Type 7 to Type 5";
            tailf:cli-compact-syntax;
            leaf always {
              tailf:info
                "Always translate LSAs on this ABR";
              type empty;
            }
            leaf suppress-fa {
              tailf:info
                "Suppress forwarding address in translated LSAs";
              type empty;
            }
          }
        }
      }
      leaf default-cost {
        tailf:info
          "Set the summary default-cost of a NSSA/stub area";
        tailf:cli-full-command;
        tailf:cli-no-value-on-delete;
        type uint32 {
          tailf:info
            "<0-16777215;;Stub's advertised external route metric";
          range "0..16777215";
        }
      }
      list filter-list {
        tailf:info
          "Filter networks between OSPF areas";
        tailf:cli-suppress-mode;
        tailf:cli-delete-when-empty;
        tailf:cli-compact-syntax;
        key "direction";
        leaf prefix {
          tailf:cli-prefix-key;
          mandatory true;
          tailf:info
            "Filter prefixes between OSPF areas";
          type string {
            tailf:info
              "WORD;;Name of an IP prefix-list";
          }
        }
        leaf direction {
          type enumeration {
            enum "in" {
              tailf:info
                "Filter networks sent to this area";
            }
            enum "out" {
              tailf:info
                "Filter networks sent from this area";
            }
          }
        }
      }
      list range {
        tailf:info
          "Summarize routes matching address/mask (border routers only)";
        tailf:cli-compact-syntax;
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        choice advertise-choice {
          leaf advertise {
            tailf:info
              "Advertise this range (default)";
            type empty;
          }
          leaf not-advertise {
            tailf:info
              "DoNotAdvertise this range";
            type empty;
          }
        }
        leaf cost {
          tailf:info
            "User specified metric for this range";
          type uint32 {
            tailf:info
              "<0-16777215>;;Advertised metric for this range";
            range "0..16777215";
          }
        }
      }
      container range-ipv6 {
        tailf:cli-drop-node-name;
        list range {
          tailf:info
            "Summarize routes matching address/mask(border routers only)";
          tailf:cli-compact-syntax;
          tailf:cli-suppress-mode;
          tailf:cli-delete-when-empty;
          key "prefix";
          leaf prefix {
            type inet:ipv6-prefix {
              tailf:info
                "X:X:X:X::X/<0-128>;;IPv6 prefix to match";
            }
          }
          choice advertise-choice {
            leaf advertise {
              tailf:info
                "Advertise this range (default)";
              type empty;
            }
            leaf not-advertise {
              tailf:info
                "DoNotAdvertise this range";
              type empty;
            }
          }
          leaf cost {
            tailf:info
              "User specified metric for this range";
            type uint32 {
              tailf:info
                "<0-16777215>;;Advertised metric for this range";
              range "0..16777215";
            }
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            tailf:info
              "<1-65535>;;Cost of the sham-link";
            range "0..65535";
          }
        }
      }
      container stub {
        tailf:info
          "Specify a stub area";
        tailf:cli-compact-syntax;
        tailf:cli-delete-when-empty;
        presence "true";
        leaf no-summary {
          tailf:info
            "Do not send summary LSA into stub area";
          type empty;
        }
        leaf no-ext-capability {
          tailf:info
            "Do not send domain specific capabilities into stub area";
          type empty;
        }
      }
      list virtual-link {
        tailf:info
          "Define a virtual link and its parameters";
        tailf:cli-suppress-mode;
        tailf:cli-delete-when-empty;
        tailf:cli-compact-syntax;
        key "id";
        leaf id {
          type inet:ipv4-address {
            tailf:info
              "A.B.C.D;;ID (IP addr) associated with virtual link neighbor";
          }
        }
        leaf retransmit-interval {
          tailf:info
            "LSA retransmit interval";
          type uint16 {
            tailf:info
              "<1-8192>;;Seconds";
            range "1..8192";
          }
        }
        leaf transmit-delay {
          tailf:info
            "LSA transmission delay";
          type uint16 {
            tailf:info
              "<1-8192>;;Seconds";
            range "1..8192";
          }
          default "1";
        }
        leaf hello-interval {
          tailf:info
            "Hello packet interval";
          type int32 {
            range "1..8192";
            tailf:info
              "<1-8192;;Seconds>";
          }
        }
        leaf dead-interval {
          tailf:info
            "Dead router detection time";
          type uint16 {
            range "1..8192";
            tailf:info
              "<1-8192;;Seconds>";
          }
        }
        leaf authentication {
          tailf:info
            "Set authentication type";
          type empty;
        }
        container authentication-key {
          tailf:info
            "Set authentication key";
          tailf:cli-flatten-container;
          tailf:cli-compact-syntax;
          tailf:cli-sequence-commands {
            tailf:cli-reset-siblings;
          }
          leaf auth-type {
            tailf:cli-drop-node-name;
            tailf:cli-optional-in-sequence;
            tailf:cli-incomplete-command;
            type uint8 {
              tailf:info
                "<0-7>;;Encryption type (0 for not yet encrypted, 7 for proprietary)";
              range "0..7";
            }
            default "0";
          }
          leaf auth-key {
            tailf:cli-drop-node-name;
            tailf:cli-full-command;
            type string {
              tailf:info
                "WORD;;Authentication key (8 chars)";
              length "1..8";
            }
          }
        }
        list message-digest-key {
          tailf:info
            "Set message digest key";
          tailf:cli-suppress-mode;
          tailf:cli-delete-when-empty;
          tailf:cli-compact-syntax;
          tailf:cli-incomplete-command;
          key "id";
          leaf id {
            tailf:cli-suppress-range;
            type uint8 {
              tailf:info
                "<1-255>;;Key ID";
              range "1..255";
            }
          }
          container md5 {
            tailf:info
              "Use MD5 algorithm";
            tailf:cli-compact-syntax;
            tailf:cli-sequence-commands {
              tailf:cli-reset-siblings;
            }
            leaf auth-type {
              tailf:cli-drop-node-name;
              tailf:cli-optional-in-sequence;
              tailf:cli-incomplete-command;
              type uint8 {
                tailf:info
                  "<0-7>;;Encryption type (0 for not yet encrypted, 7 for proprietary)";
                range "0..7";
              }
              default "0";
            }
            leaf auth-key {
              tailf:cli-drop-node-name;
              tailf:cli-full-command;
              type string {
                tailf:info
                  "WORD;;Authentication key (16 chars)";
                length "1..16";
              }
            }
          }
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1..4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      tailf:cli-show-no;
      presence "true";
      leaf detail {
        tailf:info
          "Log all state changes";
        type empty;
      }
    }
    container max-lsa {
      tailf:info
        "maximum number of LSAs OSPF process will receive";
      tailf:cli-compact-syntax;
      tailf:cli-sequence-commands {
        tailf:cli-reset-all-siblings;
      }
      leaf maximum-number {
        tailf:cli-drop-node-name;
        type uint32 {
          tailf:info
            "<1-4294967294>;;Maximum number of non self-generated LSAs this process can receive";
          range "1..4294967294";
        }
      }
      leaf threshold-percentage {
        tailf:cli-break-sequence-commands;
        tailf:cli-drop-node-name;
        type uint8 {
          tailf:info
            "<1-100>;;Threshold value (%) at which to generate a warning msg";
          range "1..100";
        }
      }
      leaf warning-only {
        tailf:info
          "Only give warning message when limit is exceeded";
        tailf:cli-full-command;
        type empty;
      }
      leaf ignore-time {
        tailf:info
          "time during which all adjacencies are suppressed";
        type uint32 {
          tailf:info
            "<1-17895>;;number of minutes during which all adjacencies are suppressed";
          range "1..17895";
        }
      }
      leaf reset-time {
        tailf:info
          "time after which ignore-count is reset to zero";
        type uint32 {
          tailf:info
            "<2-35791>;;number of minutes after which ignore-count is reset to zero";
          range "2..35791";
        }
        default "60";
      }
      leaf ignore-count {
        tailf:info
          "maximum number of times adjacencies can be suppressed";
        type uint32 {
          range "1..65534";
          tailf:info
            "<1-65534>;;count on how many times adjacencies can be suppressed";
        }
      }
    }
    uses passive-interface-grouping;
    container queue-depth {
      tailf:info
        "OSPF Hello/Router process queue depth";
      leaf hello {
        tailf:info
          "OSPF Hello process queue depth";
        type union {
          type uint32 {
            tailf:info
              "<1-2147483647>;;maximum numer of packets in the queue";
            range "1..2147483647";
          }
          type enumeration {
            enum "unlimited" {
              tailf:info
                "Unlimited queue depth";
            }
          }
        }
        default "unlimited";
      }
      leaf update {
        tailf:info
          "OSPF Router process queue depth";
        type union {
          type uint32 {
            tailf:info
              "<1-2147483647>;;maximum numer of packets in the queue";
            range "1..2147483647";
          }
          type enumeration {
            enum "unlimited" {
              tailf:info
                "Unlimited queue depth";
            }
          }
        }
      }
    }
    container timers {
      tailf:info
        "Adjust routing timers";
      container lsa {
        tailf:info
          "OSPF LSA timers";
        leaf arrival {
          tailf:info
            "OSPF LSA arrival timer";
          type uint32 {
            range "0..600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            range "5..100";
            tailf:info
              "<5-100>;;The minimum interval in msec to pace limit flooding on interface";
          }
        }
        leaf lsa-group {
          tailf:info
            "OSPF LSA group pacing timer";
          tailf:cli-full-command;
          type uint32 {
            range "10..1800";
            tailf:info
              "<10-1800>;;Interval in sec between group of LSA being refreshed or maxaged";
          }
        }
        leaf retransmission {
          tailf:info
            "OSPF retransmission pacing timer";
          tailf:cli-full-command;
          type uint32 {
            range "5..200";
            tailf:info
              "<5-200>;;The minimum interval in msec between neighbor retransmissions";
          }
        }
      }
      container throttle {
        tailf:info
          "OSPF throttle timers";
        container lsa {
          tailf:info
            "OSPF LSA throttle timers";
          tailf:cli-compact-syntax;
          tailf:cli-sequence-commands;
          leaf all {
            tailf:info
              "For all type of OSPF LSAs";
            tailf:cli-optional-in-sequence;
            tailf:cli-incomplete-command;
            type empty;
          }
          leaf start-interval {
            tailf:cli-drop-node-name;
            tailf:cli-incomplete-command;
            type uint32 {
              tailf:info
                "<0-600000>;;Delay to generate first occurrence of LSA in milliseconds";
              range "0..600000";
            }
          }
          leaf hold-interval {
            tailf:cli-drop-node-name;
            tailf:cli-incomplete-command;
            type uint32 {
              tailf:info
                "<0-600000>;;Minimum delay between originating the same LSA in milliseconds";
              range "0..600000";
            }
          }
          leaf max-interval {
            tailf:cli-drop-node-name;
            type uint32 {
              tailf:info
                "<0-600000>;;Maximum delay between originating the same LSA in milliseconds";
              range "0..600000";
            }
          }
        }
        container spf {
          tailf:info
            "OSPF SPF throttle timers";
          tailf:cli-sequence-commands;
          tailf:cli-compact-syntax;
          leaf spf-start {
            tailf:cli-drop-node-name;
            tailf:cli-incomplete-command;
            type uint32 {
              tailf:info
                "<0-600000>;;Delay between receiving a change to SPF calculation in milliseconds";
              range "0..600000";
            }
          }
          leaf spf-hold {
            tailf:cli-drop-node-name;
            tailf:cli-incomplete-command;
            type uint32 {
              tailf:info
                "<0-600000>;;Delay between first and second SPF calculation in milliseconds";
              range "0..600000";
            }
          }
          leaf spf-max-wait {
            tailf:cli-drop-node-name;
            type uint32 {
              tailf:info
                "<0-600000>;;Maximum wait time in milliseconds for SPF calculations";
              range "0..600000";
            }
          }
        }
      }
    }
    leaf router-id {
      tailf:cli-full-command;
      tailf:info
        "Override configured router identifier (peers will reset)";
      type inet:ipv4-address {
        tailf:info
          "A.B.C.D;;Manually configured router identifier";
      }
    }
  }

  grouping router-ospf-grouping {
    container capability {
      tailf:info
        "Enable specific OSPF feature";
      leaf opaque {
        tailf:info
          "Opaque LSA";
        tailf:cli-boolean-no;
        tailf:cli-full-command;
        type boolean;
        default "true";
      }
      leaf lls {
        tailf:info
          "Link-local Signaling (LLS) support";
        tailf:cli-boolean-no;
        tailf:cli-full-command;
        type boolean;
        default "true";
      }
      leaf transit {
        tailf:info
          "Transit Area";
        tailf:cli-boolean-no;
        tailf:cli-full-command;
        type boolean;
        default "true";
      }
    }
    container compatible {
      tailf:info
        "OSPF compatibility list";
      leaf rfc1583 {
        tailf:info
          "compatible with RFC 1583";
        tailf:cli-boolean-no;
        type boolean;
        default "true";
      }
    }
    uses router-distribute-list-grouping;
    container domain-id {
      tailf:info
        "OSPF domain-id";
      choice domain-id-choice {
        case a {
          leaf ip-format {
            tailf:cli-drop-node-name;
            type inet:ipv4-address {
              tailf:info
                "A.B.C.D;;OSPF domain ID in IP address format";
            }
          }
          container ip-format-secondary {
            tailf:cli-drop-node-name;
            tailf:cli-compact-syntax;
            tailf:cli-sequence-commands;
            leaf ip {
              tailf:cli-drop-node-name;
              type inet:ipv4-address {
                tailf:info
                  "A.B.C.D;;OSPF domain ID in IP address format";
              }
            }
            leaf secondary {
              tailf:info
                "Secondary Domain-ID";
              type empty;
            }
          }
        }
        leaf Null {
          tailf:info
            "Null Domain-ID";
          tailf:cli-full-command;
          type empty;
        }
        container type {
          tailf:info
            "OSPF domain ID type in Hex format";
          tailf:cli-sequence-commands;
          tailf:cli-compact-syntax;
          leaf type-leaf {
            tailf:cli-drop-node-name;
            tailf:cli-incomplete-command;
            type enumeration {
              enum "0005" {
                tailf:info
                  "Type 0x0005";
              }
              enum "0105" {
                tailf:info
                  "Type 0x0105";
              }
              enum "0205" {
                tailf:info
                  "Type 0x0205";
              }
              enum "8005" {
                tailf:info
                  "Type 0x8005";
              }
            }
          }
          leaf value {
            tailf:info
              "OSPF domain ID value in Hex format";
            type string {
              tailf:info
                "Hex-data;;OSPF domain ID ext. community value in Hex";
              pattern '[0-9a-fA-F]{12}';
            }
          }
        }
      }
    }
    leaf domain-tag {
      tailf:info
        "OSPF domain-tag";
      tailf:cli-full-command;
      type uint32 {
        range "1..4294967295";
        tailf:info
          "<1-4294967295>;;OSPF domain tag - 32-bit value";
      }
    }
    container ignore {
      tailf:info
        "Do not complain about specific event";
      container lsa {
        tailf:info
          "Do not complain upon receiving LSA of the specified type";
        leaf mospf {
          tailf:info
            "MOSPF Type 6 LSA";
          type empty;
        }
      }
    }
    leaf ispf {
      tailf:info
        "Enable incremental SPF computation";
      tailf:cli-full-command;
      type empty;
    }
    container limit {
      tailf:info
        "Limit a specific OSPF feature";
      container retransmissions {
        tailf:info
          "LS update, DBD, and LS request retransmissions";
        tailf:cli-compact-syntax;
        leaf dc {
          tailf:info
            "Demand circuit retransmissions";
          type limit-dc-non-dc-type;
        }
        leaf non-dc {
          tailf:info
            "Non-demand-circuit retransmissions";
          type limit-dc-non-dc-type;
        }
      }
    }
    container local-rib-criteria {
      tailf:info
        "Enable or disable usage of local RIB as route criteria";
      tailf:cli-compact-syntax;
      leaf forwarding-address {
        tailf:info
          "Local RIB used to validate external/NSSA forwarding addresses";
        type empty;
      }
      leaf inter-area-summary {
        tailf:info
          "Local RIB used as criteria for inter-area summaries";
        type empty;
      }
      leaf nssa-translation {
        tailf:info
          "Local RIB used as criteria for NSSA translation";
        type empty;
      }
    }
    container max-metric {
      tailf:info
        "Set maximum metric";
      container router-lsa {
        tailf:info
          "Maximum metric in self-originated router-LSAs";
        tailf:cli-compact-syntax;
        presence "true";
        leaf include-stub {
          tailf:info
            "Set maximum metric for stub links in router-LSAs";
          type empty;
        }
        leaf summary-lsa {
          tailf:info
            "Override summary-lsa metric with max-metric value";
          type empty;
        }
        leaf summary-lsa-max-metric-value {
          when '../summary-lsa' {
            tailf:xpath-root 3;
          }
          tailf:cli-drop-node-name;
          type uint32 {
            tailf:info
              " <1-16777215>;;Overriding metric in summary-LSAs (default 16711680)";
            range "1..16777215";
          }
        }
        leaf external-lsa {
          tailf:info
            "Override external-lsa metric with max-metric value";
          type empty;
        }
        leaf external-lsa-max-metric-value {
          when '../external-lsa' {
            tailf:xpath-root 3;
          }
          tailf:cli-drop-node-name;
          type uint32 {
            tailf:info
              "<1-16777215>;;Overriding metric in external-LSAs (default 16711680)";
            range "1..16777215";
          }
        }
        container on-startup {
          tailf:info
            "Set maximum metric temporarily after reboot";
          tailf:cli-flatten-container;
          tailf:cli-compact-syntax;
          choice time-wait-for-bgp-choice {
            leaf seconds {
              tailf:cli-drop-node-name;
              type uint32 {
                tailf:info
                  "<5-86400>;;Time, in seconds, router-LSAs are originated with max-metric";
                range "5..86400";
              }
            }
            leaf wait-for-bgp {
              tailf:info
                "Let BGP decide when to originate router-LSA with normal metric";
              type empty;
            }
          }
        }
      }
    }
    container mpls {
      tailf:info
        "Configure MPLS routing protocol parameters";
      container ldp {
        tailf:info
          "routing protocol commands for MPLS LDP";
        container autoconfig {
          tailf:info
            "Configure LDP automatic configuration";
          presence "Configure LDP automatic configuration";
          leaf area {
            tailf:info
              "Configure an OSPF area to run MPLS LDP";
            type ospf-area-type;
          }
        }
        container sync {
          tailf:info
            "Configure LDP-IGP Synchronization";
          presence "Configure LDP-IGP Synchronization";
        }
      }
      container traffic-eng {
        tailf:info
          "routing protocol commands for MPLS Traffic Engineering";
        tailf:cli-compact-syntax;
        leaf multicast-intact {
          tailf:info
            "MPLS TE and PIM interaction";
          tailf:cli-full-command;
          type empty;
        }
        leaf area {
          tailf:info
            "configure an ospf area to run MPLS Traffic Engineering";
          tailf:cli-full-command;
          type ospf-area-type;
        }
        container interface {
          tailf:info
            "MPLS TE interface configuration for this OSPF process";
          tailf:cli-sequence-commands;
          leaf name {
            tailf:cli-drop-node-name;
            tailf:cli-incomplete-command;
            type string {
              tailf:info
                "WORD;;Interface name";
            }
          }
          leaf area {
            tailf:info
              "advertise MPLS TE information for this interface into area";
            type uint32 {
              tailf:info
                "<0-0>;;OSPF area ID as a decimal value";
            }
          }
        }
        container mesh-group-container {
          tailf:cli-drop-node-name;
          tailf:cli-sequence-commands;
          leaf mesh-group {
            tailf:info
              "Traffic Engineering Mesh-Group advertisement";
            tailf:cli-incomplete-command;
            type uint32 {
              range "0..4294967295";
              tailf:info
                "<0-4294967295>;;Mesh Group Id";
            }
          }
          leaf interface {
            tailf:info
              "Interface";
            tailf:cli-incomplete-command;
            type string {
              tailf:info
                "WORD;;Interface name";
            }
          }
          list area {
            tailf:info
              "configure flooding scope as area";
            tailf:cli-suppress-mode;
            tailf:cli-delete-when-empty;
            key "id";
            leaf id {
              tailf:cli-suppress-range;
              type ospf-area-type;
            }
          }
        }
        container router-id {
          tailf:info
            "Traffic Engineering stable IP address for system";
          leaf interface {
            tailf:info
              "Interface";
            type string {
              tailf:info
                "WORD;;Interface name";
            }
          }
        }
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
      container cost-database-filter-container {
        tailf:cli-drop-node-name;
        tailf:cli-compact-syntax;
        leaf cost {
          tailf:info
            "OSPF cost for point-to-multipoint neighbor";
          type uint32 {
            tailf:info
              "<1-65535>;;metric";
            range "1..65535";
          }
        }
        container database-filter {
          tailf:info
            "Filter OSPF LSA during synchronization and flooding for point-to-multipoint neighbor";
          tailf:cli-flatten-container;
          tailf:cli-compact-syntax;
          container all {
            tailf:info
              "Filter all LSA";
            tailf:cli-flatten-container;
            tailf:cli-compact-syntax;
            leaf out {
              tailf:info
                "Outgoing LSA";
              type empty;
            }
          }
        }
      }
      container poll-interval-priority-container {
        tailf:cli-drop-node-name;
        tailf:cli-compact-syntax;
        leaf poll-interval {
          tailf:info
            "OSPF dead-router polling interval";
          type uint32 {
            tailf:info
              "<0-65535>;;Seconds";
            range "0..65535";
          }
        }
        leaf priority {
          tailf:info
            "OSPF priority of non-broadcast neighbor";
          type uint32 {
            tailf:info
              "<0-255>;;Priority";
            range "0..255";
          }
        }
      }
    }
    list network {
      tailf:info
        "Enable routing on an IP network";
      tailf:cli-incomplete-command;
      tailf:cli-suppress-mode;
      tailf:cli-delete-when-empty;
      key "ip mask";
      leaf ip {
        type inet:ipv4-address {
          tailf:info
            "A.B.C.D;;Network number";
        }
      }
      leaf mask {
        type inet:ipv4-address {
          tailf:info
            "A.B.C.D;;OSPF wild card bits";
        }
      }
      leaf area {
        tailf:info
          "Set the OSPF area ID";
        type ospf-area-type;
      }
    }
    container nsf {
      tailf:info
        "Non-stop forwarding";
      presence "true";
      container cisco {
        tailf:info
          "Cisco Non-stop forwarding";
        tailf:cli-delete-when-empty;
        presence "true";
        container helper {
          tailf:info
            "helper support";
          presence "true";
          leaf disable {
            tailf:info
              "disable helper support";
            tailf:cli-reset-container;
            type empty;
          }
        }
      }
      container ietf {
        tailf:info
          "IETF graceful restart";
        container helper {
          tailf:info
            "helper support";
          presence "helper support";
          leaf disable {
            tailf:info
              "disable helper support";
            tailf:cli-reset-container;
            tailf:cli-delete-container-on-delete;
            type empty;
          }
          leaf strict-lsa-checking {
            tailf:info
              "enable helper strict LSA checking";
            type empty;
          }
        }
      }
    }
    leaf prefix-suppression {
      tailf:info
        "OSPF prefix suppression";
      tailf:cli-full-command;
      type empty;
    }
    container process-min-time {
      tailf:info
        "Percentage of quantum to be used before releasing CPU";
      leaf percent {
        tailf:info
          "percent";
        type uint32 {
          range "1..100";
          tailf:info
            "<1-100>;;Minimum CPU quantum";
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    leaf shutdown {
      tailf:info
        "Shutdown the OSPF protocol under the current instance";
      tailf:cli-boolean-no;
      type boolean;
    }
    list summary-address {
      tailf:info
        "Configure IP address summaries";
      tailf:cli-suppress-mode;
      tailf:cli-delete-when-empty;
      key "ip wildcard";
      leaf ip {
        type inet:ipv4-address {
          tailf:info
            "A.B.C.D;;IP summary address";
        }
      }
      leaf wildcard {
        type inet:ipv4-address {
          tailf:info
            "A.B.C.D;;Summary mask";
        }
      }
      choice tag-no-advertise-choice {
        leaf tag {
          tailf:info
            "Set tag";
          tailf:cli-full-command;
          type uint32 {
            range "0..4294967295";
            tailf:info
              "<0-4294967295>;;32-bit tag value";
          }
        }
        leaf not-advertise {
          tailf:info
            "Do not advertise when translating OSPF type-7 LSA";
          type empty;
          tailf:cli-full-command;
        }
      }
    }
    container discard-route {
      tailf:info
        "Enable or disable discard-route installation";
      tailf:cli-compact-syntax;
      presence "true";
      leaf external {
        tailf:info
          "Discard route for redistributed summarised routes";
        type uint32 {
          tailf:info
            "<1-255>;;Administrative distance for redistributed summarised routes";
          range "1..255";
        }
      }
      leaf internal {
        tailf:info
          "Discard route for summarised internal routes";
        type uint32 {
          tailf:info
            "<1-255>;;Administrative distance for summarised internal routes";
          range "1..255";
        }
      }
    }
  }

  grouping router-ospfv3-grouping;

  grouping ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        tailf:info
          "<0-4294967295>;;32-bit tag value";
        range "0..4294967295";
      }
    }
  }

  grouping ospf-iso-igrp-redistribute-grouping {
    leaf metric {
      tailf:info
        "Metric for redistributed routes";
      type uint32 {
        tailf:info
          "<0-16777214>;;OSPF default metric";
      }
    }
    leaf metric-type {
      tailf:info
        "OSPF/IS-IS exterior metric type for redistributed routes";
      type enumeration {
        enum "1" {
          tailf:info
            "Set OSPF External Type 1 metrics";
        }
        enum "2" {
          tailf:info
            "Set OSPF External Type 2 metrics";
        }
      }
      default "2";
    }
    leaf tag {
      tailf:info
        "Set tag for routes redistributed into OSPF";
      type uint32 {
        tailf:info
          "<0-4294967295>;;32-bit tag value";
        range "0..4294967295";
      }
    }
    leaf level {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    leaf subnets {
      tailf:info
        "Consider subnets for redistribution into OSPF";
      type empty;
    }
  }

  grouping router-ospf-redistribute-grouping {
    uses ospf-iso-igrp-redistribute-grouping;
    leaf route-map {
      tailf:info
        "Route map reference";
      type string {
        tailf:info
          "WORD;;Pointer to route-map entries";
      }
    }
  }

  grouping router-rip-af-grouping {
    leaf auto-summary {
      tailf:info
        "Enable automatic network number summarization";
      tailf:cli-boolean-no;
      tailf:cli-full-command;
      type boolean;
      default "true";
    }
    leaf maximum-paths {
      tailf:info
        "Forward packets over multiple paths";
      tailf:cli-full-command;
      type uint8 {
        tailf:info
          "1-32;;Number of paths";
        range "1..32";
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
    }
    list network {
      tailf:info
        "Enable routing on an IP network";
      tailf:cli-suppress-mode;
      tailf:cli-delete-when-empty;
      key "ip";
      leaf ip {
        type inet:ipv4-address {
          tailf:info
            "A.B.C.D;;Network number";
        }
      }
    }
    leaf validate-update-source {
      tailf:info
        "Perform sanity checks against source address of routing updates";
      tailf:cli-boolean-no;
      tailf:cli-full-command;
      type boolean;
      default "true";
    }
    container default-information {
      tailf:info
        "Control distribution of default information";
      container originate {
        tailf:info
          "Distribute a default route";
        presence "true";
        leaf route-map {
          tailf:info
            "Route-map reference";
          type string {
            tailf:info
              "WORD;;Route map name";
          }
        }
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      tailf:cli-compact-syntax;
      leaf distance-leaf {
        tailf:cli-drop-node-name;
        tailf:cli-full-command;
        type uint8 {
          tailf:info
            "1-255;;Administrative distance";
          range "1..255";
        }
      }
      list distance-list {
        tailf:cli-drop-node-name;
        tailf:cli-suppress-mode;
        tailf:cli-delete-when-empty;
        key "number ip mask";
        leaf number {
          tailf:cli-suppress-range;
          type uint8 {
            tailf:info
              "1-255;;Administrative distance";
            range "1..255";
          }
        }
        leaf ip {
          type inet:ipv4-address {
            tailf:info
              "A.B.C.D;;IP source address";
          }
        }
        leaf mask {
          type inet:ipv4-address {
            tailf:info
              "A.B.C.D;;Wildcard bits";
          }
        }
        leaf access-list {
          tailf:cli-drop-node-name;
          type std-ip-acl-type;
        }
      }
    }
    uses router-distribute-list-grouping;
    list offset-list {
      tailf:info
        "Add or subtract offset from RIP metrics";
      tailf:cli-suppress-mode;
      tailf:cli-delete-when-empty;
      tailf:cli-compact-syntax;
      tailf:cli-sequence-commands;
      tailf:cli-incomplete-command;
      key "direction";
      leaf direction {
        type enumeration {
          enum "in" {
            tailf:info
              "Perform offset on incoming updates";
          }
          enum "out" {
            tailf:info
              "Perform offset on outgoing updates";
          }
        }
      }
      leaf id {
        tailf:cli-drop-node-name;
        tailf:cli-prefix-key;
        type rip-offset-list-id-type;
      }
      leaf offset {
        tailf:cli-drop-node-name;
        type uint8 {
          tailf:info
            "<0-16>;;Offset";
          range "0..16";
        }
      }
    }
    container redistribute {
      tailf:info
        "Redistribute information from another routing protocol";
      container connected {
        tailf:info
          "Connected";
        tailf:cli-compact-syntax;
        presence "true";
        uses rip-metric-route-map-grouping;
      }
      container bgp {
        tailf:info
          "Border Gateway Protocol (BGP)";
        tailf:cli-compact-syntax;
        leaf as-number {
          tailf:cli-drop-node-name;
          type union {
            type uint32 {
              tailf:info
                "<1-4294967295>;;Autonomous system number";
            }
            type string {
              tailf:info
                "<1.0-XX.YY>;;Autonomous system number";
            }
          }
        }
        uses rip-metric-route-map-grouping;
      }
      list eigrp {
        tailf:info
          "Enhanced Interior Gateway Routing Protocol (EIGRP)";
        tailf:cli-suppress-mode;
        tailf:cli-delete-when-empty;
        tailf:cli-compact-syntax;
        key "as-number";
        leaf as-number {
          type uint16 {
            tailf:info
              "<1-65535>;;AS number";
            range "1..65535";
          }
        }
        uses rip-metric-route-map-grouping;
      }
      container isis {
        tailf:info
          "ISO IS-IS";
        tailf:cli-compact-syntax;
        tailf:cli-delete-when-empty;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses rip-metric-route-map-grouping;
        }
        leaf level {
          tailf:cli-drop-node-name;
          type isis-level-type;
        }
        uses rip-metric-route-map-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses rip-metric-route-map-grouping;
        }
        uses rip-metric-route-map-grouping;
      }
      container mobile {
        tailf:info
          "Mobile routes";
        tailf:cli-compact-syntax;
        presence "Mobile routes";
        uses rip-metric-route-map-grouping;
      }
      container odr {
        tailf:info
          "On Demand stub Routes";
        tailf:cli-compact-syntax;
        presence "On Demand stub Routes";
        uses rip-metric-route-map-grouping;
      }
      list ospf {
        tailf:info
          "Open Shortest Path First (OSPF)";
        tailf:cli-suppress-mode;
        tailf:cli-delete-when-empty;
        tailf:cli-compact-syntax;
        key "process-id";
        leaf process-id {
          tailf:cli-suppress-range;
          type uint16 {
            tailf:info
              "<1-65535>;;Process ID";
            range "1..65535";
          }
        }
        uses rip-metric-route-map-grouping;
        container match {
          tailf:info
            "Redistribution of OSPF routes";
          tailf:cli-flatten-container;
          tailf:cli-compact-syntax;
          uses redistribute-ospf-match-grouping;
          uses rip-metric-route-map-grouping;
        }
      }
      container static {
        tailf:info
          "Static routes";
        tailf:cli-compact-syntax;
        tailf:cli-delete-when-empty;
        presence "Static routes";
        uses rip-metric-route-map-grouping;
      }
      container rip {
        tailf:info
          "Routing Information Protocol (RIP)";
        tailf:cli-compact-syntax;
        presence "true";
        uses rip-metric-route-map-grouping;
      }
    }
    container timers {
      tailf:info
        "Adjust routing timers";
      tailf:cli-incomplete-no;
      tailf:cli-compact-syntax;
      container basic {
        tailf:info
          "Basic routing protocol update timers";
        tailf:cli-compact-syntax;
        tailf:cli-sequence-commands;
        tailf:cli-full-no;
        leaf updates {
          tailf:cli-drop-node-name;
          tailf:cli-incomplete-command;
          tailf:cli-no-value-on-delete;
          type uint32 {
            tailf:info
              "1-4294967295;;Interval between updates for RIP";
            range "1..4294967295";
          }
        }
        leaf invalid {
          tailf:cli-drop-node-name;
          tailf:cli-incomplete-command;
          tailf:cli-no-value-on-delete;
          type uint32 {
            tailf:info
              "1-4294967295;;Invalid";
            range "1..4294967295";
          }
        }
        leaf holddown {
          tailf:cli-drop-node-name;
          tailf:cli-incomplete-command;
          tailf:cli-no-value-on-delete;
          type uint32 {
            tailf:info
              "1-4294967295;;Holddown";
            range "1..4294967295";
          }
        }
        leaf flush {
          tailf:cli-drop-node-name;
          tailf:cli-incomplete-command;
          tailf:cli-no-value-on-delete;
          type uint32 {
            tailf:info
              "1-4294967295;;Flush";
            range "1..4294967295";
          }
        }
        leaf sleep {
          tailf:cli-drop-node-name;
          tailf:cli-no-value-on-delete;
          type uint32 {
            tailf:info
              "1-4294967295;;Sleep time, in milliseconds";
            range "1..4294967295";
          }
        }
      }
    }
    leaf version {
      tailf:info
        "Set routing protocol version";
      tailf:cli-diff-dependency "/ios:ip/routing" {
        tailf:xpath-root 3;
        tailf:cli-trigger-on-set;
      }
      type uint8 {
        tailf:info
          "1-2;;rip version 1 or 2";
        range "1..2";
      }
    }
    container traffic-share {
      tailf:info
        "How to compute traffic share over alternate paths";
      container min {
        tailf:info
          "All traffic shared among min metric paths";
        leaf across-interfaces {
          tailf:info
            "Use different interfaces for equal-cost paths";
          type empty;
        }
      }
    }
  }

  grouping router-rip-grouping {
    uses router-rip-af-grouping;
    uses passive-interface-grouping;
    leaf output-delay {
      tailf:info
        "Interpacket delay for RIP updates";
      tailf:cli-full-command;
      type uint8 {
        tailf:info
          "8-50;;Delay in milliseconds";
        range "8..50";
      }
    }
    leaf input-queue {
      tailf:info
        "Specify input queue depth";
      tailf:cli-full-command;
      type uint16 {
        tailf:info
          "0-1024;;queue depth";
        range "0..1024";
      }
    }
    leaf flash-update-threshold {
      tailf:info
        "Specify flash update threshold in second";
      tailf:cli-full-command;
      type uint8 {
        tailf:info
          "<0-30>;;threshold in seconds";
        range "0..30";
      }
    }
  }

  grouping rip-metric-route-map-grouping {
    leaf metric {
      tailf:info
        "Metric for redistributed routes";
      type union {
        type uint8 {
          tailf:info
            "<0-16>;;Default metric";
          range "0..16";
        }
        type enumeration {
          enum "transparent" {
            tailf:info
              "Transparently redistribute metric";
          }
        }
      }
    }
    leaf route-map {
      tailf:info
        "Route map reference";
      type string {
        tailf:info
          "WORD;;Pointer to route-map entries";
      }
    }
  }

  grouping eigrp-metric-route-map-grouping {
    container metric {
      tailf:info
        "Metric for redistributed routes";
      tailf:cli-flatten-container;
      tailf:cli-compact-syntax;
      tailf:cli-sequence-commands {
        tailf:cli-reset-siblings;
      }
      leaf bandwidth-metric {
        tailf:cli-drop-node-name;
        tailf:cli-incomplete-command;
        type uint32 {
          tailf:info
            "<1-4294967295>;;Bandwidth metric in Kbits per second";
        }
      }
      leaf delay-metric {
        tailf:cli-drop-node-name;
        tailf:cli-incomplete-command;
        type uint32 {
          tailf:info
            "<0-4294967295>;;EIGRP delay metric, in 10 microsecond units";
        }
      }
      leaf reliability-metric {
        tailf:cli-drop-node-name;
        tailf:cli-incomplete-command;
        type uint8 {
          tailf:info
            "<0-255>;;EIGRP reliability metric where 255 is 100% reliable";
        }
      }
      leaf effective-bandwidth-metric {
        tailf:cli-drop-node-name;
        tailf:cli-incomplete-command;
        type uint8 {
          tailf:info
            "<1-255>;;EIGRP Effective bandwidth metric (Loading) where 255 is 100% loaded";
          range "1..255";
        }
      }
      leaf mtu-bytes {
        tailf:cli-drop-node-name;
        type uint16 {
          tailf:info
            "<1-65535>;;EIGRP MTU of the path";
          range "1..65535";
        }
      }
    }
    leaf route-map {
      tailf:info
        "Route map reference";
      type string {
        tailf:info
          "WORD;;Pointer to route-map entries";
      }
    }
  }

  grouping narrow-wide-transition-grouping {
    leaf narrow-wide {
      tailf:cli-drop-node-name;
      tailf:cli-full-command;
      type isis-level-type;
    }
    leaf transition {
      tailf:info
        "Accept both styles of TLVs during transition";
      tailf:cli-full-command;
      type isis-level-type;
    }
  }

  grouping spf-intervals-grouping {
    leaf interval {
      tailf:cli-drop-node-name;
      type uint32 {
        tailf:info
          "<1-120>;;Interval between consecutive SPFs in seconds";
        range "1..120";
      }
    }
    leaf initial-wait {
      tailf:cli-drop-node-name;
      type uint32 {
        tailf:info
          "<1-120000>;;Initial wait before first SPF in milliseconds";
        range "1..120000";
      }
    }
    leaf minimum-wait {
      tailf:cli-drop-node-name;
      type uint32 {
        tailf:info
          "<1-120000>;;Minimum wait between first and second SPF in milliseconds";
        range "1..120000";
      }
    }
  }

  grouping router-isis-authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping lsp-gen-interval-grouping {
    leaf interval {
      tailf:cli-drop-node-name;
      type uint32 {
        range "1..120";
        tailf:info
          "<1-120>;;Interval in seconds";
      }
    }
    leaf initial-wait {
      tailf:cli-drop-node-name;
      type uint32 {
        range "1..120000";
        tailf:info
          "<1-120000>;;Initial wait in milliseconds";
      }
    }
    leaf wait {
      tailf:cli-drop-node-name;
      type uint32 {
        range "1..120000";
        tailf:info
          "<1-120000>;;Wait between first and second lsp generation in milliseconds";
      }
    }
  }

  grouping set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping summary-address-metric-tag-grouping {
    leaf metric {
      tailf:info
        "Set metric for summay route";
      tailf:cli-full-command;
      type uint32 {
        range "1..4294967295";
        tailf:info
          "<1-4294967295>;;metric";
      }
    }
    leaf tag {
      tailf:info
        "Set tag";
      type uint32 {
        range "1..4294967295";
        tailf:info
          "<1-4294967295>;;32-bit tag value";
      }
    }
  }

  grouping authentication-level-grouping {
    leaf level {
      tailf:cli-drop-node-name;
      type authentication-level-type;
    }
  }

  grouping redist-level-grouping {
    leaf level {
      tailf:cli-drop-node-name;
      tailf:cli-break-sequence-commands;
      type isis-level-type;
    }
  }

  grouping isis-redist-container-content-grouping {
    uses redist-level-grouping;
    leaf metric {
      tailf:info
        "ISIS default metric";
      type uint32 {
        tailf:info
          "<0-4294967295>;;ISIS default metric";
        range "0..4294967295";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    leaf route-map {
      tailf:info
        "Route map reference";
      type string {
        tailf:info
          "WORD;;Pointer to route-map entries";
      }
    }
  }

  grouping router-isis-redistribute-grouping {
    uses isis-redist-container-content-grouping;
  }

  grouping isis-redist-af-grouping {
    container isis-redist-af-container {
      tailf:cli-drop-node-name;
      leaf include-connected {
        tailf:info
          "Include connected";
        type empty;
      }
      uses isis-redist-container-content-grouping;
    }
  }

  grouping isis-redist-ospf-match-grouping {
    uses redist-level-grouping;
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
  }

  grouping isis-redist-clns-ip-grouping {
    uses router-isis-redistribute-grouping;
    container clns {
      tailf:info
        "Redistribution of BGP NSAP routes";
      presence "Redistribution of BGP NSAP routes";
      leaf route-map {
        tailf:info
          "Route map reference";
        type string {
          tailf:info
            "WORD;;Pointer to route-map entries";
        }
      }
    }
    leaf ip {
      tailf:info
        "Redistribution of BGP IP routes";
      type empty;
    }
  }

  grouping router-isis-interface-grouping {
    container authentication {
      tailf:info
        "ISIS authentication for LSPs";
      container mode {
        tailf:info
          "Authentication mode";
        container md5 {
          tailf:info
            "Keyed message digest";
          presence "true";
          uses authentication-level-grouping;
        }
        container text {
          tailf:info
            "Clear text password";
          presence "true";
          uses authentication-level-grouping;
        }
      }
      container key-chain {
        tailf:info
          "Authentication key-chain";
        tailf:cli-compact-syntax;
        tailf:cli-sequence-commands;
        leaf name {
          tailf:cli-drop-node-name;
          type string {
            tailf:info
              "WORD;;Name of key-chain";
          }
        }
        uses authentication-level-grouping;
      }
      container send-only {
        tailf:info
          "Authentication send only, receive ignore";
        presence "true";
        uses authentication-level-grouping;
      }
    }
  }

  grouping router-isis-af-grouping {
    leaf adjacency-check {
      tailf:info
        "Check ISIS neighbor protocol support";
      tailf:cli-full-command;
      type empty;
    }
    container default-information {
      tailf:info
        "Control distribution of default information";
      tailf:cli-incomplete-no;
      container originate {
        tailf:info
          "Distribute a default route";
        presence "true";
        leaf route-map {
          tailf:info
            "Route-map reference";
          type string {
            tailf:info
              "WORD;;Route map name";
          }
        }
      }
    }
    leaf maximum-paths {
      tailf:info
        "Forward packets over multiple paths";
      tailf:cli-full-command;
      type uint32 {
        tailf:info
          "<1-32>;;Number of paths";
        range "1..32";
      }
    }
    container metric {
      tailf:info
        "Set ISIS metric for all interfaces";
      tailf:cli-compact-syntax;
      tailf:cli-sequence-commands;
      leaf default {
        tailf:cli-drop-node-name;
        type uint32 {
          tailf:info
            "<1-63>;;Default metric";
          range "1..63";
        }
      }
      leaf level-1-2 {
        tailf:cli-drop-node-name;
        type enumeration {
          enum "level-1" {
            tailf:info
              "Apply metric to level-1 links";
          }
          enum "level-2" {
            tailf:info
              "Apply metric to level-2 links";
          }
        }
      }
    }
    container prc-interval {
      tailf:info
        "Minimum interval between partial route calculations";
      tailf:cli-compact-syntax;
      tailf:cli-sequence-commands;
      leaf interval {
        tailf:cli-drop-node-name;
        type uint32 {
          tailf:info
            "<1-120>;;PRC interval in seconds";
          range "1..120";
        }
      }
      leaf initial-wait {
        tailf:cli-drop-node-name;
        type uint32 {
          tailf:info
            "<1-120000>;;Initial wait for PRC in milliseconds";
          range "1..120000";
        }
      }
      leaf minimum-wait {
        tailf:cli-drop-node-name;
        type uint32 {
          tailf:info
            "<1-120000>;;Minimum wait between first and second PRC in milliseconds";
          range "1..120000";
        }
      }
    }
    container set-overload-bit {
      tailf:info
        "Signal other routers not to use us in SPF";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  tailf:info
                    "<5-86400>;;Time in seconds to advertise ourself as overloaded after reboot";
                  range "5..86400";
                }
              }
              leaf suppress {
                tailf:info
                  "If overload-bit set, suppress the following types of IP prefixes";
                tailf:cli-incomplete-command;
                type empty;
              }
              uses set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                uses set-overload-bit-suppress-grouping;
              }
            }
          }
        }
        container suppress {
          tailf:info
            "If overload-bit set, suppress the following types of IP prefixes";
          tailf:cli-compact-syntax;
          uses set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses spf-intervals-grouping;
        }
        container intervals {
          tailf:cli-drop-node-name;
          tailf:cli-compact-syntax;
          tailf:cli-sequence-commands;
          uses spf-intervals-grouping;
        }
      }
    }
    container traffic-share {
      tailf:info
        "How to compute traffic share over alternate paths";
      container min {
        tailf:info
          "All traffic shared among min metric paths";
        leaf across-interface {
          tailf:info
            "Use different interfaces for equal-cost paths";
          type empty;
        }
      }
    }
  }

  grouping router-isis-grouping {
    container isis-main-container {
      tailf:cli-drop-node-name;
      uses router-isis-af-grouping;
      uses router-isis-interface-grouping;
      container address-family {
        tailf:info
          "Enter Address Family command mode";
        container ipv6 {
          tailf:info
            "Address family";
          container unicast {
            tailf:cli-add-mode;
            tailf:cli-mode-name "config-router-af";
            tailf:info
              "Address Family Modifier";
            tailf:cli-full-command;
            tailf:cli-exit-command "exit-address-family" {
              tailf:info
                "Exit from Address Family configuration mode";
            }
            uses router-isis-af-grouping;
            leaf distance {
              tailf:info
                "Administrative distance";
              tailf:cli-full-command;
              type uint32 {
                tailf:info
                  "<1-255>;;OSPF Administrative distance";
                range "1..255";
              }
            }
            container multi-topology {
              tailf:info
                "Enable multi-topology mode";
              presence "Enable multi-topology mode";
              leaf transition {
                tailf:info
                  "Accept and generate both IS-IS IPv6 and Multi-topology IPv6 TLVs";
                type empty;
              }
            }
            container redistribute {
              tailf:info
                "Redistribute IPv6 prefixes from another routing protocol";
              container bgp {
                tailf:info
                  "Border Gateway Protocol (BGP)";
                tailf:cli-compact-syntax;
                tailf:cli-sequence-commands;
                leaf as-number {
                  tailf:cli-drop-node-name;
                  type uint32 {
                    range "1..65535";
                    tailf:info
                      "<1-65535>;;Autonomous system number";
                  }
                }
                uses isis-redist-af-grouping;
              }
              container connected {
                tailf:info
                  "Connected";
                presence "Connected";
                uses router-isis-redistribute-grouping;
              }
              list eigrp {
                tailf:info
                  "Enhanced Interior Gateway Routing Protocol (EIGRP)";
                tailf:cli-suppress-mode;
                tailf:cli-delete-when-empty;
                key "as-number";
                leaf as-number {
                  tailf:cli-drop-node-name;
                  type uint32 {
                    range "1..65535";
                    tailf:info
                      "<1-65535>;;Autonomous system number";
                  }
                }
                uses isis-redist-af-grouping;
              }
              container isis {
                tailf:info
                  "ISO IS-IS";
                tailf:cli-compact-syntax;
                leaf area-tag {
                  tailf:cli-drop-node-name;
                  tailf:cli-disallow-value "level-1|level-2";
                  type string {
                    tailf:info
                      "WORD;;IPv6 process name";
                  }
                }
                container levels {
                  tailf:cli-drop-node-name;
                  tailf:cli-sequence-commands;
                  leaf isis-redist-levels1 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf into {
                    tailf:info
                      "from level-n into level-m";
                    tailf:cli-incomplete-command;
                    type empty;
                  }
                  leaf isis-redist-levels2 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf distribute-list {
                    tailf:info
                      "select routes";
                    type string {
                      tailf:info
                        "WORD;;IPv6 prefix-list name";
                    }
                  }
                }
              }
              container nemo {
                tailf:info
                  "Network Mobility (NEMO)";
                tailf:cli-compact-syntax;
                uses isis-redist-af-grouping;
              }
              list ospf {
                tailf:info
                  "Open Shortest Path First (OSPF)";
                tailf:cli-suppress-mode;
                tailf:cli-delete-when-empty;
                tailf:cli-compact-syntax;
                key "process-id";
                leaf process-id {
                  tailf:cli-suppress-range;
                  type uint32 {
                    tailf:info
                      "<1-65535>;;Process ID";
                    range "1..65535";
                  }
                }
                uses isis-redist-af-grouping;
                container match {
                  tailf:info
                    "Redistribution of OSPF routes";
                  tailf:cli-flatten-container;
                  tailf:cli-compact-syntax;
                  uses redistribute-ospf-match-grouping;
                  uses isis-redist-ospf-match-grouping;
                }
              }
              list rip {
                tailf:info
                  "IPv6 Routing Information Protocol (RIPv6)";
                tailf:cli-suppress-mode;
                tailf:cli-delete-when-empty;
                key "process";
                leaf process {
                  type string {
                    tailf:info
                      "WORD;;User selected string identifying this process";
                  }
                }
                uses isis-redist-af-grouping;
              }
              container static {
                tailf:info
                  "Static routes";
                presence "Static routes";
                uses router-isis-redistribute-grouping;
              }
            }
            list summary-prefix {
              tailf:info
                "Configure IPv6 summary prefix";
              tailf:cli-suppress-mode;
              tailf:cli-delete-when-empty;
              key "prefix";
              leaf prefix {
                type inet:ipv6-prefix {
                  tailf:info
                    "X:X:X:X::X/<0-128>;;IPv6 prefix x:x::y/<z>";
                }
              }
              leaf levels {
                tailf:cli-drop-node-name;
                type enumeration {
                  enum "level-1" {
                    tailf:info
                      "Summarize into level-1 area";
                  }
                  enum "level-1-2" {
                    tailf:info
                      "Summarize into both area and sub-domain";
                  }
                  enum "level-2" {
                    tailf:info
                      "Summarize into level-2 sub-domain";
                  }
                }
              }
            }
          }
        }
      }
      container advertise {
        tailf:info
          "Control which IP routes flow in L1 and L2 LSPs";
        leaf passive-only {
          tailf:info
            "only interface address of passive interfaces";
          type empty;
        }
      }
      container area-password {
        tailf:info
          "Configure the authentication password for an area";
        tailf:cli-compact-syntax;
        tailf:cli-sequence-commands;
        leaf name {
          tailf:cli-drop-node-name;
          type string {
            tailf:info
              "WORD;;Area password";
          }
        }
        uses router-isis-authenticate-snp-grouping;
      }
      container nsf {
        tailf:info
          "Non-stop forwarding";
        leaf cisco {
          tailf:info
            "Checkpoint method";
          type empty;
        }
      }
      container bfd {
        tailf:info
          "BFD configuration commands";
        leaf all-interfaces {
          tailf:info
            "Enable BFD on all interfaces";
          type empty;
        }
      }
      container distance {
        tailf:info
          "Define an administrative distance";
        tailf:cli-compact-syntax;
        container clns-container {
          tailf:cli-drop-node-name;
          tailf:cli-sequence-commands;
          leaf distance {
            tailf:cli-drop-node-name;
            type uint32 {
              tailf:info
                "<1-255>;;OSPF Administrative distance";
              range "1..255";
            }
          }
          leaf clns {
            tailf:info
              "Distance applied for CLNS derived routes";
            tailf:cli-full-command;
            type empty;
          }
        }
        container ip-container {
          tailf:cli-drop-node-name;
          tailf:cli-sequence-commands;
          leaf distance {
            tailf:cli-drop-node-name;
            type uint32 {
              range "1..255";
              tailf:info
                "<1-255>;;OSPF Administrative distance";
            }
          }
          leaf ip {
            tailf:info
              "Distance applied for IP derived routes";
            tailf:cli-full-command;
            type empty;
          }
        }
        container acl-container {
          tailf:cli-drop-node-name;
          tailf:cli-sequence-commands;
          leaf distance {
            tailf:cli-drop-node-name;
            type uint32 {
              tailf:info
                "<1-255>;;OSPF Administrative distance";
              range "1..255";
            }
          }
          list acl {
            tailf:cli-drop-node-name;
            tailf:cli-suppress-mode;
            tailf:cli-delete-when-empty;
            key "ip wildcard";
            leaf ip {
              type inet:ipv4-address {
                tailf:info
                  "A.B.C.D;;IP source address";
              }
            }
            leaf wildcard {
              type inet:ipv4-address {
                tailf:info
                  "A.B.C.D;;Wildcard bits";
              }
            }
            leaf access-list {
              tailf:cli-drop-node-name;
              type std-ip-acl-type;
            }
          }
        }
      }
      container domain-password {
        tailf:info
          "Set the authentication password for a routing domain";
        tailf:cli-sequence-commands;
        tailf:cli-compact-syntax;
        leaf name {
          tailf:cli-drop-node-name;
          type string {
            tailf:info
              "WORD;;Routing domain password";
          }
        }
        uses router-isis-authenticate-snp-grouping;
      }
      container fast-flood {
        tailf:info
          "Flood LSPs (that triggered SPF) before running SPF";
        presence "Flood LSPs (that triggered SPF) before running SPF";
        leaf number {
          tailf:cli-drop-node-name;
          type uint32 {
            range "1..15";
            tailf:info
              "<1-15>;;number of LSPs to be flooded before starting SPF";
          }
        }
      }
      container hello {
        tailf:info
          "Pad ISIS hello PDUs to full MTU";
        container padding {
          tailf:info
            "Pad hello PDU";
          presence "Pad hello PDU";
          leaf pad-type {
            tailf:cli-drop-node-name;
            type enumeration {
              enum "multi-point" {
                tailf:info
                  "Pad LAN hello PDUs";
              }
              enum "point-to-point" {
                tailf:info
                  "Pad point-to-point hello PDUs";
              }
            }
          }
        }
      }
      container hostname {
        tailf:info
          "Dynamic hostname for IS-IS";
        leaf dynamic {
          tailf:info
            "Dynamic hostname";
          type empty;
        }
      }
      leaf ignore-lsp-errors {
        tailf:info
          "Ignore LSPs with bad checksums";
        tailf:cli-full-command;
        type empty;
      }
      container ip {
        tailf:info
          "IP specific commands";
        container route {
          tailf:info
            "ISIS IP routes";
          container priority {
            tailf:info
              "Assign priority to IP prefixes";
            container high {
              tailf:info
                "Assign high priority to important IP prefixes in ISIS IP local RIB";
              leaf tag {
                tailf:info
                  "Assign high priority to IP prefixes with a specific route tag";
                type uint32 {
                  range "1..4294967295";
                  tailf:info
                    "<1-4294967295>;;tag value";
                }
              }
            }
          }
        }
      }
      leaf is-type {
        tailf:info
          "IS Level for this routing process (OSI only)";
        tailf:cli-full-command;
        type enumeration {
          enum "level-1" {
            tailf:info
              "Act as a station router only";
          }
          enum "level-1-2" {
            tailf:info
              "Act as both a station router and an area router";
          }
          enum "level-2-only" {
            tailf:info
              "Act as an area router only";
          }
        }
      }
      container ispf {
        tailf:info
          "Configure execution of incremental SPF";
        tailf:cli-compact-syntax;
        tailf:cli-sequence-commands;
        leaf level {
          tailf:cli-drop-node-name;
          type enumeration {
            enum "level-1" {
              tailf:info
                "Do incremental SPF for level-1";
            }
            enum "level-1-2" {
              tailf:info
                "Do incremental SPF for both levels";
            }
            enum "level-2" {
              tailf:info
                "Do incremental SPF for level-2";
            }
          }
        }
        leaf number {
          tailf:cli-drop-node-name;
          type uint32 {
            range "1..600";
            tailf:info
              "<1-600>;;Number of seconds before activating incremental-spf";
          }
        }
      }
      container log-adjacency-changes {
        tailf:info
          "Log changes in adjacency state";
        presence "true";
        leaf all {
          tailf:info
            "Include changes generated by non-IIH event";
          type empty;
        }
      }
      container lsp-full {
        tailf:info
          "If we run out of LSP fragments";
        container suppress {
          tailf:info
            "suppress the following types of IP prefixes";
          choice lsp-full-choince {
            container external-interlevel-container {
              tailf:cli-drop-node-name;
              tailf:cli-compact-syntax;
              leaf external {
                tailf:info
                  "don't advertise IP prefixes learned from other protocols";
                type empty;
              }
              leaf interlevel {
                tailf:info
                  "don't advertise IP prefixes learned from another ISIS level";
                type empty;
              }
            }
            leaf none {
              tailf:info
                "don't suppress any prefixes";
              type empty;
            }
          }
        }
      }
      container lsp-gen-interval {
        tailf:info
          "Minimum interval between regenerating same LSP";
        choice lsp-gen-interval-choice {
          container intervals {
            tailf:cli-drop-node-name;
            tailf:cli-compact-syntax;
            tailf:cli-sequence-commands;
            uses lsp-gen-interval-grouping;
          }
          container intervals-levels {
            tailf:cli-drop-node-name;
            container intervals-level-1 {
              tailf:cli-drop-node-name;
              tailf:cli-compact-syntax;
              tailf:cli-sequence-commands;
              leaf level-1 {
                tailf:info
                  "Set interval for level 1 only";
                type empty;
              }
              uses lsp-gen-interval-grouping;
            }
            container intervals-level-2 {
              tailf:cli-drop-node-name;
              tailf:cli-compact-syntax;
              tailf:cli-sequence-commands;
              leaf level-2 {
                tailf:info
                  "Set interval for level 2 only";
                type empty;
              }
              uses lsp-gen-interval-grouping;
            }
          }
        }
      }
      leaf lsp-mtu {
        tailf:info
          "Set maximum LSP size";
        tailf:cli-full-command;
        type uint32 {
          range "128..4352";
          tailf:info
            "<128-4352>;;Max LSP size in bytes";
        }
      }
      leaf lsp-refresh-interval {
        tailf:info
          "Set LSP refresh interval";
        tailf:cli-full-command;
        type uint32 {
          range "1..65535";
          tailf:info
            "<1-65535>;;LSP refresh time in seconds";
        }
      }
      leaf max-area-addresses {
        tailf:info
          "Allow configuration of more manual area addresses";
        tailf:cli-full-command;
        type uint32 {
          range "3..254";
          tailf:info
            "<3-254>;;Max number of manual area addresses";
        }
      }
      leaf max-lsp-lifetime {
        tailf:info
          "Set maximum LSP lifetime";
        tailf:cli-full-command;
        type uint32 {
          range "1..65535";
          tailf:info
            "<1-65535>;;Maximum LSP lifetime in seconds";
        }
      }
      container metric-style {
        tailf:info
          "Use old-style (ISO 10589) or new-style packet formats";
        choice metric-style-choice {
          container narrow {
            tailf:info
              "Use old style of TLVs with narrow metric";
            presence "true";
            uses narrow-wide-transition-grouping;
          }
          container transition {
            tailf:info
              "Send and accept both styles of TLVs during transition";
            presence "true";
            leaf level {
              tailf:cli-drop-node-name;
              type isis-level-type;
            }
          }
          container wide {
            tailf:info
              "Use new style of TLVs to carry wider metric";
            presence "true";
            uses narrow-wide-transition-grouping;
          }
        }
      }
      container mpls {
        tailf:info
          "Configure MPLS routing protocol parameters";
        container ldp {
          tailf:info
            "routing protocol commands for MPLS LDP";
          leaf sync {
            tailf:info
              "Configure LDP-IGP Synchronization";
            type empty;
          }
        }
        container traffic-eng {
          tailf:info
            "routing protocol commands for MPLS Traffic Engineering";
          leaf level-1 {
            tailf:info
              "Run MPLS TE on IS-IS level 1 only";
            tailf:cli-full-command;
            type empty;
          }
          leaf level-2 {
            tailf:info
              "Run MPLS TE on IS-IS level 2 only";
            tailf:cli-full-command;
            type empty;
          }
          leaf multicast-intact {
            tailf:info
              "MPLS TE and PIM interaction";
            tailf:cli-full-command;
            type empty;
          }
          container router-id {
            tailf:info
              "Traffic Engineering stable IP address for system";
            uses interface-name-grouping;
          }
          container scanner {
            tailf:info
              "Timer parameters for TE database";
            presence "Timer parameters for TE database";
            tailf:cli-compact-syntax;
            leaf interval {
              tailf:info
                "time (secs) between LSPDB walks for TE";
              type uint32 {
                range "1..60";
                tailf:info
                  "<1-60>;;interval between LSPDB walks for TE TLVs extraction";
              }
            }
            leaf max-flash {
              tailf:info
                "Number of ISIS LSPs to be processed with no delay";
              type uint32 {
                range "0..200";
                tailf:info
                  "<0-200>;;Max. number of LSPs ISIS may send to TE db without delay";
              }
            }
          }
        }
      }
      list net {
        tailf:info
          "A Network Entity Title for this process (OSI only)";
        tailf:cli-suppress-mode;
        tailf:cli-delete-when-empty;
        key "tag";
        leaf tag {
          type string {
            tailf:info
              "XX.XXXX. ... .XXX.XX;;Network entity title (NET)";
          }
        }
      }
      container partition {
        tailf:info
          "CLNS area partition";
        leaf avoidance {
          tailf:info
            "Withdraw area prefix if partition detected";
          type empty;
        }
      }
      uses passive-interface-grouping;
      container protocol {
        tailf:info
          "Set protocol's administrative state";
        leaf shutdown {
          tailf:info
            "Set protocol's administrative state to disable";
          type empty;
        }
      }
      container redistribute {
        tailf:info
          "Redistribute information from another routing protocol";
        container bgp {
          tailf:info
            "Border Gateway Protocol (BGP)";
          tailf:cli-compact-syntax;
          leaf as-number {
            tailf:cli-drop-node-name;
            type uint32 {
              range "1..65535";
              tailf:info
                "<1-65535>;;Autonomous system number";
            }
          }
          uses isis-redist-clns-ip-grouping;
        }
        container connected {
          tailf:info
            "Connected";
          tailf:cli-compact-syntax;
          tailf:cli-delete-when-empty;
          presence "Connected";
          uses router-isis-redistribute-grouping;
        }
        list eigrp {
          tailf:info
            "Enhanced Interior Gateway Routing Protocol (EIGRP)";
          tailf:cli-suppress-mode;
          tailf:cli-delete-when-empty;
          tailf:cli-compact-syntax;
          key "as-number";
          leaf as-number {
            tailf:cli-drop-node-name;
            type uint32 {
              range "1..65535";
              tailf:info
                "<1-65535>;;Autonomous system number";
            }
          }
          uses router-isis-redistribute-grouping;
        }
        container isis {
          tailf:info
            "ISO IS-IS";
          tailf:cli-compact-syntax;
          leaf area-tag {
            tailf:cli-drop-node-name;
            tailf:cli-disallow-value "ip";
            type string {
              tailf:info
                "WORD;;ISO routing area tag";
            }
          }
          container ip {
            tailf:info
              "Redistribution of IP routes between levels";
            tailf:cli-flatten-container;
            tailf:cli-compact-syntax;
            tailf:cli-sequence-commands;
            leaf level {
              tailf:cli-drop-node-name;
              tailf:cli-incomplete-command;
              type enumeration {
                enum "level-1" {
                  tailf:info
                    "Inter-area routes from level-1";
                }
                enum "level-2" {
                  tailf:info
                    "Inter-area routes from level-2";
                }
              }
            }
            leaf into {
              tailf:info
                "from level-n into level-m";
              tailf:cli-incomplete-command;
              type empty;
            }
            leaf level2 {
              tailf:cli-drop-node-name;
              tailf:cli-incomplete-command;
              type enumeration {
                enum "level-1" {
                  tailf:info
                    "Inter-area routes from level-1";
                }
                enum "level-2" {
                  tailf:info
                    "Inter-area routes from level-2";
                }
              }
            }
            choice isis-redist-isis-ip-choice {
              leaf distribute-list {
                tailf:info
                  "select routes";
                type uint32 {
                  tailf:info
                    "<100-199>;;IP extended acces-list number";
                  range "100..199";
                }
              }
              leaf route-map {
                tailf:info
                  "Route map for route matching";
                type string {
                  tailf:info
                    "WORD;;Name of the route-map";
                }
              }
            }
          }
        }
        container iso-igrp {
          tailf:info
            "IGRP for OSI networks";
          presence "IGRP for OSI networks";
          tailf:cli-compact-syntax;
          tailf:cli-sequence-commands;
          choice iso-igrp-choice {
            container area-tag-route-map-container {
              tailf:cli-drop-node-name;
              tailf:cli-flatten-container;
              tailf:cli-compact-syntax;
              tailf:cli-sequence-commands;
              leaf area-tag {
                tailf:cli-drop-node-name;
                tailf:cli-disallow-value "route-map";
                type string {
                  tailf:info
                    "WORD;;ISO routing area tag";
                }
              }
              leaf route-map {
                tailf:info
                  "Route map reference";
                type string {
                  tailf:info
                    "WORD;;Pointer to route-map entries";
                }
              }
            }
            leaf route-map {
              tailf:info
                "Route map reference";
              type string {
                tailf:info
                  "WORD;;Pointer to route-map entries";
              }
            }
          }
          uses redist-level-grouping;
          leaf metric {
            tailf:info
              "ISIS default metric";
            type uint32 {
              tailf:info
                "<0-4294967295>;;ISIS default metric";
              range "0..4294967295";
            }
          }
          leaf metric-type {
            tailf:info
              "OSPF/IS-IS exterior metric type for redistributed routes";
            type enumeration {
              enum "external" {
                tailf:info
                  "Set IS-IS External metric type";
              }
              enum "internal" {
                tailf:info
                  "Set IS-IS Internal metric type";
              }
            }
          }
        }
        container maximum-prefix {
          tailf:info
            "Maximum number of prefixes redistributed to protocol";
          tailf:cli-compact-syntax;
          tailf:cli-sequence-commands;
          leaf number {
            tailf:cli-drop-node-name;
            type uint32 {
              range "1..4294967295";
              tailf:info
                "<1-4294967295>;;Maximum number of IP prefixes redistributed";
            }
          }
          leaf threshold-value {
            tailf:cli-drop-node-name;
            tailf:cli-break-sequence-commands;
            type uint32 {
              tailf:info
                "<1-100>;;Threshold value (%) at which to generate a warning message";
              range "1..100";
            }
          }
          leaf warning-only {
            tailf:info
              "Only give warning message when limit is exceeded";
            tailf:cli-full-command;
            type empty;
          }
          leaf withdraw {
            tailf:info
              "Withdraw redistibuted prefixes";
            tailf:cli-full-command;
            type empty;
          }
        }
        container mobile {
          tailf:info
            "Mobile routes";
          tailf:cli-compact-syntax;
          presence "Mobile routes";
          uses router-isis-redistribute-grouping;
        }
        container odr {
          tailf:info
            "On Demand stub Routes";
          tailf:cli-compact-syntax;
          presence "On Demand stub Routes";
          uses router-isis-redistribute-grouping;
        }
        list ospf {
          tailf:info
            "Open Shortest Path First (OSPF)";
          tailf:cli-suppress-mode;
          tailf:cli-delete-when-empty;
          tailf:cli-compact-syntax;
          key "process-id";
          leaf process-id {
            tailf:cli-suppress-range;
            type uint32 {
              tailf:info
                "<1-65535>;;Process ID";
              range "1..65535";
            }
          }
          uses router-isis-redistribute-grouping;
          container match {
            tailf:info
              "Redistribution of OSPF routes";
            tailf:cli-flatten-container;
            tailf:cli-compact-syntax;
            uses redistribute-ospf-match-grouping;
            uses isis-redist-ospf-match-grouping;
          }
        }
        container rip {
          tailf:info
            "Routing Information Protocol (RIP)";
          tailf:cli-compact-syntax;
          presence "Routing Information Protocol (RIP)";
          uses router-isis-redistribute-grouping;
        }
        container static {
          tailf:info
            "Static routes";
          tailf:cli-compact-syntax;
          tailf:cli-delete-when-empty;
          presence "Static routes";
          uses isis-redist-clns-ip-grouping;
        }
      }
      container set-attached-bit {
        tailf:info
          "Conditionally advertise us as attached to L2";
        leaf route-map {
          tailf:info
            "Route-map reference";
          type string {
            tailf:info
              "WORD;;Route map name";
          }
        }
      }
      list summary-address {
        tailf:info
          "Configure IP address summaries";
        tailf:cli-suppress-mode;
        tailf:cli-delete-when-empty;
        key "ip mask";
        leaf ip {
          type inet:ipv4-address {
            tailf:info
              "A.B.C.D;;IP summary address";
          }
        }
        leaf mask {
          type inet:ipv4-address {
            tailf:info
              "A.B.C.D;;Summary mask";
          }
        }
        container level-1 {
          tailf:info
            "Summarize into level-1 area";
          presence "Summarize into level-1 area";
          tailf:cli-compact-syntax;
          uses summary-address-metric-tag-grouping;
        }
        container level-1-2 {
          tailf:info
            "Summarize into both area and sub-domain";
          presence "Summarize into both area and sub-domain";
          tailf:cli-compact-syntax;
          uses summary-address-metric-tag-grouping;
        }
        container level-2 {
          tailf:info
            "Summarize into level-2 sub-domain";
          presence "Summarize into level-2 sub-domain";
          tailf:cli-compact-syntax;
          uses summary-address-metric-tag-grouping;
        }
        container metric-tag-container {
          tailf:cli-drop-node-name;
          tailf:cli-compact-syntax;
          uses summary-address-metric-tag-grouping;
        }
      }
      leaf update-queue-depth {
        tailf:info
          "Set Update process queue depth";
        type uint32 {
          tailf:info
            "<1-2147483647>;;Max queue depth";
          range "1..2147483647";
        }
      }
      container use {
        tailf:info
          "Use different algorithms during SPF";
        leaf external-metrics {
          tailf:info
            "Honour external metrics during SPF";
          type empty;
        }
      }
    }
  }

  grouping interface-switch-grouping {
    container switchport {
      tailf:info
        "Set switching mode characteristics";
      tailf:cli-display-separated;
      tailf:callpoint interface-switchport-hook {
        tailf:set-hook node;
      }
      tailf:cli-diff-dependency "../ip/route-cache-conf/route-cache" {
        tailf:xpath-root 3;
        tailf:cli-trigger-on-set;
      }
      presence "true";
      container access {
        tailf:info
          "Set access mode characteristics of the interface";
        leaf vlan {
          tailf:info
            "Set VLAN when interface is in access mode";
          tailf:cli-diff-dependency "/ios:vlan/vlan-list/id" {
            tailf:xpath-root 3;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
        }
      }
      container trunk {
        tailf:info
          "Set trunking characteristics of the interface";
        leaf encapsulation {
          tailf:info
            "Set encapsulation format on trunk port";
          type enumeration {
            enum "dot1q" {
              tailf:info
                "Interface uses only 802.1q trunking encapsulation when trunking";
            }
            enum "isl" {
              tailf:info
                "Interface uses only ISL trunking encapsulation when trunking";
            }
            enum "negotiate" {
              tailf:info
                "Device will negotiate trunking encapsulation with peer on interface";
            }
          }
          default "negotiate";
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container allowed {
          tailf:info
            "Set allowed VLAN characteristics when interface is in trunking mode";
          container vlan {
            tailf:info
              "Set allowed VLANs when interface is in trunking mode";
            choice vlan-choice {
              leaf-list vlans {
                tailf:cli-replace-all;
                tailf:cli-range-list-syntax;
                tailf:cli-drop-node-name;
                type uint16 {
                  tailf:info
                    "WORD;;VLAN IDs of the allowed VLANs when this port is in trunking mode";
                }
              }
              leaf all {
                tailf:info
                  "all VLANs";
                type empty;
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-range-list-syntax;
                tailf:cli-drop-node-name;
                type uint16 {
                  tailf:info
                    "WORD;;VLAN IDs of the allowed VLANs when this port is in trunking mode";
                }
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
      }
      container autostate {
        tailf:info
          "Include or exclude this port from vlan link up calculation";
        tailf:cli-incomplete-command;
        leaf exclude {
          tailf:info
            "Exclude this port from vlan link up calculation";
          type empty;
        }
      }
      container private-vlan {
        tailf:info
          "Set the private VLAN configuration";
        container trunk {
          tailf:info
            "Set the private vlan trunking configuration";
          container native {
            tailf:info
              "Set the private vlan trunking native configuration";
            leaf vlan {
              tailf:info
                "Set native VLAN configuration";
              type union {
                type enumeration {
                  enum "tag" {
                    tailf:info
                      "Set native VLAN tagging state";
                  }
                }
                type uint16 {
                  tailf:info
                    "<1-4094>;;VLAN ID of the native VLAN when this port is in trunking mode";
                  range "1..4094";
                }
              }
            }
          }
          container allowed {
            tailf:info
              "Set allowed VLAN characteristics when interface is in private-vlan trunking mode";
            container vlan {
              tailf:info
                "Set allowed VLANs when interface is in private-vlan trunking mode";
              choice vlan-choice {
                leaf-list vlans {
                  tailf:cli-replace-all;
                  tailf:cli-range-list-syntax;
                  tailf:cli-drop-node-name;
                  type uint16 {
                    tailf:info
                      "WORD;;VLAN IDs of the allowed VLANs when interface is in private-vlan trunking mode";
                  }
                }
                leaf all {
                  tailf:info
                    "all VLANs";
                  type empty;
                }
                leaf-list except {
                  tailf:info
                    "all VLANs except the following";
                  tailf:cli-range-list-syntax;
                  type uint16 {
                    tailf:info
                      "WORD;;VLAN IDs of disallowed VLANS when this port is in trunking mode ";
                  }
                }
                leaf none {
                  tailf:info
                    "no VLANs";
                  type empty;
                }
              }
            }
          }
        }
        container association {
          tailf:info
            "Set the private VLAN association";
          list trunk {
            tailf:cli-suppress-mode;
            tailf:cli-delete-when-empty;
            tailf:cli-incomplete-command;
            key "primary-vlan-id";
            leaf primary-vlan-id {
              type uint16 {
                tailf:info
                  "<2-4094>;;Primary VLAN ID of the private VLAN trunk association";
                range "2..4094";
              }
            }
            leaf secondary-vlan-id {
              tailf:cli-drop-node-name;
              type uint16 {
                tailf:info
                  "<2-4094>;;Secondary VLAN ID of the private VLAN port/trunk association";
                range "2..4094";
              }
            }
          }
        }
      }
      container mode {
        tailf:info
          "Set trunking mode of the interface";
        choice mode-choice {
          container access {
            tailf:info
              "Set trunking mode to ACCESS unconditionally";
            presence "true";
          }
          container dot1q-tunnel {
            tailf:info
              "set trunking mode to TUNNEL unconditionally";
            presence "true";
          }
          leaf dynamic {
            tailf:info
              "Set trunking mode to dynamically negotiate access or trunk mode";
            type enumeration {
              enum "auto" {
                tailf:info
                  "Set trunking mode dynamic negotiation parameter to AUTO";
              }
              enum "desirable" {
                tailf:info
                  "Set trunking mode dynamic negotiation parameter to DESIRABLE";
              }
            }
          }
          container trunk {
            tailf:info
              "Set trunking mode to TRUNK unconditionally";
            tailf:cli-diff-dependency "../../trunk" {
              tailf:xpath-root 3;
            }
            presence "true";
          }
          container private-vlan {
            tailf:info
              "Set private-vlan mode";
            choice private-vlan-choice {
              leaf host {
                tailf:info
                  "Set the mode to private-vlan host";
                type empty;
              }
              leaf promiscuous {
                tailf:info
                  "Set the mode to private-vlan promiscuous";
                type empty;
              }
              container trunk {
                tailf:info
                  "Set the mode to private-vlan trunk";
                presence "true";
              }
            }
          }
        }
      }
      leaf nonegotiate {
        tailf:info
          "Device will not engage in negotiation protocol on this interface";
        tailf:cli-diff-dependency "../trunk" {
          tailf:xpath-root 3;
        }
        type empty;
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      container port-security {
        tailf:info
          "Security related command";
        tailf:cli-display-separated;
        tailf:cli-diff-dependency "../trunk" {
          tailf:xpath-root 3;
        }
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-compact-syntax;
          tailf:cli-sequence-commands {
            tailf:cli-reset-siblings;
          }
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        container maximum {
          tailf:info
            "Max secure addresses";
          tailf:cli-compact-syntax;
          tailf:cli-sequence-commands {
            tailf:cli-reset-siblings;
          }
          leaf max-addresses {
            tailf:cli-drop-node-name;
            type uint16 {
              tailf:info
                "<1-4097>;;Maximum addresses";
              range "1..4097";
            }
          }
          leaf vlan {
            tailf:info
              "Max secure addresses per vlan";
            type string {
              tailf:info
                "WORD;;VLAN IDs to which this maximum applies";
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      leaf protected {
        tailf:info
          "Configure an interface to be a protected port";
        type empty;
      }
      leaf host {
        tailf:info
          "Set port host";
        type empty;
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container mst {
        tailf:info
          "Multiple spanning tree";
        choice mst-choice {
          list instance-range {
            tailf:cli-suppress-mode;
            tailf:cli-delete-when-empty;
            tailf:cli-drop-node-name;
            tailf:cli-compact-syntax;
            tailf:cli-range-list-syntax;
            key "id";
            leaf id {
              type uint16 {
                tailf:info
                  "MST instance list, example 0,2-4,6,8-12";
              }
            }
            leaf cost {
              tailf:info
                "Change the interface spanning tree path cost for an instance";
              type uint32 {
                tailf:info
                  "<1-200000000>;;Change the interface spanning tree path cost for an instance";
                range "1..200000000";
              }
            }
            leaf port-priority {
              tailf:info
                "Change the spanning tree port priority for an instance";
              type uint16 {
                tailf:info
                  "<0-240>;;port priority in increments of 16";
                range "0..240" {
                  tailf:step "16";
                }
              }
            }
          }
          leaf pre-standard {
            tailf:info
              "Force pre-standard MST BPDU transmission on port";
            type empty;
          }
        }
      }
      container portfast {
        tailf:info
          "Spanning tree portfast options";
        tailf:cli-delete-when-empty;
        presence "true";
        leaf enable {
          tailf:cli-full-command;
          tailf:cli-drop-node-name;
          type enumeration {
            enum "disable" {
              tailf:info
                "Disable portfast for this interface";
            }
          }
        }
        leaf trunk {
          type empty;
        }
      }
      container loopguard {
        tailf:info
          "Spanning tree loopguard options";
        leaf default {
          tailf:info
            "Enable loopguard by default on all ports";
          type empty;
        }
      }
    }
    container srr-queue {
      container bandwidth {
        container shape {
          tailf:cli-compact-syntax;
          tailf:cli-sequence-commands;
          tailf:cli-reset-container;
          leaf weight1 {
            tailf:cli-drop-node-name;
            tailf:cli-incomplete-command;
            type uint16;
          }
          leaf weight2 {
            tailf:cli-drop-node-name;
            tailf:cli-incomplete-command;
            type uint16;
          }
          leaf weight3 {
            tailf:cli-drop-node-name;
            tailf:cli-incomplete-command;
            type uint16;
          }
          leaf weight4 {
            tailf:cli-drop-node-name;
            type uint16;
          }
        }
        container share {
          tailf:cli-compact-syntax;
          tailf:cli-sequence-commands;
          tailf:cli-reset-container;
          leaf weight1 {
            tailf:cli-drop-node-name;
            tailf:cli-incomplete-command;
            type uint8 {
              range "1..255";
            }
          }
          leaf weight2 {
            tailf:cli-drop-node-name;
            tailf:cli-incomplete-command;
            type uint8 {
              range "1..255";
            }
          }
          leaf weight3 {
            tailf:cli-drop-node-name;
            tailf:cli-incomplete-command;
            type uint8 {
              range "1..255";
            }
          }
          leaf weight4 {
            tailf:cli-drop-node-name;
            type uint8 {
              range "1..255";
            }
          }
        }
      }
    }
    leaf queue-set {
      type uint8;
    }
  }

  grouping password-07-grouping {
    leaf type {
      tailf:cli-drop-node-name;
      tailf:cli-optional-in-sequence;
      type enumeration {
        enum "0" {
          tailf:info
            "Specifies an UNENCRYPTED password/key will follow";
        }
        enum "7" {
          tailf:info
            "Specifies a HIDDEN password/key will follow";
        }
      }
    }
    leaf secret {
      tailf:cli-drop-node-name;
      type string {
        tailf:info
          "LINE;;The UNENCRYPTED (cleartext) password/key";
      }
    }
  }

  grouping router-lisp-af4-common-grouping {
    leaf map-request-source {
      tailf:info
        "Configures inner header source address in Map-Requestmessage";
      type inet:ipv4-address {
        tailf:info
          "A.B.C.D;;IPv4 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv4-local-locator {
        tailf:cli-drop-node-name;
        tailf:cli-optional-in-sequence;
        type inet:ipv4-address {
          tailf:info
            "A.B.C.D;;IPv4 address in ITR-RLOC field of map-request";
        }
      }
      leaf ipv6-local-locator {
        tailf:cli-drop-node-name;
        type inet:ipv6-address {
          tailf:info
            "X:X:X:X::X;;IPv6 address in ITR-RLOC field of map-request";
        }
      }
    }
  }

  grouping router-lisp-af6-common-grouping {
    leaf map-request-source {
      tailf:info
        "Configures inner header source address in Map-Request message";
      type inet:ipv6-address {
        tailf:info
          "X:X:X:X::X;;IPv6 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv6-local-locator {
        tailf:cli-drop-node-name;
        tailf:cli-optional-in-sequence;
        type inet:ipv6-address {
          tailf:info
            "X:X:X:X::X;;IPv6 address in ITR-RLOC field of map-request";
        }
      }
      leaf ipv4-local-locator {
        tailf:cli-drop-node-name;
        type inet:ipv4-address {
          tailf:info
            "A.B.C.D;;IPv4 address in ITR-RLOC field of map-request";
        }
      }
    }
  }

  grouping router-lisp-af-common-grouping {
    leaf map-cache-limit {
      tailf:info
        "Configures maximum size of map-cache";
      type uint32 {
        tailf:info
          "<0-100000>;;Maximum number of map-cache entries";
        range "0..100000";
      }
    }
    container map-cache-persistent {
      tailf:info
        "Dump map-cache onto flash, making it persistent across reboots";
      tailf:cli-show-no;
      presence "true";
      leaf interval {
        tailf:info
          "Interval in minutes of how often the map-cache is saved";
        type uint16 {
          tailf:info
            "<1-1440>;;Interval in minutes, default 60";
          range "1..1440";
        }
      }
    }
    leaf proxy-etr {
      tailf:info
        "Configures a LISP Proxy Engress Tunnel Router (PETR)";
      tailf:cli-full-command;
      type empty;
    }
    list use-petr {
      tailf:info
        "Encapsulate to Proxy ETR when matching forward-native entry";
      tailf:cli-suppress-mode;
      tailf:cli-delete-when-empty;
      tailf:cli-compact-syntax;
      tailf:cli-sequence-commands;
      key "address";
      leaf address {
        type union {
          type inet:ipv4-address {
            tailf:info
              "A.B.C.D;;IPv4 locator address of PETR";
          }
          type inet:ipv6-address {
            tailf:info
              "X:X:X:X::X;;IPv6 locator address of PETR";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
          range "0..100";
        }
      }
    }
  }

  grouping router-lisp-af-grouping {
    leaf map-server {
      tailf:info
        "Configures a LISP Map Server (MS)";
      type empty;
    }
    leaf map-resolver {
      tailf:info
        "Configures a LISP Map Resolver (MR)";
      type empty;
    }
    container itr {
      tailf:info
        "Configures a LISP Ingress Tunnel Router (ITR)";
      tailf:cli-display-separated;
      presence "true";
      list map-resolver {
        tailf:cli-suppress-mode;
        tailf:cli-delete-when-empty;
        key "address";
        leaf address {
          type union {
            type inet:ipv4-address {
              tailf:info
                "IPv4 Address of map resolver";
            }
            type inet:ipv6-address {
              tailf:info
                "IPv6 Address of map resolver";
            }
          }
        }
      }
    }
    container etr {
      tailf:info
        "Configures a LISP Egress Tunnel Router (ETR)";
      tailf:cli-display-separated;
      presence "true";
      list map-server {
        tailf:cli-suppress-mode;
        tailf:cli-delete-when-empty;
        tailf:cli-incomplete-command;
        key "address";
        leaf address {
          type union {
            type inet:ipv4-address {
              tailf:info
                "IPv4 Address of map server";
            }
            type inet:ipv6-address {
              tailf:info
                "IPv6 Address of map server";
            }
          }
        }
        container key {
          tailf:info
            "Authentication key used with map server";
          tailf:cli-compact-syntax;
          tailf:cli-sequence-commands {
            tailf:cli-reset-siblings;
          }
          leaf encryption {
            tailf:cli-drop-node-name;
            tailf:cli-incomplete-command;
            tailf:cli-optional-in-sequence;
            type enumeration {
              enum "0" {
                tailf:info
                  "Specifies an UNENCRYPTED password will follow";
              }
              enum "6" {
                tailf:info
                  "Specifies an ENCRYPTED password will follow";
              }
            }
          }
          leaf key {
            tailf:cli-drop-node-name;
            tailf:cli-multi-value;
            type string {
              tailf:info
                "LINE;;The UNENCRYPTED (cleartext) password";
            }
          }
        }
      }
    }
  }

  grouping router-lisp-eid-table-grouping {
    leaf instance-id {
      tailf:info
        "EID instance-ID";
      tailf:cli-hide-in-submode;
      mandatory true;
      type uint32 {
        tailf:info
          "<0-16777214>;;Instance-ID";
        range "0..16777214";
      }
    }
    list map-cache {
      tailf:cli-suppress-mode;
      tailf:cli-delete-when-empty;
      tailf:cli-compact-syntax;
      tailf:cli-sequence-commands;
      tailf:cli-incomplete-command;
      key "prefix";
      leaf prefix {
        type union {
          type ios:ipv4-prefix {
            tailf:info
              "A.B.C.D/nn;;IPv4 EID-prefix for RLOC static mapping";
          }
          type ios:ipv6-prefix {
            tailf:info
              "X:X:X:X::X/<0-128>;;IPv6 EID-prefix for RLOC static mapping";
          }
        }
      }
      choice map-cache-choice {
        case locator {
          leaf locator {
            tailf:cli-drop-node-name;
            tailf:cli-incomplete-command;
            type union {
              type inet:ipv4-address {
                tailf:info
                  "A.B.C.D;;IPv4 Address of loopback or other ETR interface";
              }
              type inet:ipv6-address {
                tailf:info
                  "X:X:X:X::X;;IPv6 Address of loopback or other ETR interface";
              }
            }
          }
          leaf priority {
            tailf:info
              "Lower priority Locator takes preference";
            tailf:cli-incomplete-command;
            type uint8 {
              tailf:info
                "<0-255>;;Lower priority Locator takes preference";
            }
          }
          leaf weight {
            tailf:info
              "Traffic load-spreading among Locators";
            type uint8 {
              tailf:info
                "<0-100>;;Relative weight of locator";
              range "0..100";
            }
          }
        }
        leaf map-request {
          tailf:info
            "Send Map-Request for LISP destination EID";
          tailf:cli-full-command;
          type empty;
        }
        leaf native-forward {
          tailf:info
            "Natively forward packets that match this map-cache entry";
          tailf:cli-full-command;
          type empty;
        }
        leaf drop {
          tailf:info
            "Drop packets that match this map-cache entry";
          tailf:cli-full-command;
          type empty;
        }
      }
    }
    list database-mapping {
      tailf:info
        "Configures Locator addresses for an ETR";
      tailf:cli-incomplete-command;
      tailf:cli-suppress-mode;
      tailf:cli-delete-when-empty;
      tailf:cli-compact-syntax;
      tailf:cli-sequence-commands;
      key "prefix";
      max-elements 100;
      leaf prefix {
        type union {
          type ios:ipv4-prefix {
            tailf:info
              "A.B.C.D/nn;;EID-prefix to advertise locators for (max 100 prefixes)";
          }
          type ios:ipv6-prefix {
            tailf:info
              "X:X:X:X::X/<0-128>;;EID-prefix to advertise locators for (max 100 prefixes)";
          }
        }
      }
      choice rloc-choice {
        leaf ipv4-address {
          tailf:cli-drop-node-name;
          tailf:cli-incomplete-command;
          type inet:ipv4-address {
            tailf:info
              "A.B.C.D;;IPv4 Address of loopback or other ETR interface";
          }
        }
        container IPv4-interface {
          tailf:info
            "Use IPv4 address of interface as locator";
          tailf:cli-flatten-container;
          tailf:cli-compact-syntax;
          tailf:cli-incomplete-command;
          uses interface-name-grouping;
        }
        container IPv6-interface {
          tailf:info
            "Use IPv6 address of interface as locator";
          tailf:cli-flatten-container;
          tailf:cli-compact-syntax;
          tailf:cli-incomplete-command;
          uses interface-name-grouping;
        }
        leaf ipv6-address {
          tailf:cli-drop-node-name;
          tailf:cli-incomplete-command;
          type inet:ipv6-address {
            tailf:info
              "X:X:X:X::X;;IPv6 Address of loopback or other ETR interface";
          }
        }
        leaf auto-discover-rlocs {
          tailf:info
            "Auto discover locators registered by other xTRs";
          tailf:cli-full-command;
          type empty;
        }
        leaf locator-set {
          tailf:info
            "Use locators defined by locator-set";
          tailf:cli-full-command;
          type string;
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
        }
      }
    }
    container loc-reach-algorithm {
      tailf:info
        "Configure locator reachability algorithm";
      leaf lsb-reports {
        tailf:info
          "Configure data packet LSB report handling";
        type enumeration {
          enum "ignore" {
            tailf:info
              "Ignore data packet LSB reports";
          }
        }
      }
      leaf rloc-probing {
        tailf:info
          "Probe high priority RLOCs with Map-Requests as last resort";
        type empty;
      }
    }
    container ipv4 {
      tailf:info
        "IPv4 address family";
      uses router-lisp-af-common-grouping;
      uses router-lisp-af4-common-grouping;
    }
    container ipv6 {
      tailf:info
        "IPv6 address family";
      uses router-lisp-af-common-grouping;
      uses router-lisp-af6-common-grouping;
    }
  }

  grouping router-lisp-grouping {
    list locator-set {
      tailf:info
        "Configure a named locator set";
      tailf:cli-mode-name "config-router-lisp-locator-set";
      tailf:cli-full-command;
      key "name";
      leaf name {
        type string {
          tailf:info
            "Configure a named locator set";
        }
      }
      list IPv4-address {
        tailf:cli-drop-node-name;
        tailf:cli-suppress-mode;
        tailf:cli-delete-when-empty;
        tailf:cli-compact-syntax;
        tailf:cli-sequence-commands;
        tailf:cli-incomplete-command;
        key "name";
        leaf name {
          type inet:ipv4-address {
            tailf:info
              "A.B.C.D;;IP address";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-address {
        tailf:cli-drop-node-name;
        tailf:cli-suppress-mode;
        tailf:cli-delete-when-empty;
        tailf:cli-compact-syntax;
        tailf:cli-sequence-commands;
        tailf:cli-incomplete-command;
        key "name";
        leaf name {
          type inet:ipv6-address {
            tailf:info
              "X:X:X:X::X;;Address of loopback or other ETR interface";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv4-interface {
        tailf:info
          "Use IPv4 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-interface {
        tailf:info
          "Use IPv6 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
    }
    container map-request {
      tailf:info
        "Configure map-request handling";
      leaf itr-rlocs {
        tailf:info
          "Configure to use the specified RLOC set as ITR RLOC in map-request";
        type string {
          tailf:info
            "WORD;;Existing locator set";
        }
        tailf:non-strict-leafref {
          path "../../locator-set/name";
        }
      }
    }
    container eid-table {
      tailf:info
        "Configure an EID instance for a VRF";
      list default-vrf {
        tailf:cli-drop-node-name;
        tailf:cli-mode-name "config-router-lisp-eid-table";
        key "name";
        leaf name {
          type enumeration {
            enum "default" {
              tailf:info
                "Default VRF";
            }
          }
        }
        uses router-lisp-eid-table-grouping;
      }
      list vrf {
        tailf:cli-mode-name "config-router-lisp-eid-table";
        key "name";
        leaf name {
          type string {
            tailf:info
              "WORD;;VRF name";
          }
        }
        uses router-lisp-eid-table-grouping;
      }
    }
    list site {
      tailf:info
        "Configure a LISP site on a map server (MS)";
      tailf:cli-mode-name "config-router-lisp-site";
      tailf:cli-full-command;
      key "name";
      leaf name {
        type string {
          tailf:info
            "WORD;;The site name";
        }
      }
      leaf description {
        tailf:info
          "Provide a description string for the LISP site";
        tailf:cli-multi-value;
        type string {
          tailf:info
            "LINE;;Site description";
        }
      }
      container authentication-key {
        tailf:info
          "Authentication key used by LISP site";
        tailf:cli-compact-syntax;
        tailf:cli-sequence-commands {
          tailf:cli-reset-siblings;
        }
        leaf encryption {
          tailf:cli-drop-node-name;
          tailf:cli-incomplete-command;
          tailf:cli-optional-in-sequence;
          type enumeration {
            enum "0" {
              tailf:info
                "Specifies an UNENCRYPTED password will follow";
            }
            enum "6" {
              tailf:info
                "Specifies an ENCRYPTED password will follow";
            }
          }
        }
        leaf key {
          tailf:cli-drop-node-name;
          tailf:cli-multi-value;
          type string {
            tailf:info
              "LINE;;The UNENCRYPTED (cleartext) password";
          }
        }
      }
      list eid-prefix {
        tailf:info
          "Site EID address prefix";
        tailf:cli-suppress-mode;
        tailf:cli-delete-when-empty;
        tailf:cli-compact-syntax;
        key "prefix";
        leaf prefix {
          type union {
            type ios:ipv4-prefix {
              tailf:info
                "A.B.C.D/nn;;IPv4 EID prefix belonging to the SITE";
            }
            type ios:ipv6-prefix {
              tailf:info
                "X:X:X:X::X/<0-128>;;IPv6 EID prefix belonging to the SITE";
            }
          }
        }
      }
      container eid-prefix-instance {
        tailf:cli-drop-node-name;
        list eid-prefix {
          tailf:cli-suppress-mode;
          tailf:cli-delete-when-empty;
          tailf:cli-compact-syntax;
          key "instance-id prefix";
          leaf instance-id {
            tailf:info
              "EID instance-ID";
            tailf:cli-expose-key-name;
            type uint32 {
              tailf:info
                "<1-16777214>;;Instance-ID";
              range "1..16777214";
            }
          }
          leaf prefix {
            type union {
              type ios:ipv4-prefix {
                tailf:info
                  "A.B.C.D/nn;;IPv4 EID prefix belonging to the SITE";
              }
              type ios:ipv6-prefix {
                tailf:info
                  "X:X:X:X::X/<0-128>;;IPv6 EID prefix belonging to the SITE";
              }
            }
          }
        }
      }
    }
    container ipv4 {
      tailf:info
        "IPv4 address family";
      uses router-lisp-af-grouping;
      uses router-lisp-af-common-grouping;
      uses router-lisp-af4-common-grouping;
    }
    container ipv6 {
      tailf:info
        "IPv6 address family";
      uses router-lisp-af-grouping;
      uses router-lisp-af-common-grouping;
      uses router-lisp-af6-common-grouping;
    }
  }

  grouping ip-nat-inside-souce-static-grouping {
    leaf extendable {
      tailf:info
        "Extend this translation when used";
      tailf:cli-optional-in-sequence;
      type empty;
    }
    leaf no-alias {
      tailf:info
        "Do not create an alias for the global address";
      tailf:cli-optional-in-sequence;
      type empty;
    }
    leaf no-payload {
      tailf:info
        "No translation of embedded address/port in the payload";
      tailf:cli-optional-in-sequence;
      type empty;
    }
    leaf route-map {
      tailf:info
        "Specify route-map";
      tailf:cli-optional-in-sequence;
      type string {
        tailf:info
          "WORD;;Route-map name";
      }
    }
    leaf reversible {
      when '../route-map' {
        tailf:xpath-root 3;
      }
      tailf:cli-optional-in-sequence;
      type empty;
    }
    leaf redundancy {
      tailf:info
        "NAT redundancy operation";
      tailf:cli-optional-in-sequence;
      type union {
        type uint8 {
          tailf:info
            "<1-2>;IP redundancy ID";
        }
        type string {
          tailf:info
            "WORD;;IP redundancy name";
        }
      }
    }
    leaf mapping-id {
      when '../redundancy' {
        tailf:xpath-root 3;
      }
      tailf:info
        "Associate a mapping id to this mapping";
      tailf:cli-optional-in-sequence;
      type uint32 {
        tailf:info
          "<1-2147483647>;;Stateful NAT mapping id";
        range "1..2147483647";
      }
    }
    leaf vrf {
      tailf:info
        "Specify vrf";
      tailf:cli-optional-in-sequence;
      tailf:cli-diff-dependency "/ios:ip/vrf" {
        tailf:xpath-root 3;
      }
      tailf:cli-diff-dependency "/ios:vrf/definition" {
        tailf:xpath-root 3;
      }
      type string {
        tailf:info
          "WORD;;vrf name";
      }
    }
    leaf match-in-vrf {
      when '../vrf' {
        tailf:xpath-root 3;
      }
      tailf:info
        "Match incoming vrf";
      tailf:cli-optional-in-sequence;
      type empty;
    }
    leaf forced {
      tailf:info
        "Delete this entry and its children, even if in use";
      tailf:cli-optional-in-sequence;
      type empty;
    }
    leaf overload {
      tailf:info
        "Overload an address translation";
      type empty;
    }
  }

  grouping ip-nat-inside-grouping {
    choice pool-or-interface {
      case pool-choice {
        leaf pool {
          tailf:info
            "Name pool of global addresses";
          type string;
          tailf:non-strict-leafref {
            path "/ncs:devices/ncs:device/ncs:config/ios:ip/nat/pool/id" {
              tailf:xpath-root 3;
            }
          }
        }
        leaf redundancy {
          tailf:info
            "NAT redundancy operation";
          tailf:cli-optional-in-sequence;
          type uint8 {
            tailf:info
              "<1-2>;;IP redundancy ID";
            range "1..2";
          }
        }
        leaf mapping-id {
          tailf:info
            "Associate a mapping id to this mapping";
          tailf:cli-optional-in-sequence;
          type uint32 {
            tailf:info
              "<1-2147483647>;;Stateful NAT mapping id";
            range "1..2147483647";
          }
        }
      }
      case interface-choice {
        container interface {
          tailf:info
            "Specify interface for global address";
          tailf:cli-flatten-container;
          tailf:cli-compact-syntax;
          uses interface-name-grouping;
        }
      }
    }
    leaf no-payload {
      tailf:info
        "No translation of embedded address/port in the payload";
      tailf:cli-optional-in-sequence;
      type empty;
    }
    leaf reversible {
      tailf:cli-optional-in-sequence;
      type empty;
    }
    leaf vrf {
      tailf:info
        "Specify vrf";
      tailf:cli-optional-in-sequence;
      tailf:cli-diff-dependency "/ios:ip/vrf" {
        tailf:xpath-root 3;
      }
      tailf:cli-diff-dependency "/ios:vrf/definition" {
        tailf:xpath-root 3;
      }
      type string {
        tailf:info
          "WORD;;vrf name";
      }
    }
    leaf match-in-vrf {
      when '../vrf' {
        tailf:xpath-root 3;
      }
      tailf:info
        "Match incoming vrf";
      tailf:cli-optional-in-sequence;
      type empty;
    }
    leaf overload {
      tailf:info
        "Overload an address translation";
      tailf:cli-optional-in-sequence;
      type empty;
    }
    leaf oer {
      tailf:info
        "Use with vtemplate only. On new translation, if OER BR is UP, OER will select IP from outgoing Interface. All packets matching translation are forwarded over Interface for duration of translation.";
      type empty;
    }
  }

  grouping mobile-ip-spi-grouping {
    choice spi-type-choice {
      leaf hex {
        tailf:cli-drop-node-name;
        type string {
          tailf:info
            "<100-FFFFFFFF>;;SPI hex value";
        }
      }
      leaf decimal {
        tailf:info
          "decimal Security parameter index - bidirectional";
        type uint32 {
          tailf:info
            "<256-4294967295>;;SPI decimal value";
          range "256..4294967295";
        }
      }
    }
  }

  grouping interface-xconnect-grouping {
    choice xconnect-choice {
      container xconnect {
        tailf:cli-break-sequence-commands;
        tailf:cli-add-mode;
        tailf:cli-mode-name "config-xconn";
        tailf:cli-compact-syntax;
        tailf:cli-sequence-commands;
        tailf:cli-incomplete-command;
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure L2TP session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          type string {
            tailf:info
              "WORD;;Pseudowire-class name";
          }
        }
        leaf pw-type {
          tailf:info
            "MPLS Pseudo-wire Type";
          tailf:cli-optional-in-sequence;
          tailf:cli-hide-in-submode;
          type uint8 {
            tailf:info
              "<4-5>;;Type-5 : Ethernet Port, Type-4 : Ethernet VLAN";
            range "4..5";
          }
        }
        leaf sequencing {
          tailf:info
            "Configure sequencing options for xconnect";
          tailf:cli-full-command;
          tailf:cli-hide-in-submode;
          when "../encapsulation = 'l2tpv3'" {
            tailf:xpath-root 3;
          }
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              type string {
                tailf:info
                  "Optional Pseudowire-class to use for backup pseudowire";
              }
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-sequence-commands;
          tailf:cli-compact-syntax;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            type string {
              tailf:info
                "WORD;;Pseudowire-class name";
            }
          }
        }
      }
    }
  }

  grouping ip-pim-grouping {
    container ssm {
      tailf:info
        "Configure Source Specific Multicast";
      choice ip-pim-ssm-choice {
        leaf default {
          tailf:info
            "Use 232/8 group range for SSM";
          type empty;
        }
        leaf range {
          tailf:info
            "ACL for group range to be used for SSM";
          type union {
            type uint16 {
              tailf:info
                "<1-99>;;Access list number";
              range "1..99";
            }
            type string {
              tailf:info
                "WORD;;IP named access list";
              pattern '[a-zA-Z].*';
            }
          }
        }
      }
    }
    list bsr-candidate {
      tailf:info
        "Candidate bootstrap router (candidate BSR)";
      tailf:cli-suppress-mode;
      tailf:cli-delete-when-empty;
      tailf:cli-compact-syntax;
      key "name";
      leaf name {
        type string {
          tailf:info
            "WORD;;Interface name";
        }
      }
      leaf hash-mask-length {
        tailf:cli-drop-node-name;
        type uint8 {
          tailf:info
            "<0-32>;;Hash Mask length for RP selection";
          range "0..32";
        }
      }
      leaf priority {
        tailf:cli-drop-node-name;
        type uint8 {
          tailf:info
            "<0-255>;;Priority value for candidate bootstrap router";
        }
      }
    }
    container rp-address {
      tailf:info
        "PIM RP-address (Rendezvous Point)";
      tailf:cli-compact-syntax;
      tailf:cli-sequence-commands {
        tailf:cli-reset-siblings;
      }
      leaf address {
        tailf:cli-drop-node-name;
        type inet:ipv4-address {
          tailf:info
            "A.B.C.D;;IP address of Rendezvous-point for group";
        }
      }
      leaf access-list {
        tailf:cli-drop-node-name;
        tailf:cli-optional-in-sequence;
        type std-acl-type;
      }
      leaf override {
        tailf:info
          "Overrides dynamically learnt RP mappings";
        type empty;
      }
    }
    list rp-candidate {
      tailf:info
        "To be a PIMv2 RP candidate";
      tailf:cli-suppress-mode;
      tailf:cli-delete-when-empty;
      tailf:cli-compact-syntax;
      key "name";
      leaf name {
        type string {
          tailf:info
            "WORD;;Interface name";
        }
      }
      leaf bidir {
        type empty;
      }
      leaf group-list {
        tailf:info
          "group-list";
        type union {
          type uint8 {
            tailf:info
              "<1-99>;;Access-list reference for group prefixes";
            range "1..99";
          }
          type string {
            tailf:info
              "WORD;;Named access list";
          }
        }
      }
      leaf interval {
        tailf:info
          "RP candidate advertisement interval";
        type uint16 {
          tailf:info
            "<1-16383>;;number of seconds";
          range "1..16383";
        }
      }
      leaf priority {
        tailf:info
          "RP candidate priority";
        type uint8 {
          tailf:info
            "<0-255>;;Priority value";
        }
      }
    }
  }

  grouping event-manager-applet-event-grouping {
    container none {
      tailf:info
        "Manually run policy event";
      leaf maxrun {
        tailf:info
          "Maximum runtime of applet";
        type uint32 {
          tailf:info
            "<0-31536000>;;Enter seconds[.milliseconds] value";
        }
      }
    }
    container snmp-notification {
      tailf:info
        "SNMP Notification Event";
      tailf:cli-compact-syntax;
      tailf:cli-reset-container;
      leaf oid {
        tailf:info
          "Object ID of data element";
        type string {
          tailf:info
            "WORD;;OID string";
        }
      }
      leaf oid-val {
        tailf:info
          "Comparison value";
        type string {
          tailf:info
            "WORD;;Comparision value";
        }
      }
      leaf op {
        tailf:info
          "Operator";
        type operator-type;
      }
      leaf src-ip-address {
        tailf:info
          "Source ip address";
        type union {
          type inet:ipv4-address {
            tailf:info
              "A.B.C.D;;Source ip address value";
          }
          type inet:ipv6-address {
            tailf:info
              "X:X:X:X::X;;Source ip address value";
          }
        }
      }
      leaf dest-ip-address {
        tailf:info
          "Destination ip address";
        type union {
          type inet:ipv4-address {
            tailf:info
              "A.B.C.D;;Destination ip address value";
          }
          type inet:ipv6-address {
            tailf:info
              "X:X:X:X::X;;Destination ip address value";
          }
        }
      }
    }
    container syslog {
      tailf:info
        "Syslog event";
      leaf pattern {
        tailf:info
          "Pattern match string for the entire message";
        type string {
          tailf:info
            "WORD;;Pattern match string for the entire message";
        }
      }
    }
    container cli {
      tailf:info
        "CLI event";
      tailf:cli-compact-syntax;
      container pattern {
        tailf:info
          "CLI command pattern match";
        tailf:cli-compact-syntax;
        tailf:cli-sequence-commands {
          tailf:cli-reset-siblings;
        }
        leaf regular-expression {
          tailf:cli-drop-node-name;
          type string {
            tailf:info
              "WORD;;Pattern match string";
          }
        }
        leaf sync {
          tailf:info
            "CLI and EEM policy execution sync or async";
          type enumeration {
            enum "no" {
              tailf:info
                "Policy and CLI will run asynchronously";
            }
            enum "yes" {
              tailf:info
                "Run policy and the result determines whether to run CLI";
            }
          }
        }
      }
    }
    container track {
      tailf:info
        "Tracking object event";
      tailf:cli-compact-syntax;
      tailf:cli-sequence-commands;
      leaf object-number {
        tailf:cli-drop-node-name;
        type uint16 {
          tailf:info
            "<1-500>;;Tracking object number";
        }
      }
      leaf state {
        tailf:info
          "State of tracking object";
        tailf:cli-optional-in-sequence;
        type enumeration {
          enum "any" {
            tailf:info
              "Any state";
          }
          enum "down" {
            tailf:info
              "Down state";
          }
          enum "up" {
            tailf:info
              "Up state";
          }
        }
      }
      leaf maxrun {
        tailf:info
          "Maximum runtime of applet";
        type uint32 {
          tailf:info
            "<0-31536000>;;Enter seconds[.milliseconds] value";
          range "0..31536000";
        }
      }
    }
  }

  grouping vrf-route-target-grouping {
    list export {
      tailf:info
        "Export Target-VPN community";
      tailf:cli-suppress-mode;
      tailf:cli-delete-when-empty;
      key "asn-ip";
      leaf asn-ip {
        type asn-ip-type {
          tailf:info
            "ASN:nn or IP-address:nn;;Target VPN Extended Community";
        }
      }
    }
    list import {
      tailf:info
        "Import Target-VPN community";
      tailf:cli-suppress-mode;
      tailf:cli-delete-when-empty;
      key "asn-ip";
      leaf asn-ip {
        type asn-ip-type {
          tailf:info
            "ASN:nn or IP-address:nn;;Target VPN Extended Community";
        }
      }
    }
  }

  grouping vrf-definition-af-grouping {
    container export {
      tailf:info
        "VRF export";
      leaf map {
        tailf:info
          "Route-map based VRF export";
        type string {
          tailf:info
            "WORD;;Route-map reference";
        }
      }
    }
    container route-target {
      tailf:info
        "Specify Target VPN Extended Communities";
      uses vrf-route-target-grouping;
    }
    container maximum {
      tailf:info
        "Set a limit";
      container routes {
        tailf:info
          "Maximum number of routes allowed in this routing table";
        tailf:cli-compact-syntax;
        tailf:cli-sequence-commands {
          tailf:cli-reset-siblings;
        }
        leaf limit {
          tailf:cli-drop-node-name;
          tailf:cli-incomplete-command;
          type uint32 {
            tailf:info
              "<1-4294967294>;;Maximum number of routes allowed";
          }
        }
        choice action {
          case a {
            leaf warning-only {
              tailf:info
                "Only give a warning message if limit is exceeded";
              type empty;
            }
          }
          case b {
            leaf warn-threshold {
              tailf:cli-drop-node-name;
              type uint8 {
                tailf:info
                  "<1-100>;;Threshold value (%) at which to generate a warning msg";
                range "1..100";
              }
            }
            leaf reinstall {
              tailf:info
                "Reinstall previous rejected route due to over maximum route limit";
              type uint8 {
                tailf:info
                  "<1-100>;;Threshold value (%) at which to reinstall routes back to VRF";
                range "1..100";
              }
            }
          }
        }
      }
    }
  }

  grouping snmp-server-host-grouping {
    leaf message-type {
      tailf:cli-optional-in-sequence;
      tailf:cli-drop-node-name;
      tailf:cli-incomplete-command;
      type enumeration {
        enum "informs" {
          tailf:info
            "Send Inform messages to this host";
        }
        enum "traps" {
          tailf:info
            "Send Trap messages to this host";
        }
      }
      default "traps";
    }
    container version {
      tailf:info
        "SNMP version to use for notification messages";
      tailf:cli-optional-in-sequence;
      tailf:cli-flatten-container;
      tailf:cli-compact-syntax;
      tailf:cli-incomplete-command;
      leaf version {
        tailf:cli-drop-node-name;
        type enumeration {
          enum "1" {
            tailf:info
              "Use SNMPv1";
          }
          enum "2c" {
            tailf:info
              "Use SNMPv2c";
          }
          enum "3" {
            tailf:info
              "Use SNMPv3";
          }
        }
      }
      leaf security-level {
        tailf:cli-drop-node-name;
        when "../version = '3'" {
          tailf:xpath-root 3;
        }
        type enumeration {
          enum "auth" {
            tailf:info
              "Use the SNMPv3 authNoPriv Security Level";
          }
          enum "noauth" {
            tailf:info
              "Use the SNMPv3 noAuthNoPriv Security Level";
          }
          enum "priv" {
            tailf:info
              "Use the SNMPv3 authPriv Security Level";
          }
        }
      }
    }
    leaf community-string {
      tailf:cli-drop-node-name;
      tailf:cli-disallow-value "version|informs|traps|vrf";
      type string {
        tailf:info
          "WORD;;SNMPv1/v2c community string or SNMPv3 user name";
      }
    }
    leaf-list allowed-traps {
      tailf:cli-drop-node-name;
      tailf:cli-flat-list-syntax {
        tailf:cli-replace-all;
      }
      type enumeration {
        enum "aaa_server" {
          tailf:info
            "Allow SNMP AAA traps";
        }
        enum "alarms" {
          tailf:info
            "Allow SNMP alarms traps";
        }
        enum "atm" {
          tailf:info
            "Allow SNMP atm traps";
        }
        enum "bfd" {
          tailf:info
            "Allow SNMP BFD traps";
        }
        enum "bgp" {
          tailf:info
            "Allow BGP state change traps";
        }
        enum "bstun" {
          tailf:info
            "Allow bstun event traps";
        }
        enum "bulkstat" {
          tailf:info
            "Allow Data-Collection-MIB traps";
        }
        enum "cable" {
          tailf:info
            "Allow SNMP cable traps";
        }
        enum "call-home" {
          tailf:info
            "Allow SNMP CISCO-CALLHOME-MIB traps";
        }
        enum "casa" {
          tailf:info
            "Allow casa event traps";
        }
        enum "cef" {
          tailf:info
            "Allows cef traps";
        }
        enum "cnpd" {
          tailf:info
            "Allow NBAR Protocol Discovery traps";
        }
        enum "config" {
          tailf:info
            "Allow SNMP config traps";
        }
        enum "config-copy" {
          tailf:info
            "Allow SNMP config-copy traps";
        }
        enum "config-ctid" {
          tailf:info
            "Allow SNMP config-ctid traps";
        }
        enum "cpu" {
          tailf:info
            "Allow cpu related traps";
        }
        enum "dhcp" {
          tailf:info
            "Allow dhcp traps";
        }
        enum "dlsw" {
          tailf:info
            "Allow dlsw traps";
        }
        enum "ds1" {
          tailf:info
            "Allow SNMP ds1 traps";
        }
        enum "dsp" {
          tailf:info
            "Allow SNMP DSP traps";
        }
        enum "dspu" {
          tailf:info
            "Allow dspu event traps";
        }
        enum "eigrp" {
          tailf:info
            "Allow SNMP EIGRP traps";
        }
        enum "entity" {
          tailf:info
            "Allow SNMP entity traps";
        }
        enum "entity-diag" {
          tailf:info
            "Allow SNMP CISCO-ENTITY-DIAG-MIB traps";
        }
        enum "entity-qfp" {
          tailf:info
            "Allow SNMP CISCO-ENTITY-QFP-MIB traps";
        }
        enum "entity-state" {
          tailf:info
            "Allow ENTITY-STATE-MIB traps";
        }
        enum "envmon" {
          tailf:info
            "Allow environmental monitor traps";
        }
        enum "ethernet-cfm" {
          tailf:info
            "Allow SNMP Ethernet CFM traps";
        }
        enum "evc" {
          tailf:info
            "Allow SNMP EVC traps";
        }
        enum "event-manager" {
          tailf:info
            "Allow SNMP Embedded Event Manager traps";
        }
        enum "firewall" {
          tailf:info
            "Allow SNMP Firewall traps";
        }
        enum "flash" {
          tailf:info
            "Allow SNMP FLASH traps";
        }
        enum "flowmon" {
          tailf:info
            "Allow SNMP flow monitor notifications";
        }
        enum "frame-relay" {
          tailf:info
            "Allow SNMP frame-relay traps";
        }
        enum "fru-ctrl" {
          tailf:info
            "Allow entity FRU control traps";
        }
        enum "gdoi" {
          tailf:info
            "Allows gdoi traps";
        }
        enum "hsrp" {
          tailf:info
            "Allow SNMP HSRP traps";
        }
        enum "iplocalpool" {
          tailf:info
            "Allow SNMP IP Local Pool traps";
        }
        enum "ipmulticast" {
          tailf:info
            "Allow SNMP ipmulticast traps";
        }
        enum "ipsec" {
          tailf:info
            "Allow SNMP IPsec traps";
        }
        enum "ipsla" {
          tailf:info
            "Allow SNMP Host IP SLA traps";
        }
        enum "isakmp" {
          tailf:info
            "Allow SNMP ISAKMP traps";
        }
        enum "isg-mib" {
          tailf:info
            "Allow SNMP isgmib traps";
        }
        enum "isis" {
          tailf:info
            "Allow IS-IS traps";
        }
        enum "l2tun-pseudowire-status" {
          tailf:info
            "Allow SNMP L2 pseudowire status traps";
        }
        enum "l2tun-session" {
          tailf:info
            "Allow SNMP L2 session traps";
        }
        enum "license" {
          tailf:info
            "Allow license traps";
        }
        enum "memory" {
          tailf:info
            "Allow SNMP Mempool traps";
        }
        enum "mpls-fast-reroute" {
          tailf:info
            "Allow SNMP MPLS traffic engineering fast reroute traps";
        }
        enum "mpls-ldp" {
          tailf:info
            "Allow SNMP MPLS label distribution protocol traps";
        }
        enum "mpls-traffic-eng" {
          tailf:info
            "Allow SNMP MPLS traffic engineering traps";
        }
        enum "mpls-vpn" {
          tailf:info
            "Allow SNMP MPLS Virtual Private Network traps";
        }
        enum "msdp" {
          tailf:info
            "Allow SNMP MSDP traps";
        }
        enum "mvpn" {
          tailf:info
            "Allow Multicast Virtual Private Network traps";
        }
        enum "nhrp" {
          tailf:info
            "Allow SNMP NHRP traps";
        }
        enum "ospf" {
          tailf:info
            "Allow OSPF traps";
        }
        enum "ospfv3" {
          tailf:info
            "Allow OSPFv3 traps";
        }
        enum "pfr" {
          tailf:info
            "Allow SNMP PfR traps";
        }
        enum "pim" {
          tailf:info
            "Allow SNMP PIM traps";
        }
        enum "pw-vc" {
          tailf:info
            "Allow SNMP Pseudowire VC traps";
        }
        enum "resource-policy" {
          tailf:info
            "Enable CISCO-ERM-MIB notifications";
        }
        enum "rf" {
          tailf:info
            "Allow all SNMP traps defined in CISCO-RF-MIB";
        }
        enum "rsrb" {
          tailf:info
            "Allow rsrb event traps";
        }
        enum "rsvp" {
          tailf:info
            "Allow RSVP flow change traps";
        }
        enum "sdlc" {
          tailf:info
            "Allow sdlc event traps";
        }
        enum "sdllc" {
          tailf:info
            "Allow sdllc event traps";
        }
        enum "snmp" {
          tailf:info
            "Allow SNMP-type notifications";
        }
        enum "sonet" {
          tailf:info
            "Allow SNMP SONET traps";
        }
        enum "srp" {
          tailf:info
            "Allow SRP protocol traps";
        }
        enum "stun" {
          tailf:info
            "Allow stun event traps";
        }
        enum "syslog" {
          tailf:info
            "Allow SNMP syslog traps";
        }
        enum "trustsec-sxp" {
          tailf:info
            "Allow SNMP CISCO-TRUSTSEC-SXP-MIB traps";
        }
        enum "tty" {
          tailf:info
            "Allow TCP connection traps";
        }
        enum "udp-port" {
          tailf:info
            "The notification host's UDP port number (default port 162)";
        }
        enum "voice" {
          tailf:info
            "Allow SNMP Voice traps";
        }
        enum "vrfmib" {
          tailf:info
            "Allow SNMP vrfmib traps";
        }
        enum "vrrp" {
          tailf:info
            "Allow SNMP vrrp traps";
        }
        enum "x25" {
          tailf:info
            "Allow x25 event traps";
        }
      }
    }
  }

  grouping ip-sla-proto-grouping {
    leaf tos {
      tailf:cli-break-sequence-commands;
      tailf:info
        "Type Of Service";
      type uint8 {
        tailf:info
          "<0-255>;;Type of Service Value";
      }
    }
    leaf verify-data {
      tailf:info
        "Verify data";
      type empty;
    }
    leaf data-pattern {
      tailf:info
        "Data Pattern";
      type string {
        tailf:info
          "WORD;;Data Pattern in Hex";
        pattern '[a-fA-F0-9].*';
      }
    }
    leaf vrf {
      tailf:info
        "Configure IP SLAs for a VPN Routing/Forwarding instance";
      tailf:cli-diff-dependency "/ios:ip/vrf" {
        tailf:xpath-root 3;
      }
      tailf:cli-diff-dependency "/ios:vrf/definition" {
        tailf:xpath-root 3;
      }
      type string {
        tailf:info
          "WORD;;VRF name";
      }
    }
    leaf owner {
      tailf:info
        "Owner of Entry";
      tailf:cli-multi-value;
      tailf:cli-full-command;
      type string {
        tailf:info
          "LINE;;Owner String";
      }
    }
    leaf tag {
      tailf:info
        "User defined tag";
      tailf:cli-multi-value;
      tailf:cli-full-command;
      type string {
        tailf:info
          "LINE;;Tag string";
      }
    }
    leaf frequency {
      tailf:info
        "Frequency of an operation";
      type uint32 {
        tailf:info
          "<1-604800>;;Frequency in seconds (default 60)";
        range "1..604800";
      }
      default "60";
    }
    leaf timeout {
      tailf:info
        "Timeout of an operation";
      type uint32 {
        tailf:info
          "<0-604800000>;;Timeout in milliseconds";
        range "0..604800000";
      }
    }
    leaf threshold {
      tailf:info
        "Operation threshold in milliseconds";
      type uint16 {
        tailf:info
          "<0-60000>;;Millisecond threshold value";
        range "0..60000";
      }
    }
    container history {
      tailf:info
        "History and Distribution Data";
      leaf hours-of-statistics-kept {
        tailf:info
          "Maximum number of statistics hour groups to capture";
        type uint8 {
          tailf:info
            "<0-25>;;Hour groups size value (default 2)";
          range "0..25";
        }
        default "2";
      }
      leaf distributions-of-statistics-kept {
        tailf:info
          "Maximum number of statistics distribution buckets to capture";
        type uint8 {
          tailf:info
            "<1-20>;;Distribution bucket size value (default 1)";
          range "1..20";
        }
        default "1";
      }
      leaf statistics-distribution-interval {
        tailf:info
          "Statistics distribution interval size";
        type uint8 {
          tailf:info
            "<1-100>;;Distribution interval value (default 20)";
          range "1..100";
        }
        default "20";
      }
      leaf lives-kept {
        tailf:info
          "Maximum number of history lives to collect";
        type uint8 {
          tailf:info
            "<0-2>;;Life size value (default 0)";
          range "0..2";
        }
        default "0";
      }
      leaf buckets-kept {
        tailf:info
          "Maximum number of history buckets to collect";
        type uint8 {
          tailf:info
            "<1-60>;;Bucket size value (default 15)";
          range "1..60";
        }
        default "15";
      }
      leaf filter {
        tailf:info
          "Add operation to History when...";
        type enumeration {
          enum "all" {
            tailf:info
              "Collect every operation in History";
          }
          enum "failures" {
            tailf:info
              "Collect operations that fail in History";
          }
          enum "none" {
            tailf:info
              "Shutoff History collection";
          }
          enum "overThreshold" {
            tailf:info
              "Collect operations that are over threshold in History";
          }
        }
      }
      container enhanced {
        tailf:info
          "Enable enhanced history collection";
        tailf:cli-compact-syntax;
        tailf:cli-sequence-commands;
        leaf interval {
          tailf:info
            "Aggregation interval";
          tailf:cli-incomplete-command;
          type uint16 {
            tailf:info
              "<1-3600>;;Interval in seconds";
            range "1..3600";
          }
        }
        leaf buckets {
          tailf:info
            "Number of buckets to collect data";
          type uint8 {
            tailf:info
              "<1-100>;;Number of buckets";
            range "1..100";
          }
        }
      }
    }
  }

  grouping aaa-authentication-method-grouping {
    leaf cache {
      tailf:info
        "Use Cached-group";
      type aaa-group-type;
    }
    leaf group {
      tailf:info
        "Use Server-group";
      type aaa-group-type;
    }
    leaf krb5 {
      tailf:info
        "Use Kerberos 5 authentication.";
      type empty;
    }
    leaf local {
      tailf:info
        "Use local username authentication.";
      type empty;
    }
    leaf line {
      tailf:info
        "Use line password for authentication.";
      type empty;
    }
    leaf enable {
      tailf:info
        "Use enable password for authentication.";
      type empty;
    }
    leaf none {
      tailf:info
        "NO authentication.";
      tailf:cli-full-command;
      type empty;
    }
  }

  grouping aaa-authorization-method-grouping {
    leaf cache {
      tailf:info
        "Use Cached-group";
      type aaa-group-type;
    }
    leaf group {
      tailf:info
        "Use server-group.";
      type aaa-group-type;
    }
    leaf krb5-instance {
      tailf:info
        "Use Kerberos instance privilege maps.";
      type empty;
    }
    leaf if-authenticated {
      tailf:info
        "Succeed if user has authenticated.";
      type empty;
    }
    leaf local {
      tailf:info
        "Use local database.";
      type empty;
    }
    leaf none {
      tailf:info
        "No authorization (always succeeds).";
      tailf:cli-full-command;
      type empty;
    }
  }

  grouping aaa-accounting-method-grouping {
    leaf action-type {
      tailf:cli-drop-node-name;
      type enumeration {
        enum "none" {
          tailf:info
            "No accounting.";
        }
        enum "start-stop" {
          tailf:info
            "Record start and stop without waiting";
        }
        enum "stop-only" {
          tailf:info
            "Record stop when service terminates.";
        }
      }
    }
    leaf broadcast {
      tailf:info
        "Use Broadcast for Accounting";
      tailf:cli-optional-in-sequence;
      tailf:cli-incomplete-command;
      type empty;
    }
    leaf group {
      tailf:info
        "Use Server-group";
      type aaa-group-type;
    }
  }

  grouping cable-modulation-profile-grouping {
    leaf fec-tbytes {
      tailf:cli-drop-node-name;
      tailf:cli-incomplete-command;
      type uint8 {
        tailf:info
          "<0-16>;;FEC tbytes";
      }
    }
    leaf fec-len {
      tailf:cli-drop-node-name;
      tailf:cli-incomplete-command;
      type uint8 {
        tailf:info
          "<16-253>;;FEC codeword length in k bytes";
      }
    }
    leaf burst-len {
      tailf:cli-drop-node-name;
      tailf:cli-incomplete-command;
      type uint8 {
        tailf:info
          "<0-255>;;max burst size in minislots";
      }
    }
    leaf guard-t {
      tailf:cli-drop-node-name;
      tailf:cli-incomplete-command;
      type uint8 {
        tailf:info
          "<0-255>;;guard time in symbols";
      }
    }
    leaf mod {
      tailf:cli-drop-node-name;
      tailf:cli-incomplete-command;
      type enumeration {
        enum "8qam" {
          tailf:info
            "8-QAM modulation";
        }
        enum "16qam" {
          tailf:info
            "16-QAM modulation";
        }
        enum "32qam" {
          tailf:info
            "32-QAM modulation";
        }
        enum "64qam" {
          tailf:info
            "64-QAM modulation";
        }
        enum "qpsk" {
          tailf:info
            "qpsk modulation";
        }
      }
    }
    leaf scrambler {
      tailf:cli-drop-node-name;
      tailf:cli-incomplete-command;
      type enumeration {
        enum "no-scrambler" {
          tailf:info
            "scrambler disabled";
        }
        enum "scrambler" {
          tailf:info
            "scrambler enabled";
        }
      }
    }
    leaf seed {
      when "../scrambler = 'scrambler'" {
        tailf:xpath-root 3;
        tailf:dependency "../scrambler";
      }
      tailf:cli-drop-node-name;
      tailf:cli-incomplete-command;
      type string {
        tailf:info
          "<0x0-0x7FFF>;;scrambler seed in hex";
      }
    }
    leaf diff {
      tailf:cli-drop-node-name;
      tailf:cli-incomplete-command;
      type enumeration {
        enum "diff" {
          tailf:info
            "diff encoding enabled";
        }
        enum "no-diff" {
          tailf:info
            "diff encoding disabled";
        }
      }
    }
    leaf pre-len {
      tailf:cli-drop-node-name;
      tailf:cli-incomplete-command;
      type uint16 {
        tailf:info
          "<4-1536>;;preamble length in bits";
      }
    }
    leaf last-cw {
      tailf:cli-drop-node-name;
      type enumeration {
        enum "fixed" {
          tailf:info
            "fixed codeword";
        }
        enum "shortened" {
          tailf:info
            "shortened codeword";
        }
      }
    }
    leaf preamble {
      tailf:cli-drop-node-name;
      type enumeration {
        enum "qpsk0" {
          tailf:info
            "QPSK0 preamble";
        }
        enum "qpsk1" {
          tailf:info
            "QPSK1 preamble";
        }
      }
    }
    leaf rs-interleave-depth {
      tailf:cli-drop-node-name;
      type uint8 {
        tailf:info
          "<0-114>;;RS interleave depth";
      }
    }
    leaf rs-interleave-block {
      tailf:cli-drop-node-name;
      type uint16 {
        tailf:info
          "<18-2048>;;RS interleave block size";
      }
    }
  }

  grouping cable-load-balance-docsis-group-grouping {
    leaf restricted {
      tailf:info
        "Set load balance group as restricted";
      type empty;
    }
    container downstream {
      tailf:info
        "Set downstream RF channels";
      tailf:cli-compact-syntax;
      tailf:cli-sequence-commands;
      leaf Modular-Cable {
        tailf:info
          "Modular cable";
        tailf:cli-incomplete-command;
        type string {
          tailf:info
            "<slot>/<card>/<port>;;Enter slot/subslot/bay";
        }
      }
      leaf rf-channel {
        tailf:info
          "RF channel";
        type string {
          tailf:info
            "<grouplist>;;List of port numbers and number ranges";
        }
      }
    }
    container upstream {
      tailf:info
        "Set upstream channels";
      tailf:cli-compact-syntax;
      tailf:cli-sequence-commands;
      leaf Cable {
        tailf:info
          "CMTS interface";
        tailf:cli-allow-join-with-value {
          tailf:cli-display-joined;
        }
        tailf:cli-incomplete-command;
        type string {
          tailf:info
            "<slot>/<card>/<port>;;Enter slot/subslot/port";
        }
      }
      leaf upstream-list {
        tailf:cli-drop-node-name;
        type string {
          tailf:info
            "<grouplist>;;List of Ranges for upstream channels <0-7>";
        }
      }
    }
    container method {
      tailf:info
        "Set load balancing type/method";
      container utilization {
        tailf:info
          "Interface utilization";
        presence "true";
      }
    }
    container threshold {
      tailf:info
        "Load balancing threshold in %";
      container load {
        tailf:info
          "Interface load threshold settings";
        leaf percentage {
          tailf:cli-drop-node-name;
          type uint8 {
            tailf:info
              "<1-100>;;Threshold value in %";
            range "1..100";
          }
        }
        leaf minimum {
          tailf:info
            "Set minimum number of modems/flows difference before loadbalancing starts";
          type uint8 {
            tailf:info
              "<1-100>;;Minimum number of modems/flows";
            range "1..100";
          }
        }
      }
      leaf stability {
        tailf:info
          "Threshold for stability detection";
        type uint8 {
          tailf:info
            "<0-100>;;Stability condition detection threshold in %";
          range "0..100";
        }
      }
    }
    leaf policy {
      tailf:info
        "Set load balancing policy";
      type enumeration {
        tailf:info
          "pure-ds-load;;Do not count US load when calculating DS utilization";
        enum "pcmm" {
          tailf:info
            "Enable balancing of modems with active PCMM service flows";
        }
        enum "pure-ds-load" {
          tailf:info
            "Do not count US load when calculating DS utilization";
        }
        enum "ugs" {
          tailf:info
            "Enable balancing of modems with active UGS service flows";
        }
        enum "us-across-ds" {
          tailf:info
            "Load balancing on US groups across DS, DS method will be ignored";
        }
      }
    }
    leaf interval {
      tailf:info
        "Set interface polling interval";
      type uint16 {
        tailf:info
          "<1-1000>;;Interface polling interval in seconds";
        range "1..1000";
      }
    }
    container init-tech-list {
      tailf:info
        "Set DCC initialization technique list";
      tailf:cli-compact-syntax;
      tailf:cli-sequence-commands {
        tailf:cli-reset-all-siblings;
      }
      leaf grouplist {
        tailf:cli-drop-node-name;
        type string {
          tailf:info
            "<grouplist> ";
        }
      }
      leaf ucc {
        tailf:info
          "Allow the use of UCC in upstream load balancing";
        type empty;
      }
    }
    leaf docsis-policy {
      tailf:info
        "Enter load balance group policy";
      type uint32 {
        tailf:info
          "<0-4294967295>;;Load balance group policy number";
        range "0..4294967295";
      }
    }
    list tag {
      tailf:info
        "Add tag to load balancing group";
      tailf:cli-suppress-mode;
      tailf:cli-delete-when-empty;
      key "name";
      leaf name {
        type string {
          tailf:info
            "WORD;;tag name";
        }
      }
    }
  }

  grouping facility-alarm-grouping {
    container major {
      tailf:info
        "Major warning threshold";
      leaf temperature {
        tailf:cli-drop-node-name;
        type uint8 {
          tailf:info
            "<20-100>;;<##> threshold temperature (degrees C)";
          range "20..100";
        }
      }
    }
    container minor {
      tailf:info
        "Minor warning threshold";
      leaf temperature {
        tailf:cli-drop-node-name;
        type uint8 {
          tailf:info
            "<20-100>;;<##> threshold temperature (degrees C)";
          range "20..100";
        }
      }
    }
    container critical {
      tailf:info
        "Critical warning threshold";
      leaf exceed-action {
        tailf:info
          "Critical outlet temperature exceed action";
        tailf:cli-full-command;
        type enumeration {
          enum "shutdown" {
            tailf:info
              "Auto-shutdown when critical outlet temperature is exceeded";
          }
        }
      }
      leaf temperature {
        tailf:cli-drop-node-name;
        tailf:cli-full-command;
        type uint8 {
          tailf:info
            "<1-255>;;<##> threshold temperature (degrees C)";
          range "1..255";
        }
      }
    }
  }

  grouping process-cpu-threshold-grouping {
    leaf rising {
      tailf:info
        "rising threshold";
      tailf:cli-incomplete-command;
      type uint8 {
        tailf:info
          "<1-100>";
        range "1..100";
      }
    }
    leaf interval {
      tailf:info
        "observation interval";
      type uint32 {
        tailf:info
          "<5-86400>";
        range "5..86400";
      }
    }
    leaf falling {
      tailf:info
        "falling threshold ";
      type uint8 {
        tailf:info
          "<1-100>";
        range "1..100";
      }
    }
    container falling-interval {
      tailf:cli-flatten-container;
      tailf:cli-drop-node-name;
      leaf interval {
        tailf:info
          "observation interval";
        type uint32 {
          tailf:info
            "<5-86400>";
          range "5..86400";
        }
      }
    }
  }

  grouping cable-submgmt-default-filter-group-grouping {
    leaf upstream {
      tailf:info
        "Default Upstream Group";
      type uint8 {
        tailf:info
          "<1-254>;;Group ID";
        range "1..254";
      }
    }
    leaf downstream {
      tailf:info
        "Default Downstream Group";
      type uint8 {
        tailf:info
          "<1-254>;;Group ID";
        range "1..254";
      }
    }
  }

  grouping storm-control-level-bps-pps-grouping {
    container level-bps-pps {
      tailf:cli-drop-node-name;
      container level {
        tailf:info
          "Set storm suppression level on this interface";
        choice level-choice {
          leaf bps {
            tailf:info
              "Enter suppression level in bits per second";
            type string {
              tailf:info
                "<0.0 - 10000000000.0>[k|m|g];;Enter rising threshold";
            }
          }
          leaf pps {
            tailf:info
              "Enter suppression level in packets per second";
            type string {
              tailf:info
                "<0.0 - 10000000000.0>[k|m|g];;Enter rising threshold";
            }
          }
        }
      }
    }
  }

  grouping service-policy-grouping {
    leaf input {
      tailf:info
        "Assign input policy-map";
      type string {
        tailf:info
          "WORD;;input Policy-map name";
      }
      tailf:non-strict-leafref {
        path "/ncs:devices/ncs:device/ncs:config/ios:policy-map/name" {
          tailf:xpath-root 3;
        }
      }
    }
    leaf output {
      tailf:info
        "Assign output policy-map";
      type string {
        tailf:info
          "WORD;;output Policy-map name";
      }
      tailf:non-strict-leafref {
        path "/ncs:devices/ncs:device/ncs:config/ios:policy-map/name" {
          tailf:xpath-root 3;
        }
      }
    }
  }

  augment "/ncs:devices/ncs:device/ncs:config" {
    container upgrade {
      tailf:ncs-device-type "cli-ned";
      tailf:display-when "not(../../ncs:module) or ../../ncs:module[ncs:name='tailf-ned-cisco-ios']";
      tailf:info
        "Global upgrade configuration subcommands";
      container fpd {
        tailf:info
          "Configure field programmable devices upgrade options";
        leaf auto {
          tailf:info
            "Auto upgrade all FPD images";
          type empty;
        }
        leaf path {
          tailf:info
            "Set path to locate the FPD image package file for auto upgrade";
          type string;
        }
      }
    }
    container tailfned {
      tailf:ncs-device-type "cli-ned";
      tailf:display-when "not(../../ncs:module) or ../../ncs:module[ncs:name='tailf-ned-cisco-ios']";
      leaf device {
        tailf:cli-no-value-on-delete;
        tailf:cli-suppress-no;
        type string;
      }
      leaf police {
        tailf:cli-no-value-on-delete;
        tailf:cli-suppress-no;
        type string {
          tailf:info
            "cirmode | bpsflat | numflat | cirflat";
        }
      }
    }
    leaf version {
      tailf:ncs-device-type "cli-ned";
      tailf:display-when "not(../../ncs:module) or ../../ncs:module[ncs:name='tailf-ned-cisco-ios']";
      tailf:info
        "Version";
      type string {
        tailf:info
          "WORD;;Version number";
      }
    }
    container service {
      tailf:ncs-device-type "cli-ned";
      tailf:display-when "not(../../ncs:module) or ../../ncs:module[ncs:name='tailf-ned-cisco-ios']";
      tailf:info
        "Modify use of network based services";
      leaf config {
        tailf:info
          "TFTP load config files";
        tailf:cli-full-command;
        type empty;
      }
      leaf exec-callback {
        tailf:info
          "Enable exec callback";
        tailf:cli-full-command;
        type empty;
      }
      leaf nagle {
        tailf:info
          "Enable Nagle's congestion control algorithm";
        tailf:cli-full-command;
        type empty;
      }
      leaf slave-log {
        tailf:info
          "Enable log capability of slave IPs";
        tailf:cli-boolean-no;
        tailf:cli-full-command;
        type boolean;
        default "true";
      }
      container pad {
        tailf:info
          "Enable PAD commands";
        tailf:cli-incomplete-no;
        tailf:cli-incomplete-command;
        leaf to-xot {
          tailf:info
            "Allow outgoing PAD over XOT connections";
          tailf:cli-full-command;
          type empty;
        }
        leaf from-xot {
          tailf:info
            "Accept XOT to PAD connections";
          tailf:cli-full-command;
          type empty;
        }
        leaf cmns {
          tailf:info
            "Enable PAD over CMNS connections";
          tailf:cli-full-command;
          type empty;
        }
      }
      container conf {
        tailf:cli-drop-node-name;
        leaf pad {
          tailf:cli-boolean-no;
          tailf:cli-full-command;
          type boolean;
          default "true";
        }
      }
      leaf tcp-keepalives-in {
        tailf:info
          "Generate keepalives on idle incoming network connections";
        tailf:cli-full-command;
        type empty;
      }
      leaf tcp-keepalives-out {
        tailf:info
          "Generate keepalives on idle outgoing network connections";
        tailf:cli-full-command;
        type empty;
      }
      container timestamps {
        tailf:info
          "Timestamp debug/log messages";
        tailf:cli-compact-syntax;
        tailf:cli-delete-when-empty;
        presence "true";
        container debug {
          tailf:info
            "Timestamp debug messages";
          choice timestamp-choice {
            leaf uptime {
              tailf:info
                "Timestamp with system uptime";
              type empty;
            }
            container datetime {
              tailf:info
                "Timestamp with date and time";
              tailf:cli-compact-syntax;
              tailf:cli-delete-when-empty;
              presence "true";
              leaf msec {
                tailf:info
                  "Include milliseconds in timestamp";
                type empty;
              }
              leaf localtime {
                tailf:info
                  "Use local time zone for timestamps";
                type empty;
              }
              leaf show-timezone {
                tailf:info
                  "Add time zone information to timestamp";
                type empty;
              }
              leaf year {
                tailf:info
                  "Include year in timestamp";
                type empty;
              }
            }
          }
        }
        container log {
          tailf:info
            "Timestamp log messages";
          choice timestamp-choice {
            leaf uptime {
              tailf:info
                "Timestamp with system uptime";
              type empty;
            }
            container datetime {
              tailf:info
                "Timestamp with date and time";
              tailf:cli-compact-syntax;
              tailf:cli-delete-when-empty;
              presence "true";
              leaf msec {
                tailf:info
                  "Include milliseconds in timestamp";
                type empty;
              }
              leaf localtime {
                tailf:info
                  "Use local time zone for timestamps";
                type empty;
              }
              leaf show-timezone {
                tailf:info
                  "Add time zone information to timestamp";
                type empty;
              }
              leaf year {
                tailf:info
                  "Include year in timestamp";
                type empty;
              }
            }
          }
        }
      }
      container password-encryption {
        tailf:info
          "Encrypt system passwords";
        tailf:cli-show-no;
        presence "true";
      }
      leaf exec-wait {
        tailf:info
          "Delay EXEC startup on noisy lines";
        tailf:cli-full-command;
        type empty;
      }
      leaf linenumber {
        tailf:info
          "enable line number banner for each exec";
        tailf:cli-full-command;
        type empty;
      }
      leaf compress-config {
        tailf:info
          "Compress the configuration file";
        tailf:cli-full-command;
        type empty;
      }
      leaf udp-small-servers {
        tailf:info
          "Enable small UDP servers (e.g., ECHO)";
        tailf:cli-full-command;
        type empty;
      }
      leaf tcp-small-servers {
        tailf:info
          "Enable small TCP servers (e.g., ECHO)";
        tailf:cli-full-command;
        type empty;
      }
      leaf old-slip-prompts {
        tailf:info
          "Allow old scripts to operate with slip/ppp";
        tailf:cli-full-command;
        type empty;
      }
      leaf pt-vty-logging {
        tailf:info
          "Log significant VTY-Async events";
        tailf:cli-full-command;
        type empty;
      }
      leaf disable-ip-fast-frag {
        tailf:info
          "Disable IP particle-based fast fragmentation";
        tailf:cli-full-command;
        type empty;
      }
      leaf sequence-numbers {
        tailf:info
          "Stamp logger messages with a sequence number";
        tailf:cli-full-command;
        type empty;
      }
      container divert-rate-limit {
        tailf:info
          "Set WAN-side divert-rate-limit parameters";
        list ip {
          tailf:info
            "WAN-IPv4 configuration";
          tailf:cli-suppress-mode;
          tailf:cli-delete-when-empty;
          tailf:cli-compact-syntax;
          tailf:cli-sequence-commands;
          tailf:cli-incomplete-command;
          key "divert-code";
          leaf divert-code {
            type string {
              tailf:info
                "WORD;;divert code";
            }
          }
          leaf rate {
            tailf:info
              "rate in packets/sec";
            tailf:cli-incomplete-command;
            type uint16 {
              tailf:info
                "<1-65535>;;rate in packets/second";
            }
          }
          leaf limit {
            tailf:info
              "limit in packets";
            type uint16 {
              tailf:info
                "<4-4194>;;limit in packets";
              range "4..4194";
            }
          }
        }
        list ipv6 {
          tailf:info
            "WAN-IPv6 configuration";
          tailf:cli-suppress-mode;
          tailf:cli-delete-when-empty;
          tailf:cli-compact-syntax;
          tailf:cli-sequence-commands;
          tailf:cli-incomplete-command;
          key "divert-code";
          leaf divert-code {
            type string {
              tailf:info
                "WORD;;divert code";
            }
          }
          leaf rate {
            tailf:info
              "rate in packets/sec";
            tailf:cli-incomplete-command;
            type uint16 {
              tailf:info
                "<1-65535>;;rate in packets/second";
            }
          }
          leaf limit {
            tailf:info
              "limit in packets";
            type uint16 {
              tailf:info
                "<4-4194>;;limit in packets";
              range "4..4194";
            }
          }
        }
        list trusted-site {
          tailf:info
            "trusted-site configuration for WAN-IPv4";
          tailf:cli-suppress-mode;
          tailf:cli-delete-when-empty;
          key "ip-address mask-ip-address tos mask";
          max-elements 4;
          leaf ip-address {
            type inet:ipv4-address {
              tailf:info
                "A.B.C.D;;source IP address";
            }
          }
          leaf mask-ip-address {
            type inet:ipv4-address {
              tailf:info
                "A.B.C.D;;IP prefix mask";
            }
          }
          leaf tos {
            tailf:info
              "ToS value";
            tailf:cli-expose-key-name;
            type string {
              tailf:info
                "<0-255>;;ToS value";
            }
          }
          leaf mask {
            tailf:info
              "ToS mask";
            tailf:cli-expose-key-name;
            type string {
              tailf:info
                "<0-255>;;ToS mask";
            }
          }
        }
        list trusted-site-ipv6 {
          tailf:info
            "trusted-site configuration for WAN-IPv6";
          tailf:cli-suppress-mode;
          tailf:cli-delete-when-empty;
          key "ip-address traffic-class mask";
          max-elements 4;
          leaf ip-address {
            type ios:ipv6-prefix {
              tailf:info
                "X:X:X:X::X/<0-128>;;IPv6 Source address/Prefix length.(e.g., 1234::1/<prefix-length>)";
            }
          }
          leaf traffic-class {
            tailf:info
              "traffic-class value";
            tailf:cli-expose-key-name;
            type string {
              tailf:info
                "<0-255>;;traffic-class value";
            }
          }
          leaf mask {
            tailf:info
              "traffic-class mask";
            tailf:cli-expose-key-name;
            type string {
              tailf:info
                "<0-255>;;traffic-class mask";
            }
          }
        }
      }
      container counters {
        tailf:info
          "Control aging of interface counters";
        container max {
          tailf:info
            "Maximum counter aging threshold";
          leaf age {
            tailf:info
              "Aging threshold";
            type uint8 {
              tailf:info
                "<0-60>;;Aging threshold value in seconds";
              range "0..60";
            }
          }
        }
      }
      container alignment {
        tailf:info
          "Control alignment correction and logging";
        leaf detection {
          tailf:info
            "Enable detection of alignment issues";
          tailf:cli-boolean-no;
          tailf:cli-full-command;
          type boolean;
          default "true";
        }
        leaf logging {
          tailf:info
            "Enable logging of alignment issues";
          tailf:cli-boolean-no;
          tailf:cli-full-command;
          type boolean;
          default "true";
        }
      }
      leaf call-home {
        tailf:info
          "Enable call-home service";
        tailf:cli-full-command;
        type empty;
      }
      leaf dhcp {
        tailf:info
          "Enable DHCP server and relay agent";
        tailf:cli-boolean-no;
        tailf:cli-full-command;
        type boolean;
        default "true";
      }
      leaf finger {
        tailf:info
          "Allow responses to finger requests";
        tailf:cli-full-command;
        type empty;
      }
      container heartbeat {
        tailf:info
          "Enable heartbeat processing";
        leaf fatal-count {
          tailf:info
            "Set heartbeat fatal count";
          type uint8 {
            tailf:info
              "<1-60>;;Number of timeouts until fatal error occurs";
            range "1..60";
          }
        }
        leaf interrupt-interval {
          tailf:info
            "Set heartbeat interrupt test interval";
          type uint8 {
            tailf:info
              "<0-60>;;Interval between interrupt level tests";
            range "0..60";
          }
        }
        leaf interrupt-max {
          tailf:info
            "Set maximum message count from interrupt test";
          type uint8 {
            tailf:info
              "<0-60>;;Maximum number of messages from interrupt test";
            range "0..60";
          }
        }
        leaf transmit-interval {
          tailf:info
            "Set heartbeat transmit interval";
          type uint8 {
            tailf:info
              "<1-30>;;Interval between heartbeat transmissions";
            range "1..30";
          }
        }
        leaf warning-timeout {
          tailf:info
            "Set heartbeat warning timeout interval";
          type uint8 {
            tailf:info
              "<5-60>;;Interval between heartbeat timeout warnings";
            range "5..60";
          }
        }
      }
      leaf hide-telnet-addresses {
        tailf:info
          "Hide destination addresses in telnet command";
        tailf:cli-full-command;
        type empty;
      }
      leaf unsupported-transceiver {
        tailf:info
          "";
        tailf:cli-full-command;
        type empty;
      }
      leaf internal {
        type empty;
      }
    }
    container cdp {
      tailf:ncs-device-type "cli-ned";
      tailf:display-when "not(../../ncs:module) or ../../ncs:module[ncs:name='tailf-ned-cisco-ios']";
      tailf:info
        "Global CDP configuration subcommands";
      leaf run {
        tailf:info
          "Enable CDP";
        tailf:cli-boolean-no;
        type boolean;
        default "true";
      }
    }
    list platform {
      tailf:ncs-device-type "cli-ned";
      tailf:display-when "not(../ncs:module) or ../ncs:module[ncs:name='tailf-ned-cisco-ios']";
      tailf:info
        "platform specific configuration";
      tailf:cli-suppress-mode;
      tailf:cli-delete-when-empty;
      ordered-by user;
      key "name";
      leaf name {
        tailf:cli-multi-word-key;
        type string {
          tailf:info
            "Full path to platform variable";
        }
      }
    }
    leaf hostname {
      tailf:ncs-device-type "cli-ned";
      tailf:display-when "not(../../ncs:module) or ../../ncs:module[ncs:name='tailf-ned-cisco-ios']";
      tailf:info
        "Set system's network name";
      type string {
        tailf:info
          "This system's network name";
      }
    }
    container vrf {
      tailf:ncs-device-type "cli-ned";
      tailf:display-when "not(../../ncs:module) or ../../ncs:module[ncs:name='tailf-ned-cisco-ios']";
      tailf:info
        "VRF commands";
      list definition {
        tailf:info
          "VRF definition mode";
        tailf:cli-full-command;
        tailf:cli-mode-name "config-vrf";
        key "name";
        leaf name {
          type string {
            tailf:info
              "WORD;;VRF name";
          }
        }
        leaf description {
          tailf:info
            "VRF specific description";
          tailf:cli-multi-value;
          tailf:cli-full-command;
          type string {
            tailf:info
              "LINE;;Up to 244 characters describing this VRF";
            length "1..244";
          }
        }
        leaf rd {
          tailf:info
            "Specify Route Distinguisher";
          tailf:cli-remove-before-change;
          tailf:cli-full-command;
          type rd-type;
        }
        container route-target {
          tailf:info
            "Specify Target VPN Extended Communities";
          uses vrf-route-target-grouping;
        }
        container address-family {
          tailf:info
            "Enter Address Family command mode";
          container ipv4 {
            tailf:info
              "Address family";
            tailf:cli-add-mode;
            tailf:cli-mode-name "config-vrf-af";
            tailf:cli-exit-command "exit-address-family";
            tailf:cli-full-command;
            presence "true";
            uses vrf-definition-af-grouping;
            container mdt {
              tailf:info
                "Backbone Multicast Distribution Tree";
              container default {
                tailf:info
                  "The default group";
                leaf address {
                  tailf:cli-drop-node-name;
                  tailf:cli-full-command;
                  tailf:cli-remove-before-change;
                  type inet:ipv4-address {
                    tailf:info
                      "A.B.C.D;;IP multicast group address";
                  }
                }
                container mpls {
                  tailf:info
                    "MPLS tunnel options";
                  leaf mldp {
                    tailf:info
                      "Use a MLDP LSP to create the default MDT";
                    type inet:ipv4-address {
                      tailf:info
                        "A.B.C.D;;MP2MP LSP root address";
                    }
                  }
                }
              }
              container data {
                tailf:info
                  "MDT data trees";
                list multicast {
                  tailf:cli-drop-node-name;
                  tailf:cli-suppress-mode;
                  tailf:cli-delete-when-empty;
                  key "address wildcard";
                  leaf address {
                    type inet:ipv4-address {
                      tailf:info
                        "A.B.C.D;;IP multicast group address";
                    }
                  }
                  leaf wildcard {
                    type inet:ipv4-address {
                      tailf:info
                        "A.B.C.D;;Wildcard bits";
                    }
                  }
                }
                leaf list {
                  tailf:info
                    "Access-list";
                  type ext-acl-type;
                }
                leaf threshold {
                  tailf:info
                    "MDT switching threshold";
                  type uint32 {
                    tailf:info
                      "<1-4294967>;;Traffic rate in kilobits per second";
                  }
                }
              }
              leaf log-reuse {
                tailf:info
                  "Event logging for data MDT reuse";
                type empty;
              }
              leaf-list preference {
                tailf:info
                  "MDT preference (default pim mldp)";
                tailf:cli-flat-list-syntax {
                  tailf:cli-replace-all;
                }
                type enumeration {
                  enum "mldp" {
                    tailf:info
                      "MDT preference mLDP";
                  }
                  enum "pim" {
                    tailf:info
                      "MDT preference PIM";
                  }
                }
              }
            }
          }
          container ipv6 {
            tailf:info
              "Address family";
            tailf:cli-add-mode;
            tailf:cli-mode-name "config-vrf-af";
            tailf:cli-exit-command "exit-address-family";
            tailf:cli-full-command;
            presence "true";
            uses vrf-definition-af-grouping;
          }
        }
      }
    }
    container security {
      tailf:ncs-device-type "cli-ned";
      tailf:display-when "not(../../ncs:module) or ../../ncs:module[ncs:name='tailf-ned-cisco-ios']";
      tailf:info
        "Infra Security CLIs";
      container passwords {
        tailf:info
          "Password security CLIs";
        leaf min-length {
          tailf:info
            "Minimum length of passwords";
          type uint8 {
            tailf:info
              "<0-16>;;Minimum length of all user/enable passwords";
            range "0..16";
          }
        }
      }
    }
    container enable {
      tailf:ncs-device-type "cli-ned";
      tailf:display-when "not(../../ncs:module) or ../../ncs:module[ncs:name='tailf-ned-cisco-ios']";
      tailf:info
        "Modify enable password parameters";
      container password {
        tailf:info
          "Assign the privileged level password (MAX of 25 characters)";
        tailf:cli-compact-syntax;
        tailf:cli-sequence-commands {
          tailf:cli-reset-siblings;
        }
        uses password-07-grouping;
        list level {
          tailf:info
            "Set exec level password";
          tailf:cli-suppress-mode;
          tailf:cli-delete-when-empty;
          tailf:cli-compact-syntax;
          tailf:cli-sequence-commands {
            tailf:cli-reset-siblings;
          }
          key "level";
          leaf level {
            type uint8 {
              tailf:info
                "<1-15>;;Level number";
            }
          }
          uses password-07-grouping;
        }
      }
      leaf last-resort {
        tailf:info
          "Define enable action if no TACACS servers respond";
        tailf:cli-full-command;
        type enumeration {
          enum "password" {
            tailf:info
              "Enable by giving the local enable password";
          }
          enum "succeed" {
            tailf:info
              "Enable without further question";
          }
        }
      }
      container secret {
        tailf:info
          "Assign the privileged level secret";
        tailf:cli-compact-syntax;
        tailf:cli-sequence-commands;
        leaf level {
          tailf:info
            "Set exec level password";
          tailf:cli-optional-in-sequence;
          type uint8 {
            tailf:info
              "<1-15>;;Level number";
          }
        }
        leaf type {
          tailf:cli-drop-node-name;
          tailf:cli-optional-in-sequence;
          type enumeration {
            enum "0" {
              tailf:info
                "Specifies an UNENCRYPTED password will follow";
            }
            enum "4";
            enum "5" {
              tailf:info
                "Specifies an ENCRYPTED secret will follow";
            }
          }
        }
        leaf secret {
          tailf:cli-drop-node-name;
          type string {
            tailf:info
              "LINE;;The UNENCRYPTED (cleartext) 'enable' secret";
          }
        }
      }
      leaf use-tacacs {
        tailf:info
          "Use TACACS to check enable passwords";
        tailf:cli-full-command;
        type empty;
      }
    }
    container aaa {
      tailf:ncs-device-type "cli-ned";
      tailf:display-when "not(../../ncs:module) or ../../ncs:module[ncs:name='tailf-ned-cisco-ios']";
      tailf:info
        "Authentication, Authorization and Accounting.";
      tailf:cli-incomplete-command;
      leaf new-model {
        tailf:info
          "Enable NEW access control commands and functions.(Disables OLD commands.)";
        type empty;
      }
      container group {
        tailf:info
          "AAA group definitions";
        tailf:cli-diff-dependency "../new-model" {
          tailf:xpath-root 3;
        }
        container server {
          tailf:info
            "AAA Server group definitions";
          list radius {
            tailf:info
              "Radius server-group definition";
            tailf:cli-mode-name "config-sg-radius";
            key "name";
            leaf name {
              type string {
                tailf:info
                  "WORD;;Server-group name";
              }
            }
            container server {
              tailf:info
                "Specify a RADIUS server";
              list name {
                tailf:info
                  "Name of radius server";
                tailf:cli-suppress-mode;
                key "name";
                leaf name {
                  type string;
                  tailf:non-strict-leafref {
                    path "/ncs:devices/ncs:device/ncs:config/ios:aaa/group/server/radius/name" {
                      tailf:xpath-root 3;
                    }
                  }
                }
              }
              list direct {
                tailf:cli-drop-node-name;
                tailf:cli-compact-syntax;
                tailf:cli-suppress-mode;
                key "name";
                leaf name {
                  tailf:cli-disallow-value "name";
                  type inet:host {
                    tailf:info
                      "Hostname or A.B.C.D;;IP address of RADIUS server";
                  }
                }
                leaf auth-port {
                  tailf:info
                    "UDP port for RADIUS authentication server (default is 1645)";
                  type uint16 {
                    tailf:info
                      "<0-65535>;;Port number";
                    range "0..65535";
                  }
                }
                leaf acct-port {
                  tailf:info
                    "UDP port for RADIUS accounting server (default is 1646)";
                  type uint16 {
                    tailf:info
                      "<0-65535>;;Port number";
                    range "0..65535";
                  }
                }
              }
            }
            container ip {
              tailf:info
                "Internet Protocol config commands";
              container radius {
                tailf:info
                  "RADIUS configuration commands";
                container source-interface {
                  tailf:info
                    "Specify interface for source address in RADIUS packets";
                  uses interface-name-grouping;
                }
              }
              container vrf {
                tailf:info
                  "Set VPN Routing Forwarding to use with the servers";
                leaf forwarding {
                  tailf:info
                    "Configure forwarding table";
                  tailf:cli-diff-dependency "/ios:ip/vrf" {
                    tailf:xpath-root 3;
                  }
                  tailf:cli-diff-dependency "/ios:vrf/definition" {
                    tailf:xpath-root 3;
                  }
                  type string {
                    tailf:info
                      "WORD;;Table name";
                  }
                }
              }
            }
          }
          list tacacsplus {
            tailf:alt-name "tacacs+";
            tailf:info
              "Tacacs+ server-group definition";
            tailf:cli-full-command;
            key "name";
            leaf name {
              type string {
                tailf:info
                  "WORD;;Server-group name";
              }
            }
            list server-private {
              tailf:info
                "Define a private TACACS server (per group)";
              tailf:cli-suppress-mode;
              tailf:cli-delete-when-empty;
              tailf:cli-compact-syntax;
              tailf:cli-sequence-commands;
              tailf:cli-reset-container;
              key "name";
              leaf name {
                type host-type {
                  tailf:info
                    "Hostname or A.B.C.D;;IP address of TACACS server";
                }
              }
              leaf timeout {
                tailf:info
                  "Time to wait for this TACACS server to reply (overrides default)";
                tailf:cli-optional-in-sequence;
                type uint16 {
                  tailf:info
                    "<1-1000>;;Timeout value in seconds to wait for server to reply";
                  range "1..1000";
                }
              }
              container key {
                tailf:info
                  "per-server encryption key (overrides default)";
                tailf:cli-flatten-container;
                tailf:cli-compact-syntax;
                tailf:cli-sequence-commands;
                leaf encryption {
                  tailf:cli-drop-node-name;
                  tailf:cli-incomplete-command;
                  tailf:cli-optional-in-sequence;
                  type enumeration {
                    enum "0" {
                      tailf:info
                        "Specifies an UNENCRYPTED key will follow";
                    }
                    enum "7" {
                      tailf:info
                        "Specifies HIDDEN key will follow";
                    }
                  }
                }
                leaf key {
                  tailf:cli-drop-node-name;
                  tailf:cli-full-command;
                  tailf:cli-multi-value;
                  type string {
                    tailf:info
                      "LINE;;The UNENCRYPTED (cleartext) shared key";
                  }
                }
              }
            }
            container ip {
              tailf:info
                "Internet Protocol config commands";
              container tacacs {
                tailf:info
                  "TACACS configuration commands";
                container source-interface {
                  tailf:info
                    "Specify interface for source address in TACACS packets";
                  uses interface-name-grouping;
                }
              }
            }
          }
        }
      }
      container authentication {
        tailf:info
          "Authentication configurations parameters.";
        tailf:cli-diff-dependency "../new-model" {
          tailf:xpath-root 3;
        }
        list dot1x {
          tailf:info
            "Set authentication lists for IEEE 802.1x.";
          tailf:cli-suppress-mode;
          tailf:cli-delete-when-empty;
          tailf:cli-compact-syntax;
          tailf:cli-incomplete-command;
          key "name";
          leaf name {
            type aaa-authentication-name-type;
          }
          leaf cache {
            tailf:info
              "Use Cached-group";
            type aaa-group-type;
          }
          leaf group {
            tailf:info
              "Use Server-group";
            type aaa-group-type;
          }
        }
        list login {
          tailf:info
            "Set authentication lists for logins.";
          tailf:cli-suppress-mode;
          tailf:cli-delete-when-empty;
          tailf:cli-compact-syntax;
          tailf:cli-incomplete-command;
          key "name";
          leaf name {
            type aaa-authentication-name-type;
          }
          uses aaa-authentication-method-grouping;
        }
        container enable {
          tailf:info
            "Set authentication list for enable.";
          container default {
            tailf:info
              "The default authentication list.";
            tailf:cli-compact-syntax;
            leaf cache {
              tailf:info
                "Use Cached-group";
              type aaa-group-type;
            }
            leaf group {
              tailf:info
                "Use Server-group";
              type aaa-group-type;
            }
            leaf line {
              tailf:info
                "Use line password for authentication.";
              type empty;
            }
            leaf enable {
              tailf:info
                "Use enable password for authentication.";
              type empty;
            }
            leaf none {
              tailf:info
                "No authentication.";
              tailf:cli-full-command;
              type empty;
            }
          }
        }
        list ppp {
          tailf:info
            "Set authentication lists for ppp.";
          tailf:cli-suppress-mode;
          tailf:cli-delete-when-empty;
          tailf:cli-compact-syntax;
          tailf:cli-incomplete-command;
          key "name";
          leaf name {
            type aaa-authentication-name-type;
          }
          uses aaa-authentication-method-grouping;
        }
      }
      container authorization {
        tailf:info
          "Authorization configurations parameters.";
        tailf:cli-incomplete-command;
        tailf:cli-diff-dependency "../new-model" {
          tailf:xpath-root 3;
        }
        leaf console {
          tailf:info
            "For enabling console authorization";
          type empty;
        }
        leaf config-commands {
          tailf:info
            "For configuration mode commands.";
          type empty;
        }
        list exec {
          tailf:info
            "For starting an exec (shell).";
          tailf:cli-suppress-mode;
          tailf:cli-delete-when-empty;
          tailf:cli-compact-syntax;
          tailf:cli-incomplete-command;
          key "name";
          leaf name {
            type aaa-authorization-name-type;
          }
          uses aaa-authorization-method-grouping;
        }
        list commands {
          tailf:info
            "For exec (shell) commands.";
          tailf:cli-suppress-mode;
          tailf:cli-delete-when-empty;
          tailf:cli-compact-syntax;
          tailf:cli-incomplete-command;
          key "level name";
          leaf level {
            type uint8 {
              tailf:info
                "<0-15>;;Enable level";
              range "0..15";
            }
          }
          leaf name {
            type aaa-authorization-name-type;
          }
          uses aaa-authorization-method-grouping;
        }
        list eventmanager {
          tailf:info
            "For starting an exec (shell).";
          tailf:cli-suppress-mode;
          tailf:cli-delete-when-empty;
          tailf:cli-compact-syntax;
          tailf:cli-incomplete-command;
          key "name";
          leaf name {
            type aaa-authorization-name-type;
          }
          uses aaa-authorization-method-grouping;
        }
        list network {
          tailf:info
            "For network services. (PPP, SLIP, ARAP)";
          tailf:cli-suppress-mode;
          tailf:cli-delete-when-empty;
          tailf:cli-compact-syntax;
          tailf:cli-incomplete-command;
          key "name";
          leaf name {
            type aaa-authorization-name-type;
          }
          uses aaa-authorization-method-grouping;
        }
      }
      container accounting {
        tailf:info
          "Accounting configurations parameters.";
        tailf:cli-incomplete-command;
        tailf:cli-diff-dependency "../new-model" {
          tailf:xpath-root 3;
        }
        list commands {
          tailf:info
            "For exec (shell) commands.";
          tailf:cli-suppress-mode;
          tailf:cli-delete-when-empty;
          tailf:cli-compact-syntax;
          tailf:cli-sequence-commands {
            tailf:cli-reset-siblings;
          }
          key "level name";
          leaf level {
            type uint8 {
              tailf:info
                "<0-15>;;Enable level";
              range "0..15";
            }
          }
          leaf name {
            type aaa-accounting-name-type;
          }
          uses aaa-accounting-method-grouping;
        }
        list exec {
          tailf:info
            "For starting an exec (shell).";
          tailf:cli-suppress-mode;
          tailf:cli-delete-when-empty;
          tailf:cli-compact-syntax;
          tailf:cli-sequence-commands {
            tailf:cli-reset-siblings;
          }
          key "name";
          leaf name {
            type aaa-accounting-name-type;
          }
          uses aaa-accounting-method-grouping;
        }
        list network {
          tailf:info
            "For network services. (PPP, SLIP, ARAP)";
          tailf:cli-suppress-mode;
          tailf:cli-delete-when-empty;
          tailf:cli-compact-syntax;
          tailf:cli-sequence-commands {
            tailf:cli-reset-siblings;
          }
          key "name";
          leaf name {
            type aaa-accounting-name-type;
          }
          uses aaa-accounting-method-grouping;
        }
        list connection {
          tailf:info
            "For outbound connections. (telnet, rlogin)";
          tailf:cli-suppress-mode;
          tailf:cli-delete-when-empty;
          tailf:cli-compact-syntax;
          tailf:cli-sequence-commands {
            tailf:cli-reset-siblings;
          }
          key "name";
          leaf name {
            type aaa-accounting-name-type;
          }
          uses aaa-accounting-method-grouping;
        }
        container system {
          tailf:info
            "For system events.";
          container default {
            tailf:cli-add-mode;
            tailf:cli-mode-name "cfg-acct-mlist";
            tailf:cli-delete-when-empty;
            presence "true";
            uses aaa-accounting-method-grouping;
          }
        }
        container suppress {
          tailf:info
            "Do not generate accounting records for a specific type of user.";
          leaf null-username {
            tailf:info
              "Do not generate accounting records for users with a null-username";
            type empty;
          }
        }
        container update {
          tailf:info
            "Enable accounting update records.";
          leaf periodic {
            tailf:info
              "Send accounting update records at regular intervals.";
            type uint32 {
              tailf:info
                "<1-71582>;;Periodic intervals to send accounting update records(in minutes)";
              range "1..71582";
            }
          }
        }
      }
      leaf session-id {
        tailf:info
          "AAA Session ID";
        tailf:cli-diff-dependency "../new-model" {
          tailf:xpath-root 3;
        }
        type enumeration {
          enum "common" {
            tailf:info
              "Common Session ID";
          }
          enum "unique" {
            tailf:info
              "Unique Session ID for different accounting types";
          }
        }
      }
      container attribute {
        tailf:info
          "AAA attribute definitions";
        list list {
          tailf:info
            "AAA attribute list definition";
          tailf:cli-mode-name "config-attr-list";
          key "name";
          leaf name {
            type string {
              tailf:info
                "WORD;;name";
            }
          }
          container attribute {
            tailf:info
              "Specify an AAA attribute";
            container type {
              tailf:info
                " Specify an AAA attribute type";
              leaf interface-config {
                tailf:info
                  "Configuration commands for an interface";
                type string {
                  tailf:info
                    "WORD;;string";
                }
              }
            }
          }
        }
      }
    }
    container clock {
      tailf:ncs-device-type "cli-ned";
      tailf:display-when "not(../../ncs:module) or ../../ncs:module[ncs:name='tailf-ned-cisco-ios']";
      tailf:info
        "Configure time-of-day clock";
      container timezone {
        tailf:info
          "Configure time zone";
        tailf:cli-compact-syntax;
        tailf:cli-sequence-commands {
          tailf:cli-reset-siblings;
        }
        leaf zone {
          tailf:cli-drop-node-name;
          tailf:cli-incomplete-command;
          type string {
            tailf:info
              "WORD;;name of time zone";
          }
        }
        leaf offset {
          tailf:cli-drop-node-name;
          tailf:cli-optional-in-sequence;
          tailf:cli-incomplete-command;
          type enumeration {
            enum "+";
            enum "-";
          }
        }
        leaf hours {
          tailf:cli-drop-node-name;
          type int8 {
            tailf:info
              "<-23 - 23>;;Hours offset from UTC";
            range "-23..23";
          }
        }
        leaf minutes {
          tailf:cli-drop-node-name;
          type int8 {
            tailf:info
              "<0-59>;;Minutes ofset from UTC";
            range "0..59";
          }
        }
      }
      container summer-time {
        tailf:info
          "Configure summer (daylight savings) time";
        tailf:cli-compact-syntax;
        tailf:cli-sequence-commands {
          tailf:cli-reset-siblings;
        }
        leaf zone {
          tailf:cli-drop-node-name;
          tailf:cli-incomplete-command;
          tailf:cli-disallow-value "date|recurring";
          type string {
            tailf:info
              "WORD;;name of time zone in summer";
          }
        }
        choice summer-choice {
          case date-case {
            leaf date {
              tailf:info
                "Configure absolute summer time";
              type empty;
            }
          }
          case recurring-case {
            leaf recurring {
              tailf:info
                "Configure recurring summer time";
              type empty;
            }
            leaf start {
              tailf:cli-drop-node-name;
              tailf:cli-incomplete-command;
              type union {
                type uint8 {
                  tailf:info
                    "<1-4>;;Week number to start";
                  range "1..4";
                }
                type enumeration {
                  enum "first" {
                    tailf:info
                      "First week of the month";
                  }
                  enum "last" {
                    tailf:info
                      "Last week of the month";
                  }
                }
              }
            }
            leaf start-day {
              tailf:cli-drop-node-name;
              tailf:cli-incomplete-command;
              type weekday-type {
                tailf:info
                  "DAY;;Weekday to start";
              }
            }
            leaf start-month {
              tailf:cli-drop-node-name;
              tailf:cli-incomplete-command;
              type month-type {
                tailf:info
                  "MONTH;;Month to start";
              }
            }
            leaf start-time {
              tailf:cli-drop-node-name;
              tailf:cli-incomplete-command;
              type hhmm-type {
                tailf:info
                  "hh:mm;;Time to start (hh:mm)";
              }
            }
            leaf end {
              tailf:cli-drop-node-name;
              tailf:cli-incomplete-command;
              type union {
                type uint8 {
                  tailf:info
                    "<1-4>;;Week number to end";
                  range "1..4";
                }
                type enumeration {
                  enum "first" {
                    tailf:info
                      "First week of the month";
                  }
                  enum "last" {
                    tailf:info
                      "Last week of the month";
                  }
                }
              }
            }
            leaf end-day {
              tailf:cli-drop-node-name;
              tailf:cli-incomplete-command;
              type weekday-type {
                tailf:info
                  "DAY;;Weekday to end";
              }
            }
            leaf end-month {
              tailf:cli-drop-node-name;
              tailf:cli-incomplete-command;
              type month-type {
                tailf:info
                  "MONTH;;Month to end";
              }
            }
            leaf end-time {
              tailf:cli-drop-node-name;
              type hhmm-type {
                tailf:info
                  "hh:mm;;Time to end (hh:mm)";
              }
            }
          }
        }
      }
      container calendar-valid {
        tailf:info
          "Calendar time is authoritative";
        presence "true";
      }
    }
    container facility-alarm {
      tailf:ncs-device-type "cli-ned";
      tailf:display-when "not(../../ncs:module) or ../../ncs:module[ncs:name='tailf-ned-cisco-ios']";
      tailf:info
        "Alarm thresholds configuration";
      container core-temperature {
        tailf:info
          "Threshold for processor module temperature";
        uses facility-alarm-grouping;
      }
      container outlet-temperature {
        tailf:info
          "Threshold for air outlet temperature";
        uses facility-alarm-grouping;
      }
      container intake-temperature {
        tailf:info
          "Threshold for air inlet temperature";
        uses facility-alarm-grouping;
      }
      container critical {
        tailf:info
          "Behavior on critical threshold exceed";
        leaf exceed-action {
          tailf:info
            "Behavior on critical threshold exceed";
          type enumeration {
            enum "shutdown" {
              tailf:info
                "Behavior on critical threshold exceed";
            }
          }
        }
      }
    }
    container cef {
      tailf:ncs-device-type "cli-ned";
      tailf:display-when "not(../../ncs:module) or ../../ncs:module[ncs:name='tailf-ned-cisco-ios']";
      tailf:info
        "Cisco Express Forwarding";
      container table {
        tailf:info
          "Set CEF forwarding table characteristics";
        container output-chain {
          tailf:info
            "Set table output chain characteristics";
          container build {
            tailf:info
              "Set table output chain building characteristics";
            leaf favor {
              tailf:info
                "Set which table output chain building characteristics to favor";
              type enumeration {
                enum "convergence-speed" {
                  tailf:info
                    "Favor faster convergence";
                }
                enum "memory-utilization" {
                  tailf:info
                    "Favor smaller memory utilization";
                }
              }
            }
          }
        }
      }
    }
    container ipdr {
      tailf:ncs-device-type "cli-ned";
      tailf:display-when "not(../../ncs:module) or ../../ncs:module[ncs:name='tailf-ned-cisco-ios']";
      tailf:info
        "IPDR Configuration";
      list session {
        tailf:info
          "IPDR session";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf session-name {
          tailf:cli-drop-node-name;
          tailf:cli-incomplete-command;
          type string {
            tailf:info
              "WORD;;IPDR session name";
          }
        }
        leaf session-descr {
          tailf:cli-drop-node-name;
          tailf:cli-multi-value;
          type string {
            tailf:info
              "LINE;;IPDR session description";
          }
        }
      }
      list type {
        tailf:info
          "IPDR session type";
        tailf:cli-suppress-mode;
        tailf:cli-delete-when-empty;
        tailf:cli-compact-syntax;
        tailf:cli-incomplete-command;
        key "session-id";
        leaf session-id {
          type uint8 {
            tailf:info
              "<1-255>;;IPDR session id";
            range "1..255";
          }
        }
        choice type-choice {
          leaf ad-hoc {
            tailf:info
              "Ad-hoc type session";
            type empty;
          }
          leaf event {
            tailf:info
              "Event type session";
            type empty;
          }
          leaf time-interval {
            tailf:info
              "Time interval type session";
            type uint16 {
              tailf:info
                "<15-1440>;;Interval in minute";
            }
          }
        }
      }
      list collector {
        tailf:info
          "IPDR collector";
        tailf:cli-suppress-mode;
        tailf:cli-delete-when-empty;
        tailf:cli-compact-syntax;
        tailf:cli-sequence-commands {
          tailf:cli-reset-siblings;
        }
        tailf:cli-incomplete-command;
        key "name";
        leaf name {
          type string {
            tailf:info
              "WORD;;IPDR collector name string";
          }
        }
        leaf ip-addr {
          tailf:cli-drop-node-name;
          type inet:ipv4-address {
            tailf:info
              "A.B.C.D;;IPDR collector ip address";
          }
        }
        leaf port {
          tailf:cli-drop-node-name;
          type uint16 {
            tailf:info
              "<1-65535>;;IPDR collector port";
            range "1..65535";
          }
        }
      }
      list associate {
        tailf:info
          "IPDR collector to session association";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf collector-name {
          tailf:cli-drop-node-name;
          tailf:cli-incomplete-command;
          type string {
            tailf:info
              "WORD;;IPDR collector name";
          }
        }
        leaf priority {
          tailf:cli-drop-node-name;
          type uint8 {
            tailf:info
              "<1-10>;;Priority of the collector in session, lower number is higher priority";
            range "1..10";
          }
        }
      }
      list template {
        tailf:info
          "IPDR template";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf template-name {
          tailf:cli-drop-node-name;
          type string {
            tailf:info
              "WORD;;Template name";
          }
        }
      }
      container exporter {
        tailf:info
          "IPDR exporter";
        leaf start {
          tailf:info
            "start IPDR exporter";
          type empty;
        }
      }
    }
    container card {
      tailf:ncs-device-type "cli-ned";
      tailf:display-when "not(../../ncs:module) or ../../ncs:module[ncs:name='tailf-ned-cisco-ios']";
      tailf:info
        "Configure card type";
      list card-slot {
        tailf:cli-drop-node-name;
        tailf:cli-suppress-mode;
        tailf:cli-delete-when-empty;
        tailf:cli-compact-syntax;
        key "slot card-type";
        leaf slot {
          type uint8 {
            tailf:info
              "<1-3>;;Enter odd slot";
            range "1|3";
          }
        }
        leaf card-type {
          type enumeration {
            enum "4jacket-1" {
              tailf:info
                "create a 4jacket-1 cardtype";
            }
          }
        }
      }
      list card-slot-subslot {
        tailf:cli-drop-node-name;
        tailf:cli-suppress-mode;
        tailf:cli-delete-when-empty;
        tailf:cli-compact-syntax;
        tailf:cli-sequence-commands {
          tailf:cli-reset-all-siblings;
        }
        key "slot-subslot card-type";
        leaf slot-subslot {
          type string {
            tailf:info
              "<1-8>/<0-3>;;Enter slot/subslot (subslot 2 and 3 is for SPA only)";
            pattern '[1-8]/[0-3]';
          }
        }
        leaf card-type {
          type enumeration {
            enum "24rfchannel-spa-1" {
              tailf:info
                "create a Wideband DOCSIS SPA";
            }
            enum "2cable-dtcc" {
              tailf:info
                "Utility Card w/DTI (EightBells)";
            }
            enum "2cable-tccplus" {
              tailf:info
                "Utility Card";
            }
            enum "SPA-1XTENGE-XFP-V2" {
              tailf:info
                "create a 10GE SPA 1 PORT cardtype";
            }
            enum "SPA-2X1GE-V2" {
              tailf:info
                "create a GE SPA 2 PORT cardtype";
            }
            enum "SPA-5X1GE-V2" {
              tailf:info
                "create a GE SPA 5 PORT cardtype";
            }
            enum "SPA-8X1GE-V2" {
              tailf:info
                "create a GE SPA 8 PORT cardtype";
            }
            enum "SPA-DOCSIS-HD-V1" {
              tailf:info
                "create a High Density DOCSIS SPA";
            }
            enum "ubr10k-clc-3g60" {
              tailf:info
                "create a uBR10000 line card with MC3Gx60";
            }
            enum "ubr10k-clc-mc2020v" {
              tailf:info
                "create a uBR10000 line card with MC20x20";
            }
          }
        }
        leaf SPA-DOCSIS-HD-V1-port {
          when "../card-type = 'SPA-DOCSIS-HD-V1'" {
            tailf:xpath-root 3;
          }
          tailf:cli-drop-node-name;
          type enumeration {
            enum "1x10GE" {
              tailf:info
                "using 1x10GE port";
            }
            enum "3x1GE" {
              tailf:info
                "using 3x1GE port";
            }
          }
        }
        leaf license {
          tailf:info
            "create a license for the line card";
          type string {
            tailf:info
              "WORD;;License string";
          }
        }
      }
      container type {
        tailf:info
          "Configure card type";
        list t1 {
          tailf:info
            "T1";
          tailf:cli-suppress-mode;
          tailf:cli-delete-when-empty;
          tailf:cli-compact-syntax;
          key "slot";
          leaf slot {
            type uint8;
          }
        }
        container t1-bay {
          tailf:cli-drop-node-name;
          list t1 {
            tailf:cli-suppress-mode;
            tailf:cli-delete-when-empty;
            tailf:cli-compact-syntax;
            key "slot bay";
            leaf slot {
              type uint8 {
                tailf:info
                  "<0-2>;;Card slot number (always 0 for 1800 series & 2801 routers)";
              }
            }
            leaf bay {
              type uint8 {
                tailf:info
                  "<0-3>;;WIC slot number (0:WIC, 1:Onboard for NM-HDV2)";
              }
            }
          }
        }
        list t3 {
          tailf:info
            "T3";
          tailf:cli-suppress-mode;
          tailf:cli-delete-when-empty;
          tailf:cli-compact-syntax;
          key "slot";
          leaf slot {
            type uint32;
          }
        }
      }
    }
    container hw-module {
      tailf:ncs-device-type "cli-ned";
      tailf:display-when "not(../../ncs:module) or ../../ncs:module[ncs:name='tailf-ned-cisco-ios']";
      tailf:info
        "Slot/subslot/port level commands";
      list bay {
        tailf:info
          "Bay level commands";
        tailf:cli-suppress-mode;
        tailf:cli-delete-when-empty;
        tailf:cli-compact-syntax;
        tailf:cli-sequence-commands {
          tailf:cli-reset-siblings;
        }
        tailf:cli-incomplete-command;
        key "name";
        leaf name {
          type string {
            tailf:info
              "WORD;;<1-3>/<0-3>";
          }
        }
        leaf shutdown {
          tailf:info
            "Shutdown the target subslot";
          type empty;
        }
        choice power-choice {
          leaf powered {
            tailf:info
              "Hold the target subslot in reset";
            type empty;
          }
          leaf unpowered {
            tailf:info
              "Power-off the target subslot";
            type empty;
          }
        }
      }
    }
    container cable {
      tailf:ncs-device-type "cli-ned";
      tailf:display-when "not(../../ncs:module) or ../../ncs:module[ncs:name='tailf-ned-cisco-ios']";
      tailf:info
        "Global cable configuration";
      container upstream {
        tailf:info
          "global upstream parameters";
        container rate-adapt {
          tailf:info
            "rate adapt";
          tailf:cli-compact-syntax;
          leaf priority {
            tailf:info
              "Configure priority to enable rate-adapt";
            type uint8 {
              tailf:info
                "<0-7>;;priority at or above enables rate-adapt.";
              range "0..7";
            }
          }
          leaf rate {
            tailf:info
              "Configure rate to enable rate-adapt";
            type uint32 {
              tailf:info
                "<0-30000000>;;rate at or above enables rate-adapt.";
              range "0..30000000";
            }
          }
          leaf local {
            tailf:info
              "Enable rate-adapt locally per upstream";
            type empty;
          }
        }
      }
      container admission-control {
        tailf:info
          "Configure Cable Admission Control";
        container preempt {
          tailf:info
            "Reason for preemption";
          leaf priority-voice {
            tailf:info
              "Priority Voice call can preempt normal";
            tailf:cli-show-no;
            type empty;
          }
        }
      }
      container flap-list {
        tailf:info
          "Cable flap-list configuration";
        leaf aging {
          tailf:info
            "Flap-list aging";
          type uint32 {
            tailf:info
              "<1-86400>;;Maximum number of minutes the cable modem is kept in the flap-list";
            range "1..86400";
          }
        }
      }
      container source-verify {
        tailf:info
          "Source verify";
        container leasequery-filter {
          tailf:info
            "Source verify Lease query filter";
          container downstream {
            tailf:info
              "Source verify Lease query filter for downstream pkts";
            tailf:cli-compact-syntax;
            tailf:cli-sequence-commands;
            leaf threshold {
              tailf:cli-drop-node-name;
              tailf:cli-incomplete-command;
              type uint8 {
                tailf:info
                  "<0-255>;;Number of lease queries for unknown sid";
                range "0..255";
              }
            }
            leaf interval {
              tailf:cli-drop-node-name;
              type uint8 {
                tailf:info
                  "<1-10>;;size of time window in seconds";
                range "1..10";
              }
            }
          }
        }
      }
      container modem {
        tailf:info
          "Modem polling using SNMP query";
        container remote-query {
          tailf:info
            "Modem polling using SNMP query";
          container gather {
            tailf:cli-drop-node-name;
            tailf:cli-compact-syntax;
            tailf:cli-sequence-commands;
            leaf polling-interval {
              tailf:cli-drop-node-name;
              tailf:cli-incomplete-command;
              type uint32 {
                tailf:info
                  "<1-86400>;;Periodic polling interval in seconds";
                range "1..86400";
              }
            }
            leaf community-string {
              tailf:cli-drop-node-name;
              type string {
                tailf:info
                  "WORD;;Community string ";
              }
            }
          }
          leaf src-ip {
            tailf:info
              "source IP address";
            type inet:ipv4-address {
              tailf:info
                "A.B.C.D;;Source IP addr";
            }
          }
        }
        leaf max-cpe {
          tailf:info
            "Max CPE override";
          type union {
            type uint8 {
              tailf:info
                "<1-255>;;Number";
            }
            type enumeration {
              enum "unlimited" {
                tailf:info
                  "Max CPE not enforced";
              }
            }
          }
        }
        leaf v6-max-cpe-prefix {
          tailf:info
            "Max CPE override";
          type uint16 {
            tailf:info
              "<0-1023>;;Number";
            range "0..1023";
          }
        }
        list vendor {
          tailf:info
            "Cable modem vendor information";
          tailf:cli-suppress-mode;
          tailf:cli-delete-when-empty;
          key "oui";
          leaf oui {
            type string {
              tailf:info
                "WORD;;OUI of the vendor in the format xx.xx.xx or xx:xx:xx";
            }
          }
          leaf vendor-name {
            tailf:cli-drop-node-name;
            type string {
              tailf:info
                "WORD;Vendor name";
            }
          }
        }
      }
      container modulation-profile {
        tailf:info
          "Modulation profile";
        list modulation-profile-list {
          tailf:cli-drop-node-name;
          tailf:cli-suppress-mode;
          tailf:cli-delete-when-empty;
          tailf:cli-incomplete-command;
          key "profile";
          leaf profile {
            type string {
              tailf:info
                "WORD;;Modulation Profile Group";
            }
          }
          container request {
            tailf:info
              "Request Burst";
            tailf:cli-compact-syntax;
            tailf:cli-sequence-commands {
              tailf:cli-reset-all-siblings;
            }
            uses cable-modulation-profile-grouping;
          }
          container initial {
            tailf:info
              "Initial Ranging Burst";
            tailf:cli-compact-syntax;
            tailf:cli-sequence-commands {
              tailf:cli-reset-all-siblings;
            }
            uses cable-modulation-profile-grouping;
          }
          container station {
            tailf:info
              "Station Ranging Burst";
            tailf:cli-compact-syntax;
            tailf:cli-sequence-commands {
              tailf:cli-reset-all-siblings;
            }
            uses cable-modulation-profile-grouping;
          }
          container short {
            tailf:info
              "Short Grant Burst";
            tailf:cli-compact-syntax;
            tailf:cli-sequence-commands {
              tailf:cli-reset-all-siblings;
            }
            uses cable-modulation-profile-grouping;
          }
          container long {
            tailf:info
              "Long Grant Burst";
            tailf:cli-compact-syntax;
            tailf:cli-sequence-commands {
              tailf:cli-reset-all-siblings;
            }
            uses cable-modulation-profile-grouping;
          }
          container a-short {
            tailf:info
              "Advanced Phy Short Grant Burst";
            tailf:cli-compact-syntax;
            tailf:cli-sequence-commands {
              tailf:cli-reset-all-siblings;
            }
            uses cable-modulation-profile-grouping;
          }
          container a-long {
            tailf:info
              "Advanced Phy Long Grant Burst";
            tailf:cli-compact-syntax;
            tailf:cli-sequence-commands {
              tailf:cli-reset-all-siblings;
            }
            uses cable-modulation-profile-grouping;
          }
          container a-ugs {
            tailf:info
              "Advanced Phy Unsolicited Grant Burst";
            tailf:cli-compact-syntax;
            tailf:cli-sequence-commands {
              tailf:cli-reset-all-siblings;
            }
            uses cable-modulation-profile-grouping;
          }
        }
      }
      list tag {
        tailf:info
          "cable tag";
        tailf:cli-mode-name "config-cmts-tag";
        key "id";
        leaf id {
          type uint16 {
            tailf:info
              "<1-1000>;;The id of the tag";
            range "1..1000";
          }
        }
        leaf name {
          tailf:info
            "Name of the tag";
          type string {
            tailf:info
              "WORD;;Globally unique name string of the tag";
          }
        }
        leaf docsis-version {
          tailf:info
            "Set the match rule for DOCSIS version";
          type enumeration {
            enum "docsis10" {
              tailf:info
                "Match docsis 1.0 modems";
            }
            enum "docsis11" {
              tailf:info
                "Match docsis 1.1 modems";
            }
            enum "docsis20" {
              tailf:info
                "Match docsis 2.0 modems";
            }
            enum "docsis30" {
              tailf:info
                "Match docsis 3.0 modems";
            }
          }
        }
        leaf service-class {
          tailf:info
            "Set the match rule for service class name";
          type string {
            tailf:info
              "WORD;;Service class name";
          }
        }
      }
      container service {
        tailf:info
          "Service flow/class setting";
        list class {
          tailf:info
            "Service class settings";
          tailf:cli-suppress-mode;
          tailf:cli-delete-when-empty;
          tailf:cli-incomplete-command;
          key "class-index";
          leaf class-index {
            type uint16 {
              tailf:info
                "<1-1023>;;Class Index";
              range "1..1023";
            }
          }
          leaf name {
            tailf:cli-full-command;
            type string {
              tailf:info
                "WORD;;The ascii string identifier for this Service Class";
            }
          }
          leaf downstream {
            tailf:info
              "Service Class is downstream";
            tailf:cli-full-command;
            type empty;
          }
          leaf upstream {
            tailf:info
              "Service Class is upstream";
            tailf:cli-full-command;
            type empty;
          }
          leaf peak-rate {
            tailf:info
              "Peak Rate within maximum traffic burst";
            type uint32 {
              tailf:info
                "<0-4294967295>;;Enter Peak Rate (bps";
            }
          }
          leaf max-concat-burst {
            tailf:info
              "Max Concat Burst";
            type uint16 {
              tailf:info
                "<0-65535>;;Enter Max Concat Burst (bytes)";
            }
          }
          container tos-overwrite {
            tailf:info
              "Overwrite TOS byte by setting mask bits to value";
            tailf:cli-compact-syntax;
            tailf:cli-sequence-commands;
            leaf and-mask {
              tailf:cli-drop-node-name;
              tailf:cli-incomplete-command;
              type string {
                tailf:info
                  "<0x0-0xFF>;,TOS-overwrite-mask-and byte in hex";
              }
            }
            leaf or-mask {
              tailf:cli-drop-node-name;
              type string {
                tailf:info
                  "<0x0-0xFF>;;TOS-overwrite-mask-or byte in hex";
              }
            }
          }
          leaf max-rate {
            tailf:info
              "Max Rate";
            type uint32 {
              tailf:info
                "<0-4294967295>;;Enter Max Rate (bps)";
            }
          }
          leaf max-burst {
            tailf:info
              "Max Tx Burst";
            type uint32 {
              tailf:info
                "<1522-4294967295>;;Enter Max Tx Burst (bytes)";
              range "1522..4294967295";
            }
          }
          leaf min-rate {
            tailf:info
              "Min Rate";
            type uint32 {
              tailf:info
                "<0-4294967295>;;Enter Min Resv Rate (bps)";
            }
          }
          leaf priority {
            tailf:info
              "Priority";
            type uint8 {
              tailf:info
                "<0-7>;;Enter Priority";
              range "0..7";
            }
          }
          leaf sched-type {
            tailf:info
              "Service Class Schedule Type";
            type enumeration {
              enum "2" {
                tailf:info
                  "Best Effort Schedule Type";
              }
              enum "3" {
                tailf:info
                  "Non Real-Time Polling Service Schedule Type";
              }
              enum "4" {
                tailf:info
                  "Real-Time Polling Service Schedule Type";
              }
              enum "5" {
                tailf:info
                  "Unsolicited Grant Service with Activity Detection Schedule Type";
              }
              enum "6" {
                tailf:info
                  "Unsolicited Grant Service Schedule Type";
              }
            }
          }
        }
        container attribute {
          tailf:info
            "Service attribute settings";
          container ds-bonded {
            tailf:info
              "Downstream Bonding Settings";
            container downstream-type {
              tailf:info
                "Bonding downstream-type settings";
              container bonding-enabled {
                tailf:info
                  "Channel Bonding only supported on Bonding-capable interfaces";
                tailf:cli-delete-when-empty;
                presence "true";
                leaf enforce {
                  tailf:info
                    "Enforce Bonding-capable interface selection";
                  type empty;
                }
              }
            }
          }
          container withhold-tlvs {
            tailf:info
              "Withhold D3.0 TLVs from pre-D3.0 modems";
            leaf peak-rate {
              tailf:info
                "Peak Traffic Rate TLV 24/25.27";
              type empty;
            }
          }
        }
      }
      container qos {
        tailf:info
          "Cable Quality of Service";
        container permission {
          tailf:info
            "Permission for Creating Cable Quality of Service Profile";
          leaf create {
            tailf:info
              "Allow create by management";
            tailf:cli-show-no;
            type empty;
          }
          leaf update {
            tailf:info
              "Allow update by management";
            tailf:cli-show-no;
            type empty;
          }
          leaf modems {
            tailf:info
              "Allow create by modems";
            tailf:cli-show-no;
            type empty;
          }
        }
      }
      container filter {
        tailf:info
          "CMTS packet filter settings";
        list group {
          tailf:info
            "CMTS packet filter group settings";
          tailf:cli-suppress-mode;
          tailf:cli-delete-when-empty;
          tailf:cli-compact-syntax;
          key "group-id";
          leaf group-id {
            type uint8 {
              tailf:info
                "<1-254>;;Group ID";
              range "1..254";
            }
          }
          list index {
            tailf:info
              "CMTS packet filter index settings";
            tailf:cli-suppress-mode;
            tailf:cli-delete-when-empty;
            key "index-num";
            leaf index-num {
              type uint8 {
                tailf:info
                  "<1-255>;;Filter Index";
              }
            }
            leaf src-ip {
              tailf:info
                "IP source address";
              type inet:ipv4-address {
                tailf:info
                  "A.B.C.D;;Enter IP source address";
              }
            }
            leaf src-mask {
              tailf:info
                "IP source address mask";
              type inet:ipv4-address {
                tailf:info
                  "A.B.C.D;;Enter IP source address mask";
              }
            }
            leaf dest-ip {
              tailf:info
                "IP destination address";
              type inet:ipv4-address {
                tailf:info
                  "A.B.C.D;;Enter IP destination address";
              }
            }
            leaf dest-mask {
              tailf:info
                "IP destination address mask";
              type inet:ipv4-address {
                tailf:info
                  "A.B.C.D;;Enter IP destination address mask";
              }
            }
            leaf v6-src-address {
              tailf:info
                "IPv6 source address";
              type inet:ipv6-address {
                tailf:info
                  " X:X:X:X::X;;Enter IPv6 source address";
              }
            }
            leaf v6-src-pfxlen {
              tailf:info
                "IPv6 source address prefix length";
              type uint8 {
                tailf:info
                  "<0-128>;;Enter Source Address Prefix Length";
                range "0..128";
              }
            }
            leaf v6-dest-address {
              tailf:info
                "IPv6 destination address";
              type inet:ipv6-address {
                tailf:info
                  " X:X:X:X::X;;Enter IPv6 destination address";
              }
            }
            leaf v6-dest-pfxlen {
              tailf:info
                "IPv6 destination address prefix length";
              type uint8 {
                tailf:info
                  "<0-128>;;Enter Destination Address Prefix Length";
                range "0..128";
              }
            }
            leaf v6-flow-label {
              tailf:info
                "IPv6 flow label";
              type uint32 {
                tailf:info
                  "<0-1048575>;;Enter IPv6 flow label";
                range "0..1048575";
              }
            }
            leaf ip-proto {
              tailf:info
                "IP protocol";
              type uint16 {
                tailf:info
                  "<0-256>;;Enter IP protocol type";
                range "0..256";
              }
            }
            container ip-tos {
              tailf:info
                "IP TOS byte settings";
              tailf:cli-compact-syntax;
              tailf:cli-sequence-commands;
              leaf tos-mask {
                tailf:cli-drop-node-name;
                tailf:cli-incomplete-command;
                type string {
                  tailf:info
                    "<0x0-0xFF>;;Enter mask against TOS value, byte in hex";
                }
              }
              leaf tos-value {
                tailf:cli-drop-node-name;
                type string {
                  tailf:info
                    "<0x0-0xFF>;;Enter TOS value, byte in hex";
                }
              }
            }
            leaf src-port {
              tailf:info
                "TCP/UDP source port";
              type uint16 {
                tailf:info
                  "<0-65535>;;Enter TCP/UDP Source Port";
              }
            }
            leaf dest-port {
              tailf:info
                "TCP/UDP destination port";
              type uint16 {
                tailf:info
                  "<0-65535>;;Enter TCP/UDP Destination Port";
              }
            }
            leaf ip-version {
              tailf:info
                "IP version of filter";
              type enumeration {
                enum "IPv4" {
                  tailf:info
                    "Filter is for IPv4 (default)";
                }
                enum "IPv6" {
                  tailf:info
                    "Filter is for IPv6";
                }
              }
              default "IPv4";
            }
            container tcp-flags {
              tailf:info
                "TCP flags settings";
              tailf:cli-compact-syntax;
              tailf:cli-sequence-commands;
              leaf flags-mask {
                tailf:cli-drop-node-name;
                tailf:cli-incomplete-command;
                type string {
                  tailf:info
                    "<0x0-0x3F;;Enter TCP Flags Mask in Hex";
                }
              }
              leaf flags-value {
                tailf:cli-drop-node-name;
                type string {
                  tailf:info
                    "<0x0-0x3F>;;Enter TCP Flags Value in Hex";
                }
              }
            }
            leaf match-action {
              tailf:info
                "Filter Match action processing";
              type enumeration {
                enum "accept" {
                  tailf:info
                    "Accept Packet on Match";
                }
                enum "drop" {
                  tailf:info
                    "Drop Packet on Match";
                }
              }
            }
            leaf status {
              tailf:info
                "Status of filter";
              type enumeration {
                enum "active" {
                  tailf:info
                    "Filter is active";
                }
                enum "inactive" {
                  tailf:info
                    "Filter is inactive";
                }
              }
              default "active";
            }
          }
        }
      }
      container submgmt {
        tailf:info
          "CMTS Subscriber Management Objects";
        container default {
          tailf:info
            "Defaults";
          container filter-group {
            tailf:info
              "Configure Filter Group";
            container cm {
              tailf:info
                "CM Group Defaults";
              uses cable-submgmt-default-filter-group-grouping;
            }
            container cpe {
              tailf:info
                "CPE Group Defaults";
              uses cable-submgmt-default-filter-group-grouping;
            }
            container mta {
              tailf:info
                "MTA Group Defaults";
              uses cable-submgmt-default-filter-group-grouping;
            }
            container stb {
              tailf:info
                "STB Group Defaults";
              uses cable-submgmt-default-filter-group-grouping;
            }
            container ps {
              tailf:info
                "PS Group Defaults";
              uses cable-submgmt-default-filter-group-grouping;
            }
          }
          leaf active {
            tailf:info
              "CPE Control for Subscriber Management Filtering";
            type empty;
          }
        }
      }
      container logging {
        tailf:info
          "Logs specific cable messages";
        container badipsource {
          tailf:info
            "cable BADIPSOURCE messages";
          tailf:cli-delete-when-empty;
          presence "true";
          leaf buffer-size {
            tailf:cli-drop-node-name;
            type uint32 {
              tailf:info
                "<4096-4121440>;;Buffer size";
            }
          }
        }
        container layer2events {
          tailf:info
            "cable layer 2 messages";
          tailf:cli-delete-when-empty;
          presence "true";
          leaf buffer-size {
            tailf:cli-drop-node-name;
            type uint32 {
              tailf:info
                "<4096-4121440>;;Buffer size";
            }
          }
        }
        container overlapip {
          tailf:info
            "cable OVERLAPIP messages";
          tailf:cli-delete-when-empty;
          presence "true";
          leaf buffer-size {
            tailf:cli-drop-node-name;
            type uint32 {
              tailf:info
                "<4096-4121440>;;Buffer size";
            }
          }
        }
        container ironbus {
          tailf:info
            "cable IRONBUS messages";
          tailf:cli-delete-when-empty;
          presence "true";
          leaf buffer-size {
            tailf:cli-drop-node-name;
            type uint32 {
              tailf:info
                "<4096-4121440>;;Buffer size";
            }
          }
        }
        container downstream-index {
          tailf:info
            "cable downstream index messages";
          tailf:cli-delete-when-empty;
          presence "true";
          leaf buffer-size {
            tailf:cli-drop-node-name;
            type uint32 {
              tailf:info
                "<4096-4121440>;;Buffer size";
            }
          }
        }
      }
      container default-tos-qos10 {
        tailf:info
          "Default DOCSIS 1.0 ToS Overwrite";
        container tos-overwrite {
          tailf:info
            "Overwrite ToS byte by setting mask bits to value";
          tailf:cli-compact-syntax;
          tailf:cli-sequence-commands;
          leaf tos-and {
            tailf:cli-drop-node-name;
            tailf:cli-incomplete-command;
            type string {
              tailf:info
                "<0x0-0xFF>;;ToS-overwrite-mask-and byte in hex";
            }
          }
          leaf tos-or {
            tailf:cli-drop-node-name;
            type string {
              tailf:info
                "<0x0-0xFF>;;ToS-overwrite-mask-or byte in hex";
            }
          }
        }
      }
      container primary-sflow-qos11 {
        tailf:info
          "Keep the primary service flows after CM in QoS DOCSIS11 mode offline";
        leaf keep {
          tailf:info
            "Keep the primary service flows after CM in QoS DOCSIS11 mode offline";
          type enumeration {
            enum "all" {
              tailf:info
                "Keep CLI and SNMP counters after CM in QoS DOCSIS11 mode offline";
            }
            enum "snmp-only" {
              tailf:info
                "Keep SNMP counters only after CM in QoS DOCSIS11 mode offline";
            }
          }
        }
      }
      container sflog {
        tailf:info
          "CMTS Service Flow Logging Configuration";
        tailf:cli-compact-syntax;
        tailf:cli-sequence-commands;
        leaf max-entry {
          tailf:info
            "Max. number of entries in service flow log.";
          tailf:cli-incomplete-command;
          type uint16 {
            tailf:info
              "<30000-59999>;;Max. number of entries in the service flow log.";
            range "30000..59999";
          }
        }
        leaf entry-duration {
          tailf:info
            "Service flow log entry duration in second";
          type uint32 {
            tailf:info
              "<3600-86400>;;Service flow log entry duration in second.";
            range "3600..86400";
          }
        }
      }
      container dynamic-secret {
        tailf:info
          "Cable dynamic secret";
        container exclude {
          tailf:info
            "Exclude single modem";
          leaf modem {
            tailf:info
              "Exclude single modem";
            type string {
              tailf:info
                "H.H.H;;MAC address of the modem to exclude";
            }
          }
          leaf oui {
            tailf:info
              "Exclude group of modems based on OUI";
            type string {
              tailf:info
                "WORD;;OUI to exclude";
            }
          }
        }
        container tftp {
          tailf:info
            "TFTP Proxy Options";
          leaf insert-upgrade-server {
            tailf:info
              "Automatically insert upgrade server TLV into the DOCSIS configuration file";
            type empty;
          }
        }
      }
      container docsis30-voice {
        tailf:info
          "Docsis 3.0 voice default configurations";
        container downstream {
          tailf:info
            "Downstream Service parameters";
          tailf:cli-compact-syntax;
          tailf:cli-sequence-commands;
          leaf req-attr-mask {
            tailf:info
              "SF Required Attribute Mask";
            tailf:cli-incomplete-command;
            type string {
              tailf:info
                "<0-FFFFFFFF>;;The attribute bitmap in hex";
            }
          }
          leaf forb-attr-mask {
            tailf:info
              "SF Forbidden Attribute Mask";
            type string {
              tailf:info
                "<0-FFFFFFFF>;;The attribute bitmap in hex";
            }
          }
        }
      }
      leaf util-interval {
        tailf:info
          "Set channel utilization interval";
        type uint32 {
          tailf:info
            "<1-86400>;;The time interval in seconds";
          range "1..86400";
        }
      }
      container clock {
        tailf:info
          "Clock card";
        leaf dti {
          tailf:info
            "set DTI clock reference mode";
          type empty;
        }
      }
      container bgsync {
        tailf:info
          "switch snmp sync state";
        leaf active {
          tailf:info
            "set background sync status";
          tailf:cli-boolean-no;
          tailf:cli-full-command;
          type boolean;
          default "true";
        }
        leaf ptime {
          tailf:info
            "set how long(unit second) a p packet sent";
          type uint32 {
            tailf:info
              "<5-86400>;;in second";
            range "5..86400";
          }
          default "5";
        }
        leaf itime {
          tailf:info
            "set how long(unit second) a i packet sent";
          type uint32 {
            tailf:info
              "<5-31536000>;;in second";
            range "5..31536000";
          }
          default "86400";
        }
      }
      container privacy {
        tailf:info
          "Cable Privacy";
        leaf encrypt-alg-priority {
          tailf:info
            "Encryption algorithm priority";
          type enumeration {
            enum "aes128-des40-des56" {
              tailf:info
                "Priority AES128, DES40, DES56";
            }
            enum "aes128-des56-des40" {
              tailf:info
                "Priority AES128, DES56, DES40";
            }
            enum "des40-aes128-des56" {
              tailf:info
                "Priority DES40, AES128, DES56";
            }
            enum "des40-des56-aes128" {
              tailf:info
                "Priority DES40, DES56, AES128";
            }
            enum "des56-aes128-des40" {
              tailf:info
                "Priority DES56, AES128, DES40";
            }
            enum "des56-des40-aes128" {
              tailf:info
                "Priority DES56, DES40, AES128";
            }
          }
        }
      }
      container dsg {
        tailf:info
          "Set DSG advance mode global parameters";
        list client-list {
          tailf:info
            "DSG client list settings";
          tailf:cli-suppress-mode;
          tailf:cli-delete-when-empty;
          tailf:cli-compact-syntax;
          tailf:cli-incomplete-command;
          key "client-list-id";
          leaf client-list-id {
            type uint16 {
              tailf:info
                "<1-65535>;;DSG client list ID";
              range "1..65535";
            }
          }
          list id-index {
            tailf:info
              "DSG Client ID settings";
            tailf:cli-suppress-mode;
            tailf:cli-delete-when-empty;
            tailf:cli-incomplete-command;
            key "id";
            leaf id {
              type uint16 {
                tailf:info
                  "<1-65535>;;DSG client ID index for the client list";
                range "1..65535";
              }
            }
            choice parameter-choice {
              leaf application-id {
                tailf:info
                  "DSG Client type Application ID";
                type string {
                  tailf:info
                    "<1-FFFF>;;Hex value of DSG Client type Application ID";
                }
              }
              leaf broadcast {
                tailf:info
                  "DSG Client type broadcast";
                type uint16 {
                  tailf:info
                    "<1--65535>;;DSG Broadcast client";
                  range "1..65535";
                }
              }
              leaf ca-system-id {
                tailf:info
                  "DSG Client type CA system ID";
                type string {
                  tailf:info
                    "<1-FFFF>;;Hex value of DSG Client type CA system ID";
                }
              }
              leaf mac-addr {
                tailf:info
                  "DSG Client type Mac address";
                type string {
                  tailf:info
                    "H.H.H;;DSG Client MAC address";
                }
              }
            }
          }
        }
        list tg {
          tailf:cli-suppress-mode;
          tailf:cli-delete-when-empty;
          key "group-id";
          leaf group-id {
            type uint16 {
              tailf:info
                "<1-65535>;;DSG Tunnel Group ID";
              range "1..65535";
            }
          }
          list channel {
            tailf:info
              "DSG Channel";
            tailf:cli-suppress-mode;
            tailf:cli-delete-when-empty;
            tailf:cli-compact-syntax;
            key "channel-id";
            leaf channel-id {
              type uint16 {
                tailf:info
                  "<1-65535>;;DSG Channel ID";
                range "1..65535";
              }
            }
            leaf priority {
              tailf:info
                "DSG Rule priority";
              type uint8 {
                tailf:info
                  "<0-255>;;DSG Rule priority";
              }
            }
            leaf status {
              tailf:cli-drop-node-name;
              type enumeration {
                enum "disable" {
                  tailf:info
                    "Disable DSG tunnel group";
                }
                enum "enable" {
                  tailf:info
                    "Enable DSG tunnel group";
                }
              }
              default "enable";
            }
          }
        }
        list tunnel {
          tailf:info
            "DSG tunnel";
          tailf:cli-suppress-mode;
          tailf:cli-delete-when-empty;
          tailf:cli-compact-syntax;
          tailf:cli-sequence-commands;
          key "tunnel-id";
          leaf tunnel-id {
            type uint16 {
              tailf:info
                "<1-65535>;;Tunnel id";
              range "1..65535";
            }
          }
          leaf mac-addr {
            tailf:info
              "destination MAC address";
            tailf:cli-incomplete-command;
            type string {
              tailf:info
                "H.H.H;;Multicast group MAC address";
            }
          }
          leaf tg {
            tailf:info
              "tunnel group id";
            tailf:cli-incomplete-command;
            type uint16 {
              tailf:info
                "<1-65535>;;tunnel group id";
              range "1..65535";
            }
          }
          leaf clients {
            tailf:info
              "DSG Clients";
            type uint16 {
              tailf:info
                "<1-65535>;;DSG Clients";
              range "1..65535";
            }
          }
          leaf status {
            tailf:cli-drop-node-name;
            type enumeration {
              enum "disable" {
                tailf:info
                  "disable tunnel";
              }
              enum "enable" {
                tailf:info
                  "enable tunnel";
              }
            }
            default "enable";
          }
        }
        list cfr {
          tailf:info
            "DSG classifier";
          tailf:cli-suppress-mode;
          tailf:cli-delete-when-empty;
          tailf:cli-compact-syntax;
          tailf:cli-sequence-commands;
          key "index";
          leaf index {
            type uint16 {
              tailf:info
                "<1-65535>;;Classifier index";
              range "1..65535";
            }
          }
          leaf dest-ip {
            tailf:info
              "destination IP address";
            type string {
              tailf:info
                "WORD;;Multicast group IP address or hostname";
            }
          }
          leaf tunnel {
            tailf:cli-break-sequence-commands;
            tailf:info
              "tunnel index";
            type uint16 {
              tailf:info
                "<1-65535>;;tunnel index";
              range "1..65535";
            }
          }
          leaf priority {
            tailf:info
              "Classifier priority";
            type uint8 {
              tailf:info
                "<0-255>;;Classifier priority";
            }
          }
          leaf src-ip {
            tailf:info
              "source IP address";
            type string {
              tailf:info
                "WORD;;source IP address or hostname";
            }
          }
          leaf in-dcd {
            tailf:info
              "classifier is included in DCD or not";
            type enumeration {
              enum "ignore" {
                tailf:info
                  "classifier is not included in DCD regardless of tunnel MAC address";
              }
              enum "no" {
                tailf:info
                  "classifier is not included in DCD";
              }
              enum "yes" {
                tailf:info
                  "classifier is included in DCD";
              }
            }
          }
        }
        list timer {
          tailf:info
            "DSG Timer settings";
          tailf:cli-suppress-mode;
          tailf:cli-delete-when-empty;
          tailf:cli-compact-syntax;
          key "index";
          leaf index {
            type uint16 {
              tailf:info
                "<1-65535>;;DSG Timer index";
              range "1..65535";
            }
          }
          leaf Tdsg1 {
            tailf:info
              "DSG Initialization Timeout (Tdsg1) setting";
            type uint16 {
              tailf:info
                "<1-65535>;;DSG Initialization Timeout (Tdsg1) value";
              range "1..65535";
            }
          }
          leaf Tdsg2 {
            tailf:info
              "DSG Operational Timeout (Tdsg2) setting";
            type uint16 {
              tailf:info
                "<1-65535>;;DSG Initialization Timeout (Tdsg2) value";
              range "1..65535";
            }
          }
          leaf Tdsg3 {
            tailf:info
              "DSG Two-Way Retry Timer (Tdsg3) setting";
            type uint16 {
              tailf:info
                "<0-65535>;;DSG Initialization Timeout (Tdsg3) value";
            }
          }
          leaf Tdsg4 {
            tailf:info
              "DSG One-Way Retry Timer (Tdsg4) setting";
            type uint16 {
              tailf:info
                "<0-65535>;;DSG Initialization Timeout (Tdsg4) value";
            }
          }
        }
      }
      container load-balance {
        tailf:info
          "DOCSIS load balancing";
        leaf docsis-enable {
          tailf:info
            "Enable docsis 2.0 load balancing";
          type empty;
        }
        leaf docsis30-enable {
          tailf:info
            "Enable docsis 3.0 load balancing";
          type empty;
        }
        container modem {
          tailf:info
            "Modem settings";
          leaf max-failures {
            tailf:info
              "Set the time of failed movements before modem is removed from dynamic LB";
            type uint8 {
              tailf:info
                "<0-100>;;Maximum failures before modem is removed from dynamic LB";
              range "0..100";
            }
          }
        }
        list rule {
          tailf:info
            "Enter docsis load balance rule";
          tailf:cli-suppress-mode;
          tailf:cli-delete-when-empty;
          tailf:cli-compact-syntax;
          tailf:cli-sequence-commands;
          tailf:cli-incomplete-command;
          key "rule-id";
          leaf rule-id {
            type uint32 {
              tailf:info
                "<1-4294967295>;;DOCSIS load balance rule ID";
              range "1..4294967295";
            }
          }
          choice status-choice {
            container ds {
              tailf:cli-drop-node-name;
              container disable-throughput-lowerbound {
                tailf:info
                  "load balance is disabled if CM throughput is lower than a threshold";
                leaf ds {
                  tailf:info
                    "Specify DS throughput lowerbound";
                  type uint32 {
                    tailf:info
                      "<0-1000000>;;Throughput lowerbound in kbps";
                    range "0..1000000";
                  }
                }
              }
            }
            container us {
              tailf:cli-drop-node-name;
              container disable-throughput-lowerbound {
                tailf:info
                  "load balance is disabled if CM throughput is lower than a threshold";
                leaf us {
                  tailf:info
                    "Specify US throughput lowerbound";
                  type uint32 {
                    tailf:info
                      "<0-1000000>;;Throughput lowerbound in kbps";
                    range "0..1000000";
                  }
                }
              }
            }
            leaf disabled {
              tailf:info
                "load balance is always disabled";
              type empty;
            }
            leaf enabled {
              tailf:info
                "load balance is always enabled";
              type empty;
            }
          }
        }
        list docsis-policy {
          tailf:info
            "Enter docsis load balance policy";
          tailf:cli-suppress-mode;
          tailf:cli-delete-when-empty;
          key "policy-id";
          leaf policy-id {
            type uint32 {
              tailf:info
                "<1-4294967295>;;DOCSIS load balance policy ID";
              range "1..4294967295";
            }
          }
          list rule {
            tailf:info
              "Enter docsis load balance rule";
            tailf:cli-suppress-mode;
            tailf:cli-delete-when-empty;
            key "rule-id";
            leaf rule-id {
              type uint32 {
                tailf:info
                  "<1-4294967295>;;DOCSIS load balance rule ID";
              }
            }
          }
          leaf tag {
            tailf:info
              "Tag name";
            type string {
              tailf:info
                "WORD;;Tag name";
            }
          }
          leaf override {
            tailf:info
              "Override the default";
            type empty;
          }
        }
        container d30-ggrp-default {
          tailf:info
            "Set DOCSIS 3.0 general group default value";
          leaf disable {
            tailf:info
              "Set disable DOCSIS GGRP as default";
            type empty;
          }
          leaf init-tech-list {
            tailf:info
              "Set DOCSIS GGRP DCC/DBC init tech as default";
            type string {
              tailf:info
                "<grouplist>;;Set DCC/DBC Initialization technique list as default";
            }
          }
          leaf docsis-policy {
            tailf:info
              "Set DOCSIS GGRP policy ID as default";
            type uint32 {
              tailf:info
                "<0-4294967295>;;Set DOCSIS load balance policy ID as default";
            }
          }
        }
        container docsis-group {
          tailf:info
            "DOCSIS group";
          list FN {
            tailf:cli-mode-name "config-lb-group";
            key "fn-id";
            leaf fn-id {
              type uint16 {
                tailf:info
                  "<1-256>;;cable fiber-node ID";
                range "1..256";
              }
            }
            container MD {
              tailf:info
                "Enter MAC-domain interface";
              tailf:cli-hide-in-submode;
              tailf:cli-flatten-container;
              leaf Cable {
                tailf:info
                  "Cable;;CMTS interface";
                tailf:cli-allow-join-with-value {
                  tailf:cli-display-joined;
                }
                tailf:cli-hide-in-submode;
                type string {
                  pattern '[0-9]+.*';
                }
                tailf:non-strict-leafref {
                  path "/ncs:devices/ncs:device/ncs:config/ios:interface/Cable/name" {
                    tailf:xpath-root 3;
                  }
                }
              }
            }
            uses cable-load-balance-docsis-group-grouping;
          }
          list docsis-group-list {
            tailf:cli-drop-node-name;
            tailf:cli-mode-name "config-lb-group";
            key "docsis-group-id";
            leaf docsis-group-id {
              type uint32 {
                tailf:info
                  "<1-2147483647>;;DOCSIS load balance group number";
                range "1..2147483647";
              }
            }
            uses cable-load-balance-docsis-group-grouping;
          }
        }
        container exclude {
          tailf:info
            "Exclude modems from load balancing";
          list oui {
            tailf:cli-suppress-mode;
            tailf:cli-delete-when-empty;
            tailf:cli-compact-syntax;
            tailf:cli-reset-container;
            key "word";
            leaf word {
              type string {
                tailf:info
                  "WORD;;OUI of exclude modem in the formatxx.xx.xx or xx:xx:xx";
              }
            }
            leaf assignment {
              tailf:info
                "Exclude modem at assigning phase";
              tailf:cli-full-command;
              type empty;
            }
            leaf enforce {
              tailf:info
                "Exclude only for enforced load balancing";
              tailf:cli-full-command;
              type empty;
            }
            leaf static {
              tailf:info
                "Exclude only for static load balancing";
              type empty;
            }
            leaf strict {
              tailf:info
                "Exclude all forms of load balancing";
              tailf:cli-full-command;
              type empty;
            }
          }
        }
      }
      container metering {
        tailf:info
          "CMTS Metering Configuration";
        choice cable-metering-choice {
          container destination {
            tailf:info
              "Cable Metering Collector IP address";
            tailf:cli-compact-syntax;
            tailf:cli-sequence-commands {
              tailf:cli-reset-siblings;
            }
            leaf ip-address {
              tailf:cli-drop-node-name;
              tailf:cli-incomplete-command;
              tailf:cli-remove-before-change;
              type inet:ipv4-address {
                tailf:info
                  "A.B.C.D;;Enter IP address of primary";
              }
            }
            leaf port {
              tailf:cli-drop-node-name;
              tailf:cli-incomplete-command;
              type uint16 {
                tailf:info
                  "<1-65535>;;Enter Port Number of primary";
                range "1..65535";
              }
            }
            leaf ip-address2 {
              tailf:cli-drop-node-name;
              tailf:cli-optional-in-sequence;
              tailf:cli-incomplete-command;
              type inet:ipv4-address {
                tailf:info
                  "A.B.C.D;;Enter IP address of secondary";
              }
            }
            leaf port2 {
              when '../ip-address2' {
                tailf:xpath-root 3;
              }
              tailf:cli-drop-node-name;
              tailf:cli-incomplete-command;
              type uint16 {
                tailf:info
                  "<1-65535>;;Enter Port Number of secondary";
                range "1..65535";
              }
            }
            leaf retries {
              tailf:cli-drop-node-name;
              tailf:cli-incomplete-command;
              type uint8 {
                tailf:info
                  "<0-5>;;Enter number of retries ";
                range "0..5";
              }
            }
            leaf minutes {
              tailf:cli-drop-node-name;
              tailf:cli-incomplete-command;
              type uint16 {
                tailf:info
                  "<2-1440>;;Enter metering data collection interval in minutes";
                range "2..1440";
              }
            }
            leaf security {
              tailf:cli-drop-node-name;
              type enumeration {
                enum "non-secure" {
                  tailf:info
                    "Non secure streaming";
                }
                enum "secure" {
                  tailf:info
                    "Secure streaming";
                }
              }
            }
            leaf flow-aggregate {
              tailf:cli-break-sequence-commands;
              tailf:info
                "Only aggregate service flow information";
              type empty;
            }
            leaf cpe-list-suppress {
              tailf:info
                "Suppress cpe information";
              type empty;
            }
            leaf full-records {
              tailf:info
                "Full service flow (active and idle) records";
              type empty;
            }
          }
          container ipdr-d3 {
            tailf:info
              "Cable Metering Exporter through IPDR D3.0";
            container session {
              tailf:info
                "IPDR D3 session";
              tailf:cli-compact-syntax;
              tailf:cli-sequence-commands {
                tailf:cli-reset-siblings;
              }
              leaf session-id {
                tailf:cli-drop-node-name;
                tailf:cli-incomplete-command;
                type uint8 {
                  tailf:info
                    "<1-255>;;Enter metering ipdr D3 session id";
                  range "1..255";
                }
              }
              leaf type {
                tailf:info
                  "IPDR D3 Service Definition Type of Metering";
                type uint8 {
                  tailf:info
                    "<1-2>;;Enter metering IPDR D3 Service Definition Type";
                  range "1..2";
                }
              }
              leaf flow-aggregate {
                tailf:info
                  "Only aggregate service flow information";
                tailf:cli-optional-in-sequence;
                type empty;
              }
              leaf full-records {
                tailf:info
                  "Full service flow (active and idle) records";
                type empty;
              }
            }
          }
        }
        container source-interface {
          tailf:info
            "source-interface for the billing packets";
          uses interface-name-grouping;
        }
        container data-per-session {
          tailf:info
            "Number of flows per session";
          tailf:cli-compact-syntax;
          tailf:cli-sequence-commands;
          leaf data-per-session {
            tailf:cli-drop-node-name;
            type uint8 {
              tailf:info
                "<3-30>;;Enter # of data flows per session";
              range "3..30";
            }
          }
          leaf timer {
            tailf:info
              "CLC timer to wake up ";
            type uint16 {
              tailf:info
                "<8-500>;;Enter timer wake up interval in msec";
              range "8..500";
            }
          }
        }
      }
      container rf-change-trigger {
        tailf:info
          "NP RF status change trigger";
        tailf:cli-compact-syntax;
        leaf percent {
          tailf:info
            "% of CM report NP RF status change";
          type uint8 {
            tailf:info
              "<1-100>;;% of CM report NP RF status change";
            range "1..100";
          }
        }
        leaf count {
          tailf:info
            "#of CM report NP RF status change";
          type uint16 {
            tailf:info
              "<1-65535>;;#of CM report NP RF status change";
            range "1..65535";
          }
        }
        leaf secondary {
          tailf:info
            "move secondary service flows";
          type empty;
        }
      }
      container throttle-modem {
        tailf:info
          "Manage CM initialization/registration throttling on large systems";
        tailf:cli-compact-syntax;
        tailf:cli-sequence-commands {
          tailf:cli-reset-siblings;
        }
        leaf init-rate {
          tailf:info
            "Maximum number of modems pass the initialization step per second";
          tailf:cli-incomplete-command;
          type uint16 {
            tailf:info
              "<1-1000>;;Default value is 32 CM/Sec";
            range "1..1000";
          }
        }
        leaf holdoff-time {
          tailf:info
            "Maximum number of seconds a modem waiting in throttling queue";
          tailf:cli-incomplete-command;
          type uint8 {
            tailf:info
              "<5-100>;;Default value is 45 Seconds";
            range "5..100";
          }
        }
        leaf flush-rate {
          tailf:info
            "Maximum number of modems flushing from throttling queue once holdoff time is expired";
          type uint16 {
            tailf:info
              "<100-1000>;;Default value is 300 CM/Sec";
            range "100..1000";
          }
        }
      }
      container ds-max-burst {
        tailf:info
          "Enable maximum traffic burst";
        tailf:cli-delete-when-empty;
        presence "true";
        choice optional {
          leaf burst-threshold {
            tailf:info
              "Threshold to enable maximum traffic burst";
            type uint32 {
              tailf:info
                "<64-1000000>;;Burst Threshold in Kbytes (default = 1000)";
              range "64..1000000";
            }
            default "1000";
          }
          leaf peak-rate {
            tailf:info
              "Peak rate within the maximum traffic burst";
            type uint32 {
              tailf:info
                "<0-1000000>;;Peak Rate in Kbps (default is unshaped)";
              range "0..1000000";
            }
          }
        }
      }
      container acfe {
        tailf:info
          "Configure Fairness across DOCSIS interfaces";
        leaf enable {
          tailf:info
            "Enable Fairness across DOCSIS interfaces (Adaptive CIR Fair EIR)";
          type empty;
        }
      }
      container l2-vpn-service {
        tailf:info
          "Use Layer-2 Tunnels for CPE traffic behind certain CMs";
        container xconnect {
          tailf:info
            "Tunnel traffic to L2VPN circuit";
          container nsi {
            tailf:info
              "Network System Interface";
            container dot1q {
              tailf:info
                "Tunnel traffic to DOT1Q L2VPN";
              tailf:cli-display-separated;
              presence "true";
              container interface {
                tailf:info
                  "Default Ethernet NSI interface";
                uses interface-name-grouping;
              }
            }
            container mpls {
              tailf:info
                "Tunnel traffic to ATOM/MPLS PW";
              presence "true";
            }
          }
        }
      }
      list dot1q-vc-map {
        tailf:info
          "Map a CM to an Ethernet VLAN";
        tailf:cli-suppress-mode;
        tailf:cli-delete-when-empty;
        tailf:cli-compact-syntax;
        tailf:cli-sequence-commands;
        tailf:cli-incomplete-command;
        key "mac-address";
        leaf mac-address {
          type string {
            tailf:info
              "H.H.H;;Modem MAC address";
          }
        }
        container ethernet-interface {
          tailf:cli-drop-node-name;
          tailf:cli-flatten-container;
          tailf:cli-compact-syntax;
          tailf:cli-incomplete-command;
          uses interface-name-grouping;
        }
        leaf vlan-id {
          tailf:cli-drop-node-name;
          type uint16 {
            tailf:info
              "<2-4095>;;IEEE 802.1Q VLAN ID";
            range "2..4095";
          }
        }
        leaf cust-name {
          tailf:cli-drop-node-name;
          type string {
            tailf:info
              "WORD;;Customer Name";
          }
        }
      }
      list l2vpn {
        tailf:info
          "Cable Modem Ethernet L2VPN Service";
        tailf:cli-mode-name "config-l2vpn";
        tailf:cli-sequence-commands;
        key "mac-address";
        leaf mac-address {
          type string {
            tailf:info
              "H.H.H;;Modem MAC address";
          }
        }
        leaf customer-name {
          tailf:cli-drop-node-name;
          tailf:cli-hide-in-submode;
          type string {
            tailf:info
              "WORD;;Customer Name";
          }
        }
        container service {
          tailf:cli-break-sequence-commands;
          tailf:info
            "Ethernet service";
          list instance {
            tailf:info
              "Ethernet service Instance";
            tailf:cli-mode-name "config-ethsrv";
            tailf:cli-sequence-commands;
            tailf:cli-incomplete-command;
            max-elements 1;
            key "id";
            leaf id {
              type uint16 {
                tailf:info
                  "<1-8000>;;Ethernet service Instance id";
              }
            }
            leaf ethernet {
              tailf:info
                "Service Type  - Ethernet";
              tailf:cli-hide-in-submode;
              tailf:cli-full-command;
              type empty;
            }
            uses interface-xconnect-grouping;
            container cable {
              tailf:info
                "Cable Specific commands";
              container set {
                tailf:info
                  "Set parameters";
                leaf mpls-experimental {
                  tailf:info
                    "Set MPLS Pseudo-wire Experimental bits";
                  type uint8 {
                    tailf:info
                      "<0-7>;;MPLS Experimental Bits Value";
                  }
                }
              }
            }
          }
        }
      }
      container wideband {
        tailf:info
          "Wideband Configuration";
        leaf auto-reset {
          tailf:info
            "Reset WCMs reg'd traditional-DOCSIS";
          type empty;
        }
      }
      list rcc-template {
        tailf:info
          "Create Cable RCC-Template";
        tailf:cli-mode-name "config-rcc-template";
        key "index";
        leaf index {
          type uint8 {
            tailf:info
              "<1-255>;;cable rcc-template id";
            range "1..255";
          }
        }
        leaf rcp-id {
          tailf:info
            "Receive Channel Profile ID";
          tailf:cli-multi-value;
          tailf:cli-full-command;
          type string {
            tailf:info
              "<0x0-0xFF>;;RCP ID in hex";
          }
        }
        list receive-module {
          tailf:info
            "Receive Module entry";
          tailf:cli-suppress-mode;
          tailf:cli-delete-when-empty;
          tailf:cli-compact-syntax;
          tailf:cli-sequence-commands;
          tailf:cli-incomplete-command;
          key "index";
          leaf index {
            type uint8 {
              tailf:info
                "<1-10>;;Receive Module index";
              range "1..10";
            }
          }
          leaf first-center-frequency {
            tailf:info
              "Module Center frequency";
            type uint32 {
              tailf:info
                "<55000000-1050000000>;;Center Frequency - Hz";
              range "55000000..1050000000";
            }
          }
          leaf connected-receive-module {
            tailf:info
              "Receive Modules";
            type uint8 {
              tailf:info
                "<1-10>;;Connected Receive Module index";
              range "1..10";
            }
          }
        }
        list receive-channel {
          tailf:info
            "Receive Channel entry";
          tailf:cli-suppress-mode;
          tailf:cli-delete-when-empty;
          tailf:cli-compact-syntax;
          tailf:cli-sequence-commands;
          tailf:cli-incomplete-command;
          key "index";
          leaf index {
            type uint8 {
              tailf:info
                "<1-24>;;Receive Channel index";
              range "1..24";
            }
          }
          leaf center-frequency {
            tailf:info
              "Channel Center frequency";
            tailf:cli-incomplete-command;
            type uint32 {
              tailf:info
                "<55000000-1050000000>;;Center Frequency - Hz";
              range "55000000..1050000000";
            }
          }
          leaf connected-receive-module {
            tailf:info
              "Receive Modules";
            type uint8 {
              tailf:info
                "<1-10>;;Connected Receive Module index";
              range "1..10";
            }
          }
          leaf primary {
            tailf:info
              "Receive Channel Primary indicator";
            type empty;
          }
        }
      }
      list fiber-node {
        tailf:info
          "Create Cable fiber-node";
        tailf:cli-mode-name "config-fiber-node";
        key "fiber-node-id";
        leaf fiber-node-id {
          type uint16 {
            tailf:info
              "<1-256>;;cable fiber-node id";
            range "1..256";
          }
        }
        leaf description {
          tailf:info
            "Fiber node name/description";
          tailf:cli-multi-value;
          tailf:cli-full-command;
          type string {
            tailf:info
              "LINE;;Description of this fiber node that will be truncated to 80 characters.";
          }
        }
        container downstream {
          tailf:info
            "Cable downstream channel";
          tailf:cli-compact-syntax;
          tailf:cli-sequence-commands;
          choice downstream-choice {
            leaf Modular-Cable {
              tailf:info
                "Modular cable";
              tailf:cli-incomplete-command;
              type string {
                tailf:info
                  "<slot>/<card>/<port>;;Enter slot/subslot/port";
              }
            }
            leaf Cable {
              tailf:info
                "CMTS interface";
              tailf:cli-incomplete-command;
              type string {
                tailf:info
                  "<slot>/<card>/<port>;;Enter slot/subslot/port";
              }
            }
          }
          leaf rf-channel {
            tailf:info
              "RF channel";
            type string {
              tailf:info
                "<grouplist>;;List of port numbers and number ranges";
            }
          }
        }
        container upstream {
          tailf:info
            "Cable upstream channel";
          tailf:cli-compact-syntax;
          tailf:cli-sequence-commands;
          leaf Cable {
            type string {
              tailf:info
                "<5-8>/<0-1>;;Enter slot/subslot numbers";
            }
          }
          leaf connector {
            tailf:info
              "Physical upstream port connector on LC";
            type string {
              tailf:info
                "<grouplist>;;List of port numbers and number ranges";
            }
          }
        }
      }
      container ipv6 {
        tailf:info
          "Configure CMTS-wide IPv6 commands";
        container pd-route {
          tailf:info
            "Configure PD enclosing route";
          tailf:cli-compact-syntax;
          tailf:cli-sequence-commands;
          leaf prefix {
            tailf:cli-drop-node-name;
            tailf:cli-incomplete-command;
            type ios:ipv6-prefix {
              tailf:info
                "X:X:X:X::X/<0-128>;;IPv6 prefix";
            }
          }
          leaf Bundle {
            tailf:info
              "Virtual Bundle";
            tailf:cli-allow-join-with-value {
              tailf:cli-display-joined;
            }
            type uint8 {
              tailf:info
                "<1-255>;;Bundle interface number";
              range "1..255";
            }
          }
        }
        container source-verify {
          tailf:info
            "IPv6 Source verify";
          container leasequery-filter {
            tailf:info
              "Source verify Lease query filter";
            container downstream {
              tailf:info
                "Source verify IPv6 Lease query filter for downstream pkts";
              tailf:cli-compact-syntax;
              tailf:cli-sequence-commands;
              leaf threshold {
                tailf:cli-drop-node-name;
                tailf:cli-incomplete-command;
                type uint8 {
                  tailf:info
                    "<0-255>;;Number of ipv6 lease queries for unknown sid";
                  range "0..255";
                }
              }
              leaf interval {
                tailf:cli-drop-node-name;
                type uint8 {
                  tailf:info
                    "<1-10>;;size of time window in seconds";
                  range "1..10";
                }
              }
            }
          }
        }
      }
    }
    list l2tp-class {
      tailf:ncs-device-type "cli-ned";
      tailf:display-when "not(../ncs:module) or ../ncs:module[ncs:name='tailf-ned-cisco-ios']";
      tailf:info
        "l2tp-class configuration";
      tailf:cli-mode-name "config-l2tp-class";
      key "l2tp-class-name";
      leaf l2tp-class-name {
        type string {
          tailf:info
            "WORD;;l2tp-class name";
        }
      }
      leaf hello {
        tailf:info
          "Set HELLO message interval";
        type uint16 {
          tailf:info
            "<0-1000>;;Seconds, default is 60";
          range "0..1000";
        }
        default "60";
      }
      container retransmit {
        tailf:info
          "Control message retransmission parameters";
        leaf retries {
          tailf:info
            "Number of retries before tearing down a control connection";
          type uint16 {
            tailf:info
              "<5-1000>;;Maximum retransmissions";
            range "5..1000";
          }
        }
        container timeout {
          tailf:info
            "Control packet retransmission timeout parameters";
          choice timeout-choice {
            leaf max {
              tailf:info
                "Maximum timeout";
              type uint8 {
                tailf:info
                  "<1-8>;;Seconds";
                range "1..8";
              }
            }
            leaf min {
              tailf:info
                "Minimum timeout";
              type uint8 {
                tailf:info
                  "<1-8>;;Seconds";
                range "1..8";
              }
            }
          }
        }
      }
    }
    container packetcable {
      tailf:ncs-device-type "cli-ned";
      tailf:display-when "not(../../ncs:module) or ../../ncs:module[ncs:name='tailf-ned-cisco-ios']";
      tailf:info
        "Global packetcable configuration";
      tailf:cli-display-separated;
      presence "true";
      leaf multimedia {
        tailf:info
          "Enable Packetcable Multimedia functionality";
        type empty;
      }
    }
    list depi-class {
      tailf:ncs-device-type "cli-ned";
      tailf:display-when "not(../ncs:module) or ../ncs:module[ncs:name='tailf-ned-cisco-ios']";
      tailf:info
        "depi-class configuration";
      tailf:cli-mode-name "config-depi-class";
      key "depi-class-name";
      leaf depi-class-name {
        type string {
          tailf:info
            "WORD;;depi-class name";
        }
      }
      container mode {
        tailf:info
          "Set DEPI Mode";
        leaf mpt {
          tailf:info
            "MPT Mode";
          type empty;
        }
      }
    }
    list depi-tunnel {
      tailf:ncs-device-type "cli-ned";
      tailf:display-when "not(../ncs:module) or ../ncs:module[ncs:name='tailf-ned-cisco-ios']";
      tailf:info
        "depi-tunnel configuration";
      tailf:cli-mode-name "config-depi-tunnel";
      key "depi-tunnel-name";
      leaf depi-tunnel-name {
        type string {
          tailf:info
            "WORD;depi-tunnel name";
        }
      }
      leaf dest-ip {
        tailf:info
          "Set Destination IP address of Tunnel";
        type inet:ipv4-address {
          tailf:info
            "A.B.C.D;;Peer IP address";
        }
      }
      leaf l2tp-class {
        tailf:info
          "Set l2tp-class to associate depi tunnel with";
        type string {
          tailf:info
            "WORD;;L2TP class with which this depi-tunnel is associated";
        }
      }
      leaf depi-class {
        tailf:info
          "Set depi-class to associate depi tunnel with";
        type string {
          tailf:info
            "WORD;;depi-class with which this depi-tunnel is associated";
        }
      }
      leaf protect-tunnel {
        tailf:info
          "Specify protect depi-tunnel";
        type string {
          tailf:info
            "WORD;;protect depi-tunnel with which this depi-tunnel is associated";
        }
      }
    }
    list chat-script {
      tailf:ncs-device-type "cli-ned";
      tailf:display-when "not(../ncs:module) or ../ncs:module[ncs:name='tailf-ned-cisco-ios']";
      tailf:info
        "Define a modem chat script";
      tailf:cli-suppress-mode;
      tailf:cli-delete-when-empty;
      key "name";
      leaf name {
        type string {
          tailf:info
            "WORD;;Name of chat script";
        }
      }
      leaf line {
        tailf:cli-drop-node-name;
        tailf:cli-multi-value;
        tailf:cli-full-command;
        type string {
          tailf:info
            "LINE;;Chat script in form EXPECT SEND EXPECT SEND ...";
        }
      }
    }
    container autonomic {
      tailf:ncs-device-type "cli-ned";
      tailf:display-when "not(../../ncs:module) or ../../ncs:module[ncs:name='tailf-ned-cisco-ios']";
      tailf:info
        "Autonomic Networking";
      container registrar {
        tailf:info
          "Registrar";
        tailf:cli-add-mode;
        tailf:cli-mode-name "config-registrar";
        leaf domain-id {
          tailf:info
            "Autonomic Domain ID";
          type string {
            tailf:info
              "WORD;;Autonomic Domain ID in string format";
          }
        }
        container CA {
          tailf:info
            "Create a Certificate Authority";
          leaf local {
            tailf:info
              "Create local Certificate Authority";
            type empty;
          }
        }
      }
    }
    container controller {
      tailf:ncs-device-type "cli-ned";
      tailf:display-when "not(../../ncs:module) or ../../ncs:module[ncs:name='tailf-ned-cisco-ios']";
      tailf:info
        "Configure controller";
      list controller-tx-ex-list {
        tailf:cli-mode-name "config-controller";
        tailf:cli-drop-node-name;
        key "name number";
        leaf name {
          type enumeration {
            tailf:info
              "Controller name";
            enum "T1" {
              tailf:info
                "T1 controller";
            }
            enum "E1" {
              tailf:info
                "E1 controller";
            }
            enum "T3" {
              tailf:info
                "T3 controller";
            }
          }
        }
        leaf number {
          type string {
            tailf:info
              "WORD;;slot/subslot or port[/:]port";
          }
        }
        leaf framing {
          tailf:info
            "Specify the type of Framing on a DS1 link";
          tailf:cli-full-command;
          type string;
        }
        container clock {
          tailf:info
            "Specify the clock source for a DS1 link";
          container source {
            tailf:info
              "Specify the clock source for a DS1 link";
            choice source-choice {
              container line {
                tailf:info
                  "Recovered Clock";
                tailf:cli-delete-when-empty;
                presence "true";
                leaf line-mode {
                  tailf:cli-drop-node-name;
                  tailf:cli-full-command;
                  type enumeration {
                    enum "primary" {
                      tailf:info
                        "Primary Source";
                    }
                    enum "secondary";
                    enum "bits" {
                      tailf:info
                        "Bits Clocking";
                    }
                    enum "independent" {
                      tailf:info
                        "Independent Source";
                    }
                  }
                }
              }
              leaf internal {
                tailf:info
                  "Internal Clock";
                tailf:cli-full-command;
                type empty;
              }
              leaf loop-timed {
                tailf:cli-full-command;
                type empty;
              }
              leaf free-running {
                tailf:info
                  "Free Running Clock";
                tailf:cli-full-command;
                type empty;
              }
            }
          }
        }
        leaf linecode {
          tailf:info
            "Specify the line encoding method for a DS1 link";
          tailf:cli-full-command;
          type enumeration {
            enum "ami" {
              tailf:info
                "AMI encoding";
            }
            enum "b8zs" {
              tailf:info
                "B8ZS encoding";
            }
            enum "hdb3";
          }
        }
        container cablelength {
          tailf:info
            "Specify the cable length for a DS1 link";
          choice cablelength-choice {
            leaf value {
              tailf:cli-drop-node-name;
              tailf:cli-full-command;
              type uint32;
            }
            leaf long {
              tailf:info
                "long cable";
              tailf:cli-full-command;
              type string;
            }
            leaf short {
              tailf:info
                "short cable";
              tailf:cli-full-command;
              type string;
            }
          }
        }
        container pri-group {
          tailf:info
            "Configure the specified timeslots for PRI";
          list timeslots {
            tailf:info
              "List of timeslots in the pri-group";
            tailf:cli-compact-syntax;
            tailf:cli-suppress-mode;
            tailf:cli-delete-when-empty;
            tailf:cli-range-list-syntax;
            key "id";
            leaf id {
              type uint8;
            }
            leaf nfas_d {
              tailf:info
                "Specify the operation of the D-channel timeslot.";
              type enumeration {
                enum "primary";
                enum "backup";
                enum "none";
              }
            }
            leaf nfas_int {
              when '../nfas_d' {
                tailf:xpath-root 3;
              }
              tailf:info
                "Specify the provisioned NFAS interface value.";
              type uint32 {
                tailf:info
                  "<0-48>;;The NFAS interface value.";
              }
            }
            leaf nfas_group {
              when '../nfas_int' {
                tailf:xpath-root 3;
              }
              tailf:info
                "Specify the NFAS group.";
              type uint8 {
                range "1..24";
              }
            }
            leaf service {
              tailf:info
                "Specify the service type";
              type enumeration {
                enum "mgcp" {
                  tailf:info
                    "Media Gateway Control Protocol service";
                }
              }
            }
          }
        }
        list channel-group {
          tailf:info
            "Specify the timeslots to channel-group mapping for an interface";
          tailf:cli-suppress-mode;
          tailf:cli-delete-when-empty;
          key "number";
          leaf number {
            type uint8 {
              range "0..30";
            }
          }
          leaf-list timeslots {
            tailf:cli-replace-all;
            tailf:cli-range-list-syntax;
            type uint16;
          }
        }
        leaf description {
          tailf:info
            "Controller specific description";
          tailf:cli-multi-value;
          tailf:cli-full-command;
          type string {
            tailf:info
              "LINE;;Up to 80 characters describing this interface";
          }
        }
        list t1 {
          tailf:cli-suppress-mode;
          tailf:cli-delete-when-empty;
          tailf:cli-compact-syntax;
          key "id";
          leaf id {
            type uint8;
          }
          leaf channel-group {
            type uint8 {
              range "0..23";
            }
          }
          leaf-list timeslots {
            tailf:cli-range-list-syntax;
            type uint8 {
              range "1..24";
            }
          }
          leaf speed {
            type enumeration {
              enum "56";
              enum "64";
            }
          }
        }
        leaf shutdown {
          tailf:info
            "Shut down a DS1 link (send Blue Alarm)";
          type empty;
        }
      }
      container BITS {
        tailf:info
          "Configure BITS Interface";
        container input {
          tailf:info
            "Configure BITS input";
          container applique {
            tailf:info
              "Link type E1 or T1";
            container E1 {
              tailf:info
                "E1;;Link type E1";
              tailf:cli-compact-syntax;
              tailf:cli-sequence-commands;
              choice E1-choice {
                case clock-case {
                  leaf clock-if {
                    tailf:cli-drop-node-name;
                    type enumeration {
                      enum "2048KHz" {
                        tailf:info
                          "2048 KHz clock interface";
                      }
                    }
                  }
                }
                case framing-case {
                  leaf framing {
                    tailf:info
                      "BITS framing options for E1";
                    tailf:cli-incomplete-command;
                    type enumeration {
                      enum "fas_crc4" {
                        tailf:info
                          "FASCRC4";
                      }
                      enum "fas_nocrc" {
                        tailf:info
                          "FAS";
                      }
                      enum "mfas_crc4" {
                        tailf:info
                          "MFASCRC4";
                      }
                      enum "mfas_nocrc" {
                        tailf:info
                          "MFAS";
                      }
                    }
                  }
                  leaf linecode {
                    tailf:info
                      "BITS linecode options for E1";
                    type enumeration {
                      enum "ami" {
                        tailf:info
                          "AMI encoding";
                      }
                      enum "hdb3" {
                        tailf:info
                          "HDB3 encoding";
                      }
                    }
                  }
                }
              }
            }
          }
        }
      }
      list Cellular {
        tailf:info
          "3G/4G WWAN Cellular controller";
        tailf:cli-mode-name "config-controller";
        key "id";
        leaf id {
          type uint32 {
            tailf:info
              "<0-0>;;Controller unit number";
            range "0";
          }
        }
        leaf description {
          tailf:info
            "Controller specific description";
          tailf:cli-multi-value;
          type string {
            tailf:info
              "LINE;;Up to 80 characters describing this interface";
            length "1..80";
          }
        }
        container lte {
          tailf:info
            "LTE type carrier";
          container gps {
            tailf:info
              "GPS configuration";
            leaf enable {
              tailf:info
                "enable GPS feature";
              type empty;
            }
            container mode {
              tailf:info
                "select GPS mode";
              leaf standalone {
                tailf:info
                  "select Standalone mode";
                type empty;
              }
            }
            container nmea {
              tailf:info
                "enable NMEA data";
              choice nmea-choice {
                container ip {
                  tailf:info
                    "NMEA over IP interface";
                  presence "true";
                }
                container serial {
                  tailf:info
                    "NMEA over serial interface";
                  presence "true";
                  leaf streaming {
                    tailf:cli-drop-node-name;
                    type enumeration {
                      enum "38400" {
                        tailf:info
                          "38400 bps, 8 databits, No parity, 1 stopbit";
                      }
                      enum "4800" {
                        tailf:info
                          "4800 bps, 8 databits, No parity, 1 stopbit (default)";
                      }
                      enum "line-config" {
                        tailf:info
                          "Use tty line configuration";
                      }
                    }
                  }
                }
              }
            }
          }
          container modem {
            tailf:info
              "Modem logging configuration";
            container link-recovery {
              tailf:info
                "Cellular Link Recovery";
              leaf enable {
                type empty;
              }
              container rssi {
                tailf:info
                  "RSSI Onset Threshold value";
                leaf onset-threshold {
                  tailf:info
                    "RSSI Onset Threshold";
                  type int8 {
                    tailf:info
                      "<-125 - -90>;;RSSI value in -dbm";
                    range "-125..-90";
                  }
                }
              }
              leaf monitor-timer {
                tailf:info
                  "Monitor Timer";
                type uint8 {
                  tailf:info
                    "<20 - 60>;;Monitor Timer value in seconds";
                  range "20..60";
                }
              }
              leaf wait-timer {
                tailf:info
                  "Wait Timer";
                type uint8 {
                  tailf:info
                    "<5 - 60>;;Wait Timer value in seconds";
                  range "5..60";
                }
              }
              leaf debounce-count {
                tailf:info
                  "Debounce Count";
                type uint8 {
                  tailf:info
                    "<6 - 20>;;Debounce Count value";
                  range "6..20";
                }
              }
            }
          }
        }
      }
      list Modular-Cable {
        tailf:info
          "Modular-Cable controller";
        tailf:cli-mode-name "config-controller";
        key "name";
        leaf name {
          type string {
            tailf:info
              "WORD;;Controller slot/subslot/unit";
          }
        }
        leaf ip-address {
          tailf:info
            "Configure IP address";
          type inet:ipv4-address {
            tailf:info
              "A.B.C.D;;IP address of Blaze";
          }
        }
        container modular-host {
          tailf:info
            "Configure modular host";
          leaf subslot {
            tailf:info
              "Configure slot";
            tailf:cli-remove-before-change;
            type string {
              tailf:info
                "WORD;;slot/subslot";
            }
          }
        }
        list rf-channel {
          tailf:info
            "RF channel configuration";
          tailf:cli-suppress-mode;
          tailf:cli-delete-when-empty;
          key "rf-port";
          leaf rf-port {
            type uint8 {
              tailf:info
                "<0-23>;;RF channel number";
              range "0..23";
            }
          }
          leaf description {
            tailf:info
              "configure RF channel name/description";
            tailf:cli-multi-value;
            tailf:cli-full-command;
            type string {
              tailf:info
                "LINE;;Description of this RF channel that will be truncated to 80 characters";
            }
          }
          container cable {
            tailf:info
              "configure RF channel cable downstream channel-id";
            container downstream {
              tailf:info
                "configure RF channel cable downstream channel-id";
              leaf channel-id {
                tailf:info
                  "configure RF channel cable downstream channel-id";
                type uint8 {
                  tailf:info
                    "<1-255>;;RF channel cable downstream channel-id";
                  range "1..255";
                }
              }
            }
          }
          container frequency {
            tailf:info
              "configure RF channel frequency in Hz";
            tailf:cli-compact-syntax;
            tailf:cli-sequence-commands {
              tailf:cli-reset-siblings;
            }
            leaf freq {
              tailf:cli-drop-node-name;
              type uint32 {
                tailf:info
                  "<55000000-1050000000>;;Frequency in Hz";
                range "55000000..1050000000";
              }
            }
            leaf annex {
              tailf:info
                "ITU-T J.83 MPEG standard";
              tailf:cli-incomplete-command;
              type enumeration {
                enum "A" {
                  tailf:info
                    "Annex A, European Standard";
                }
                enum "B" {
                  tailf:info
                    "Annex B, North American Standard";
                }
              }
            }
            leaf modulation {
              tailf:info
                "configure RF channel modulation type";
              type enumeration {
                enum "256qam" {
                  tailf:info
                    "256-QAM modulation";
                }
                enum "64qam" {
                  tailf:info
                    "64-QAM modulation";
                }
              }
            }
            leaf interleave-depth {
              tailf:info
                "Interleave depth";
              type enumeration {
                enum "128" {
                  tailf:info
                    "R/S Interleave I=128, J=1";
                }
                enum "16" {
                  tailf:info
                    "R/S Interleave I=16, J=8";
                }
                enum "32" {
                  tailf:info
                    "R/S Interleave I=32, J=4";
                }
                enum "64" {
                  tailf:info
                    "R/S Interleave I=64, J=2";
                }
                enum "8" {
                  tailf:info
                    "R/S Interleave I=8, J=16";
                }
                enum "12" {
                  tailf:info
                    "R/S Interleave I=12, J=17";
                }
              }
            }
          }
          container ip-address {
            tailf:info
              "configure IP address of edge QAM";
            tailf:cli-compact-syntax;
            tailf:cli-sequence-commands {
              tailf:cli-reset-siblings;
            }
            leaf ip-address {
              tailf:cli-drop-node-name;
              tailf:cli-incomplete-command;
              type inet:ipv4-address {
                tailf:info
                  "A.B.C.D;;IP address of edge QAM";
              }
            }
            leaf mac-address {
              tailf:info
                "MAC address of edge QAM";
              tailf:cli-incomplete-command;
              type string {
                tailf:info
                  "H.H.H;;MAC address of edge QAM";
              }
            }
            leaf depi-remote-id {
              tailf:info
                "configure DEPI session ID for edge QAM";
              type uint32 {
                tailf:info
                  "<1-4294967295>;;DEPI remote ID";
                range "1..4294967295";
              }
            }
            leaf eqam-headroom {
              tailf:info
                "Headroom for Edge QAM channel";
              type uint8 {
                tailf:info
                  "<0-28>;;EdgeQAM Headroom";
                range "0..28";
              }
            }
          }
          container depi-tunnel {
            tailf:info
              "DEPI Data Session Configuration";
            tailf:cli-compact-syntax;
            tailf:cli-sequence-commands {
              tailf:cli-reset-siblings;
            }
            leaf depi-tunnel-name {
              tailf:cli-drop-node-name;
              tailf:cli-incomplete-command;
              type string {
                tailf:info
                  "WORD;;depi-tunnel name";
              }
            }
            leaf tsid {
              tailf:info
                "tsid ";
              type uint16 {
                tailf:info
                  "<0-65535>;;tsid value";
              }
            }
          }
          leaf rf-power {
            tailf:info
              "Set RF Power";
            type string {
              tailf:info
                "<1-100>;;dBmV (The format is XY.Z; by default, .Z is .0)";
            }
          }
          leaf rf-shutdown {
            tailf:cli-boolean-no;
            tailf:cli-full-command;
            type boolean;
            default "true";
          }
        }
      }
      list wanphy {
        tailf:info
          "WANPHY controller";
        tailf:cli-mode-name "config-controller";
        key "name";
        leaf name {
          type string {
            tailf:info
              "WORD;;Controller slot/subslot/unit";
          }
        }
      }
    }
    container ip {
      tailf:ncs-device-type "cli-ned";
      tailf:display-when "not(../../ncs:module) or ../../ncs:module[ncs:name='tailf-ned-cisco-ios']";
      tailf:info
        "Global IP configuration subcommands";
      leaf subnet-zero {
        tailf:info
          "Allow 'subnet zero' subnets";
        tailf:cli-boolean-no;
        tailf:cli-full-command;
        type boolean;
        default "true";
      }
      leaf source-route {
        tailf:info
          "Process packets with source routing header options";
        tailf:cli-boolean-no;
        tailf:cli-show-with-default;
        tailf:cli-full-command;
        type boolean;
        default "true";
      }
      leaf routing {
        tailf:info
          "Enable IP routing";
        tailf:cli-boolean-no;
        tailf:cli-full-command;
        tailf:cli-diff-dependency "../../router" {
          tailf:xpath-root 3;
          tailf:cli-trigger-on-set;
        }
        tailf:callpoint ip-routing-hook {
          tailf:set-hook node;
        }
        type boolean;
        default "true";
      }
      container arp {
        tailf:info
          "IP ARP global configuration";
        container proxy {
          tailf:info
            "Global proxy ARP configuration";
          leaf disable {
            tailf:info
              "Disable proxy ARP on all interfaces";
            tailf:cli-full-command;
            type empty;
          }
        }
        container inspection {
          tailf:info
            "Arp Inspection configuration";
          leaf-list bridge-domain {
            tailf:info
              "Enable/Disable ARP Inspection on bridge-domains";
            tailf:cli-range-list-syntax;
            type uint16 {
              tailf:info
                "WORD;;bridge-domain range, example: 1,3-5,7,9-11";
              range "1..4094";
            }
          }
          container bridge-domain-list {
            tailf:cli-drop-node-name;
            list bridge-domain {
              tailf:info
                "Enable/Disable ARP Inspection on bridge-domains";
              tailf:cli-suppress-mode;
              tailf:cli-delete-when-empty;
              tailf:cli-compact-syntax;
              tailf:cli-incomplete-command;
              key "id";
              leaf id {
                type uint16 {
                  tailf:info
                    "WORD;;bridge-domain range, example: 1,3-5,7,9-11";
                  range "1..4094";
                }
              }
              container logging {
                tailf:cli-flatten-container;
                choice logging-choice {
                  leaf acl-match {
                    tailf:info
                      "Logging of packets that match ACLs";
                    type enumeration {
                      enum "matchlog" {
                        tailf:info
                          "Log packets on ACE logging configuration";
                      }
                      enum "none" {
                        tailf:info
                          "Do not log packets that match ACLs";
                      }
                    }
                  }
                  leaf dhcp-bindings {
                    tailf:info
                      "Logging of packet that match DHCP bindings";
                    type enumeration {
                      enum "all" {
                        tailf:info
                          "Log all packets that match DHCP bindings";
                      }
                      enum "none" {
                        tailf:info
                          "Do not log packets that match DHCP bindings";
                      }
                      enum "permit" {
                        tailf:info
                          "Log DHCP Binding Permitted packets";
                      }
                    }
                  }
                }
              }
            }
          }
          leaf-list validate {
            tailf:info
              "Validate addresses";
            tailf:cli-flat-list-syntax {
              tailf:cli-replace-all;
            }
            type enumeration {
              enum "src-mac" {
                tailf:info
                  "Validate source MAC address";
              }
              enum "dst-mac" {
                tailf:info
                  "Validate destination MAC address";
              }
              enum "ip" {
                tailf:info
                  "Validate IP addresses";
              }
            }
          }
          container log-buffer {
            tailf:info
              "Log Buffer Configuration";
            leaf entries {
              tailf:info
                "Number of entries for log buffer";
              type uint16 {
                tailf:info
                  "<0-1024>;;Number of entries for log buffer";
                range "0..1024";
              }
            }
            container logs {
              tailf:info
                "Number of logs per interval";
              tailf:cli-compact-syntax;
              tailf:cli-sequence-commands;
              leaf number {
                tailf:cli-drop-node-name;
                tailf:cli-incomplete-command;
                type uint16 {
                  tailf:info
                    "<0-1024>;;Number of entries";
                  range "0..1024";
                }
              }
              leaf interval {
                tailf:info
                  "Interval for controlling logging rate";
                type uint32 {
                  tailf:info
                    "<0-86400>;;Interval (seconds)";
                }
              }
            }
          }
        }
      }
      choice gratuitous-arps-choice {
        container gratuitous-arps-conf {
          tailf:cli-drop-node-name;
          leaf gratuitous-arps {
            tailf:info
              "Generate gratuitous ARPs for PPP/SLIP peer addresses";
            tailf:cli-boolean-no;
            tailf:cli-full-command;
            type boolean;
          }
        }
        container gratuitous-arps {
          tailf:cli-incomplete-command;
          tailf:cli-incomplete-no;
          leaf non-local {
            tailf:info
              "Send only non-local PPP/SLIP gratuitous ARPs (default)";
            tailf:cli-boolean-no;
            tailf:cli-full-command;
            type boolean;
            default "true";
          }
        }
        default "gratuitous-arps";
      }
      container cef-conf {
        tailf:cli-drop-node-name;
        leaf cef {
          tailf:info
            "Cisco Express Forwarding";
          tailf:cli-show-no;
          type empty;
        }
      }
      container cef {
        tailf:info
          "Cisco Express Forwarding";
        tailf:cli-incomplete-no;
        tailf:cli-incomplete-command;
        leaf distributed {
          tailf:info
            "Distributed Cisco Express Forwarding";
          tailf:cli-full-command;
          type empty;
        }
        container optimize {
          tailf:info
            "Optimizations";
          container neighbor {
            tailf:info
              "Optimizations for directly connected neighbors";
            leaf resolution {
              tailf:info
                "Trigger layer 2 address resolution directly from CEF";
              tailf:cli-boolean-no;
              tailf:cli-full-command;
              type boolean;
              default "true";
            }
          }
        }
      }
      list vrf {
        tailf:info
          "Configure an IP VPN Routing/Forwarding instance";
        tailf:cli-mode-name "config-vrf";
        tailf:callpoint ip-vrf-hook {
          tailf:set-hook node;
        }
        key "name";
        leaf name {
          type string {
            tailf:info
              "WORD;;VPN Routing/Forwarding instance name";
          }
        }
        leaf description {
          tailf:info
            "VRF specific description";
          tailf:cli-multi-value;
          type string {
            tailf:info
              "LINE;;Up to 244 characters describing this VRF";
            length "1..244";
          }
        }
        leaf rd {
          tailf:info
            "Specify Route Distinguisher";
          tailf:cli-full-command;
          tailf:cli-remove-before-change;
          type rd-type;
        }
        container vpn {
          tailf:info
            "Configure VPN ID as specified in rfc2685";
          leaf id {
            tailf:info
              "Configure VPN ID in rfc2685 format";
            type vpn-id-type;
          }
        }
        leaf context {
          tailf:info
            "Associate SNMP context with this vrf";
          type string {
            tailf:info
              "WORD;;SNMP Context Name";
          }
        }
        container import {
          tailf:info
            "VRF import";
          leaf map {
            tailf:info
              "Route-map based VRF import";
            tailf:cli-full-command;
            tailf:cli-diff-dependency "../ipv4" {
              tailf:xpath-root 3;
              tailf:cli-trigger-on-set;
            }
            type string {
              tailf:info
                "WORD;;VRF import route-map name";
            }
          }
          container ipv4 {
            tailf:info
              "Address family based VRF import";
            tailf:cli-compact-syntax;
            tailf:cli-sequence-commands;
            tailf:cli-diff-dependency "../map" {
              tailf:xpath-root 3;
              tailf:cli-trigger-on-set;
            }
            leaf ipv4-type {
              tailf:cli-drop-node-name;
              type enumeration {
                enum "unicast" {
                  tailf:info
                    "Import prefixes from IPv4 Unicast table";
                }
                enum "multicast" {
                  tailf:info
                    "Import prefixes from IPv4 Multicast table";
                }
              }
            }
            leaf upper-limit {
              tailf:cli-break-sequence-commands;
              tailf:cli-drop-node-name;
              type uint32 {
                tailf:info
                  "<1-2147483647>;;Upper limit on import prefixes without hogging memory";
                range "1..2147483647";
              }
            }
            leaf map {
              tailf:info
                "Route-map based VRF import";
              type string {
                tailf:info
                  "WORD;;VRF import route-map name";
              }
            }
          }
        }
        container export {
          tailf:info
            "VRF export";
          leaf map {
            tailf:info
              "Route-map based VRF export";
            type string {
              tailf:info
                "WORD;;VRF export route-map name";
            }
          }
        }
        container maximum {
          tailf:info
            "Set a limit";
          tailf:cli-compact-syntax;
          tailf:cli-sequence-commands;
          tailf:cli-incomplete-command;
          presence "true";
          leaf routes {
            tailf:info
              "Maximum number of routes allowed in this routing table";
            tailf:cli-incomplete-command;
            type uint32 {
              tailf:info
                "<1-4294967295>;;Maximum number of routes allowed";
              range "1..4294967295";
            }
          }
          choice maximum-choice {
            mandatory true;
            case threshold-case {
              leaf threshold {
                tailf:cli-drop-node-name;
                type uint16 {
                  range "1..100";
                  tailf:info
                    "<1-100>;;Threshold value (%) at which to generate a warning msg";
                }
              }
              leaf reinstall {
                tailf:info
                  "Reinstall previous rejected route due to over maximum route limit";
                type uint16 {
                  tailf:info
                    "<1-100>;;Threshold value (%) at which to reinstall routes back to VRF";
                  range "1..100";
                }
              }
            }
            case warning-case {
              leaf warning-only {
                tailf:info
                  "Only give a warning message if is limit exceeded";
                type empty;
              }
            }
          }
        }
        container bgp {
          tailf:info
            "Commands pertaining to BGP";
          container next-hop {
            tailf:info
              "Next-hop for the routes of a VRF in the backbone";
            leaf Loopback {
              tailf:info
                "Loopback interface number";
              tailf:cli-allow-join-with-value {
                tailf:cli-display-joined;
              }
              type uint32 {
                tailf:info
                  "<0-2147483647>;;Loopback interface number";
                range "0..2147483647";
              }
            }
          }
        }
        container mdt {
          tailf:info
            "Backbone Multicast Distribution Tree";
          tailf:cli-incomplete-command;
          presence "Backbone Multicast Distribution Tree";
          leaf default {
            tailf:info
              "The default group";
            type inet:ipv4-address {
              tailf:info
                "A.B.C.D;;IP multicast group address";
            }
          }
          container data {
            tailf:info
              "MDT data group range";
            tailf:cli-compact-syntax;
            tailf:cli-sequence-commands;
            tailf:cli-incomplete-command;
            leaf mulicast-address {
              tailf:cli-drop-node-name;
              tailf:cli-incomplete-command;
              type inet:ipv4-address {
                tailf:info
                  "A.B.C.D;;IP multicast group address";
              }
            }
            leaf wildcard-bits {
              tailf:cli-drop-node-name;
              type inet:ipv4-address {
                tailf:info
                  "A.B.C.D;;Wildcard bits";
              }
            }
            choice mdt-data-choice {
              case mdt-data-threshold {
                leaf threshold {
                  tailf:info
                    "MDT switching threshold";
                  type uint32 {
                    tailf:info
                      "<1-4294967>;;Traffic rate in kilobits per second";
                    range "1..4294967";
                  }
                }
                leaf threshold-list {
                  tailf:info
                    "Access-list";
                  tailf:alt-name "list";
                  type ext-acl-type;
                }
              }
              case mdt-data-list {
                leaf list {
                  tailf:info
                    "Access-list";
                  type ext-acl-type;
                }
              }
            }
          }
          leaf log-reuse {
            tailf:info
              "Event logging for data MDT reuse";
            type empty;
          }
        }
        list route-target {
          tailf:info
            "Specify Target VPN Extended Communities";
          tailf:cli-suppress-mode;
          tailf:cli-delete-when-empty;
          key "direction target";
          leaf direction {
            type enumeration {
              enum "both" {
                tailf:info
                  "Both import and export Target-VPN community";
              }
              enum "export" {
                tailf:code-name "direction_export";
                tailf:info
                  "Export Target-VPN community";
              }
              enum "import" {
                tailf:code-name "direction_import";
                tailf:info
                  "Import Target-VPN community";
              }
            }
          }
          leaf target {
            type rd-type {
              tailf:info
                "ASN:nn or IP-address:nn;;Target VPN Extended Community";
            }
          }
        }
      }
      container dhcp-server {
        tailf:info
          "Specify target DHCP server parameters";
        list dhcp-server-list {
          tailf:cli-drop-node-name;
          tailf:cli-suppress-mode;
          tailf:cli-delete-when-empty;
          tailf:cli-compact-syntax;
          key "server";
          leaf server {
            type string {
              tailf:info
                "Hostname or A.B.C.D;;IP address or Name of DHCP server";
            }
          }
        }
      }
      container dhcp {
        tailf:info
          "Configure DHCP server and relay parameters";
        leaf smart-relay {
          tailf:info
            "Enable Smart Relay feature";
          type empty;
        }
        container use {
          tailf:info
            "Configure use of certain parameters during allocation";
          container vrf {
            tailf:info
              "Ignore or use receiving interface VRF";
            leaf connected {
              tailf:info
                "Use input interface VRF when servicing connected clients";
              tailf:cli-boolean-no;
              tailf:cli-full-command;
              type boolean;
              default "true";
            }
          }
        }
        container conflict {
          tailf:info
            "DHCP address conflict parameters";
          leaf logging {
            tailf:info
              "Record address conflicts in a log file";
            tailf:cli-boolean-no;
            tailf:cli-full-command;
            type boolean;
            default "true";
          }
        }
        container excluded-address {
          tailf:info
            "Prevent DHCP from assigning certain addresses";
          uses ip-dhcp-excluded-address-grouping;
          list vrf {
            tailf:info
              "VRF name for excluded address range";
            tailf:cli-suppress-mode;
            tailf:cli-delete-when-empty;
            tailf:cli-compact-syntax;
            tailf:cli-incomplete-command;
            key "name";
            leaf name {
              type string {
                tailf:info
                  "WORD;;VPN Routing/Forwarding instance name";
              }
            }
            uses ip-dhcp-excluded-address-grouping;
          }
        }
        list pool {
          tailf:info
            "Configure DHCP address pools";
          tailf:cli-mode-name "dhcp-config";
          key "id";
          leaf id {
            type string {
              tailf:info
                "WORD;;Pool name";
            }
          }
          leaf vrf {
            tailf:info
              "Associate this pool with a VRF";
            type string {
              tailf:info
                "WORD;;VRF name";
            }
          }
          container network {
            tailf:info
              "Network number and mask";
            tailf:cli-compact-syntax;
            tailf:cli-sequence-commands {
              tailf:cli-reset-siblings;
            }
            leaf network-number {
              tailf:cli-drop-node-name;
              type inet:ipv4-address {
                tailf:info
                  "Network number in dotted-decimal notation";
              }
            }
            leaf mask {
              tailf:cli-drop-node-name;
              type inet:ipv4-address {
                tailf:info
                  "A.B.C.D;;Network mask";
              }
            }
          }
          leaf-list dns-server {
            tailf:info
              "DNS servers";
            tailf:cli-flat-list-syntax;
            type inet:host {
              tailf:info
                "Hostname or A.B.C.D;;Server's name or IP address";
            }
          }
          leaf domain-name {
            tailf:info
              "Domain name";
            tailf:cli-full-command;
            type string {
              tailf:info
                "NAME;;Domain name";
            }
          }
          leaf-list default-router {
            tailf:info
              "Default routers";
            tailf:cli-flat-list-syntax;
            type inet:host {
              tailf:info
                "Hostname or A.B.C.D;;Router's name or IP address";
            }
          }
          list option {
            tailf:info
              "Raw DHCP options";
            tailf:cli-suppress-mode;
            tailf:cli-delete-when-empty;
            tailf:cli-compact-syntax;
            tailf:cli-reset-container;
            tailf:cli-incomplete-command;
            key "code";
            leaf code {
              type uint8 {
                tailf:info
                  "<0-254>;;DHCP option code";
                range "0..254";
              }
            }
            leaf ascii {
              tailf:info
                "Data is an NVT ASCII string";
              type string {
                tailf:info
                  "LINE;;NVT ASCII string";
              }
            }
            leaf hex {
              tailf:info
                "Data is a hexadecimal string";
              type union {
                type string {
                  tailf:info
                    "LINE;;Hexadecimal string";
                }
                type enumeration {
                  enum "none" {
                    tailf:info
                      "No data";
                  }
                }
              }
            }
            leaf instance {
              tailf:info
                "Specify the option instance";
              type uint8 {
                tailf:info
                  "<0-255>;;DHCP option instance";
              }
            }
            leaf-list ip {
              tailf:info
                "Data is one or more IP addresses";
              tailf:cli-flat-list-syntax;
              type inet:host {
                tailf:info
                  "Hostname or A.B.C.D;;Server's name or IP address";
              }
            }
          }
          leaf netbios-name-server {
            tailf:info
              "NetBIOS (WINS) name servers";
            type inet:host {
              tailf:info
                "Hostname or A.B.C.D  Server's name or IP address";
            }
          }
          container lease {
            tailf:info
              "Address lease time";
            tailf:cli-compact-syntax;
            tailf:cli-sequence-commands {
              tailf:cli-reset-all-siblings;
            }
            choice lease-choice {
              case a {
                leaf infinite {
                  tailf:info
                    "Infinite lease";
                  type empty;
                }
              }
              case b {
                leaf days {
                  tailf:cli-drop-node-name;
                  type uint16 {
                    tailf:info
                      "<0-365>;;Days";
                    range "0..365";
                  }
                }
                leaf hours {
                  tailf:cli-drop-node-name;
                  type uint16 {
                    tailf:info
                      "<0-23>;;Hours";
                    range "0..23";
                  }
                }
                leaf minutes {
                  tailf:cli-drop-node-name;
                  type uint16 {
                    tailf:info
                      "<0-59>;;Minutes";
                    range "0..59";
                  }
                }
              }
            }
          }
        }
        list class {
          tailf:info
            "Configure DHCP classes";
          tailf:cli-mode-name "config-dhcp-class";
          key "id";
          leaf id {
            type string {
              tailf:info
                "WORD;;Class name";
            }
          }
          leaf remark {
            tailf:info
              "Specify a remark for this class";
            tailf:cli-multi-value;
            type string {
              tailf:info
                "LINE;;Up to 240 characters describing this class";
              length "1..240";
            }
          }
          container relay {
            tailf:info
              "Enter relay agent information option configuration submode";
            container agent {
              tailf:info
                "Enter relay agent information option configuration submode";
              container information {
                tailf:info
                  "Enter relay agent information option configuration submode";
                tailf:cli-add-mode;
                tailf:cli-mode-name "config-dhcp-class-relayinfo";
                presence "true";
              }
            }
          }
        }
        container snooping {
          tailf:info
            "DHCP Snooping";
          tailf:cli-display-separated;
          presence "true";
          leaf-list bridge-domain {
            tailf:info
              "DHCP Snooping bridge-domain";
            tailf:cli-range-list-syntax;
            tailf:cli-suppress-list-no;
            tailf:cli-full-command;
            tailf:cli-diff-dependency "../../snooping" {
              tailf:xpath-root 3;
            }
            type uint16 {
              tailf:info
                "WORD;;bridge-domain range, example: 1,3-5,7,9-11";
              range "1..4094";
            }
          }
          container information {
            tailf:info
              "DHCP Snooping information";
            container option {
              tailf:info
                "DHCP Snooping information option";
              presence "true";
              leaf allow-untrusted {
                tailf:info
                  "DHCP Snooping information option allow-untrusted";
                type empty;
              }
              container format {
                tailf:info
                  "Option 82 information format";
                container remote-id {
                  tailf:info
                    "Remote id option 82 format";
                  choice remote-id-choice {
                    leaf hostname {
                      tailf:info
                        "Use configured hostname for remote id";
                      type empty;
                    }
                    leaf string {
                      tailf:info
                        "User defined string for remote id";
                      type string {
                        tailf:info
                          "WORD;;Use string for remote id (max length 63)";
                      }
                    }
                  }
                }
              }
            }
          }
          container database {
            tailf:info
              "DHCP snooping database agent";
            leaf url {
              tailf:cli-drop-node-name;
              type string {
                tailf:info
                  "WORD;;Database agent URL";
              }
            }
          }
          container track {
            tailf:info
              "DHCP snooping track";
            leaf host {
              tailf:info
                "DHCP snooping track host";
              type empty;
            }
          }
          container verify {
            tailf:info
              "DHCP snooping verify";
            leaf mac-address {
              tailf:info
                "DHCP snooping verify mac-address";
              type empty;
            }
            leaf no-relay-agent-address {
              tailf:info
                "DHCP snooping verify giaddr";
              type empty;
            }
          }
          leaf-list vlan {
            tailf:info
              "DHCP Snooping vlan";
            type uint16 {
              tailf:info
                "WORD;;DHCP Snooping vlan fist number or vlan range, example: 1,3-5,7,9-11";
            }
          }
        }
        container relay {
          tailf:info
            "DHCP relay agent parameters";
          container information {
            tailf:info
              "Relay agent information option";
            container option {
              tailf:info
                "Insert relay information in BOOTREQUEST";
              presence "true";
            }
            leaf check {
              tailf:info
                "Validate relay information in BOOTREPLY";
              tailf:cli-boolean-no;
              tailf:cli-full-command;
              type boolean;
              default "true";
            }
            leaf trust-all {
              tailf:info
                "Received DHCP packets may contain relay info option with zero giaddr";
              type empty;
            }
          }
        }
      }
      container bootp {
        tailf:info
          "Config BOOTP services";
        leaf server {
          tailf:info
            "Enable BOOTP server";
          tailf:cli-boolean-no;
          tailf:cli-full-command;
          type boolean;
          default "true";
        }
      }
      container domain {
        tailf:info
          "IP DNS Resolver";
        tailf:cli-incomplete-no;
        leaf round-robin {
          tailf:info
            "Round-robin multiple IP addresses in cache";
          tailf:cli-full-command;
          type empty;
        }
        container list-vrf {
          tailf:cli-drop-node-name;
          container list {
            tailf:cli-incomplete-command;
            tailf:cli-incomplete-no;
            list vrf {
              tailf:info
                "Specify VRF";
              tailf:cli-suppress-mode;
              tailf:cli-delete-when-empty;
              tailf:cli-compact-syntax;
              tailf:cli-incomplete-command;
              key "name";
              leaf name {
                type string {
                  tailf:info
                    "WORD;;VRF name";
                }
              }
              leaf domain-name {
                tailf:cli-drop-node-name;
                type string {
                  tailf:info
                    "WORD;;A domain name";
                }
              }
            }
          }
        }
        list list {
          tailf:info
            "Domain name to complete unqualified host names";
          tailf:cli-suppress-mode;
          tailf:cli-delete-when-empty;
          key "name";
          leaf name {
            type string {
              tailf:info
                "WORD;;A domain name";
            }
          }
        }
        leaf retry {
          tailf:info
            "Specify times to retry sending a DNS query";
          tailf:cli-full-command;
          type uint8 {
            tailf:info
              "<0-100>;;Number of retries";
            range "0..100";
          }
        }
        leaf timeout {
          tailf:info
            "Specify timeout waiting for response to a DNS query";
          tailf:cli-full-command;
          type uint16 {
            tailf:info
              "<1-3600>;;Timeout value in seconds";
            range "1..3600";
          }
        }
        container lookup-conf {
          tailf:cli-drop-node-name;
          leaf lookup {
            tailf:info
              "Enable IP Domain Name System hostname translation";
            tailf:cli-boolean-no;
            tailf:cli-full-command;
            type boolean;
            default "true";
          }
        }
        container lookup {
          tailf:info
            "Enable IP Domain Name System hostname translation";
          tailf:cli-incomplete-command;
          tailf:cli-incomplete-no;
          leaf nsap {
            tailf:info
              "Enable IP DNS queries for CLNS NSAP addresses";
            tailf:cli-boolean-no;
            tailf:cli-full-command;
            type boolean;
            default "true";
          }
          leaf recursive {
            tailf:info
              "Enable IP DNS recursive lookup";
            tailf:cli-full-command;
            type empty;
          }
          container source-interface {
            tailf:info
              "Specify source interface for DNS resolver";
            uses interface-name-grouping;
          }
          leaf vrf {
            tailf:info
              "Specify VRF";
            tailf:cli-diff-dependency "/ios:ip/vrf" {
              tailf:xpath-root 3;
            }
            tailf:cli-diff-dependency "/ios:vrf/definition" {
              tailf:xpath-root 3;
            }
            type string {
              tailf:info
                "WORD;;VRF name";
            }
          }
        }
        container name-vrf {
          tailf:cli-drop-node-name;
          container name {
            tailf:cli-incomplete-command;
            tailf:cli-incomplete-no;
            list vrf {
              tailf:info
                "Specify VRF";
              tailf:cli-suppress-mode;
              tailf:cli-delete-when-empty;
              tailf:cli-compact-syntax;
              tailf:cli-incomplete-command;
              key "name";
              leaf name {
                type string {
                  tailf:info
                    "WORD;;VRF name";
                }
              }
              leaf domain-name {
                tailf:cli-drop-node-name;
                type string {
                  tailf:info
                    "WORD;;Default domain name";
                }
              }
            }
          }
        }
        leaf name {
          tailf:info
            "Define the default domain name";
          type string {
            tailf:info
              "WORD;;Default domain name";
          }
        }
        leaf multicast {
          tailf:info
            "Define the domain name for multicast address lookups";
          tailf:cli-full-command;
          type string {
            tailf:info
              "WORD;;Multicast domain name";
          }
        }
        container recursive {
          tailf:info
            "Configure recursive DNS lookup";
          leaf retry {
            tailf:info
              "Configure maximum no. referrals to be allowed";
            tailf:cli-full-command;
            type uint8 {
              tailf:info
                "<0-100>;;Maximum no. of referrals allowed - default 10";
              range "0..100";
            }
          }
          leaf allow-soa {
            tailf:info
              "Treat response containing SOA RR in AUTHORITY as a referral";
            tailf:cli-full-command;
            type empty;
          }
        }
      }
      container host {
        tailf:info
          "Add an entry to the ip hostname table";
        tailf:cli-diff-dependency "/ios:ip/vrf" {
          tailf:xpath-root 3;
        }
        tailf:cli-diff-dependency "/ios:vrf/definition" {
          tailf:xpath-root 3;
        }
        uses ip-host-grouping;
        list vrf {
          tailf:info
            "Specify VRF";
          tailf:cli-suppress-mode;
          tailf:cli-delete-when-empty;
          tailf:cli-compact-syntax;
          tailf:cli-incomplete-command;
          key "name";
          leaf name {
            type string {
              tailf:info
                "WORD;;VRF name";
            }
          }
          uses ip-host-grouping;
        }
      }
      container name-server {
        tailf:info
          "Specify address of name server to use";
        uses ip-name-server-grouping;
        list vrf {
          tailf:info
            "Specify VRF";
          tailf:cli-suppress-mode;
          tailf:cli-delete-when-empty;
          tailf:cli-compact-syntax;
          tailf:cli-incomplete-command;
          key "name";
          leaf name {
            type string {
              tailf:info
                "WORD;;VRF name";
            }
          }
          uses ip-name-server-grouping;
        }
      }
      container mcr-conf {
        tailf:cli-drop-node-name;
        leaf multicast-routing {
          tailf:info
            "Enable IP multicast forwarding";
          type empty;
        }
      }
      container multicast-routing {
        tailf:info
          "Enable IP multicast forwarding";
        tailf:cli-incomplete-no;
        tailf:cli-incomplete-command;
        tailf:cli-diff-dependency "/ios:ip/vrf" {
          tailf:xpath-root 3;
        }
        tailf:cli-diff-dependency "/ios:vrf/definition" {
          tailf:xpath-root 3;
        }
        tailf:cli-diff-dependency "../mcr-conf/multicast-routing" {
          tailf:xpath-root 3;
        }
        list vrf {
          tailf:info
            "Select VPN Routing/Forwarding instance";
          tailf:cli-suppress-list-no;
          tailf:cli-suppress-mode;
          tailf:cli-delete-when-empty;
          tailf:cli-compact-syntax;
          tailf:cli-reset-container;
          tailf:cli-diff-dependency "../../mcr-conf/multicast-routing" {
            tailf:xpath-root 3;
          }
          key "name";
          leaf name {
            type string {
              tailf:info
                "WORD;;VPN Routing/Forwarding instance name";
            }
          }
          leaf distributed {
            tailf:info
              "Distributed multicast switching";
            type empty;
          }
        }
        leaf distributed {
          tailf:info
            "Distributed multicast switching";
          tailf:cli-full-command;
          type empty;
        }
      }
      container multicast {
        tailf:info
          "Global IP Multicast Commands";
        leaf route-limit {
          tailf:info
            "Maximum number of multicast routes";
          type uint32 {
            tailf:info
              "<1-2147483647>;;number of routes";
            range "1..2147483647";
          }
        }
        container multipath {
          tailf:info
            "RPF across equal-cost paths";
          presence "true";
          leaf s-g-hash {
            tailf:info
              "Per-(source, group) load sharing algorithm selection";
            type enumeration {
              enum "basic" {
                tailf:info
                  "Basic hash on (source, group)";
              }
              enum "next-hop-based" {
                tailf:info
                  "Advanced hash on (source, group) and next-hop";
              }
            }
          }
        }
      }
      container icmp {
        tailf:info
          "ICMP options";
        container rate-limit {
          tailf:info
            "rate limit ICMP messages generated";
          container unreachable {
            tailf:info
              "ICMP type 3, Destination Unreachable";
            tailf:cli-compact-syntax;
            tailf:cli-sequence-commands {
              tailf:cli-reset-siblings;
            }
            leaf DF {
              tailf:info
                "code 4, fragmentation needed and DF set";
              tailf:cli-optional-in-sequence;
              type empty;
            }
            leaf ms {
              tailf:cli-drop-node-name;
              type uint32 {
                tailf:info
                  "<1-4294967295>;;Once per milliseconds";
              }
            }
            container log {
              tailf:cli-flatten-container;
              tailf:cli-compact-syntax;
              tailf:cli-sequence-commands;
              tailf:cli-delete-when-empty;
              presence "true";
              leaf packets {
                tailf:cli-drop-node-name;
                type uint32 {
                  tailf:info
                    "<1-4294967295>;;number of unreachables within interval to trigger a message";
                  range "1..4294967295";
                }
              }
              leaf interval-ms {
                tailf:cli-drop-node-name;
                type uint32 {
                  tailf:info
                    "<10000-4294967295>;;log message once per milliseconds";
                  range "10000..4294967295";
                }
              }
            }
          }
        }
      }
      container igmp {
        tailf:info
          "IGMP global configuration";
        leaf limit {
          tailf:info
            "IGMP limit";
          type uint16 {
            tailf:info
              "<1-64000>;;Max Allowed State";
            range "1..64000";
          }
        }
        container snooping {
          tailf:info
            "Global IGMP Snooping enable for Catalyst Vlans";
          presence "true";
          leaf l2-entry-limit {
            tailf:info
              "limit on the l2 entry that can be installed by IGMP snooping";
            type uint32 {
              tailf:info
                "<1-100000>;;maximum number of l2 entries";
              range "1..100000";
            }
          }
        }
      }
      container device {
        tailf:info
          "Device tracking";
        container tracking {
          tailf:info
            "Device tracking";
          tailf:cli-delete-when-empty;
          presence "true";
        }
      }
      container finger {
        tailf:info
          "finger server";
        tailf:cli-delete-when-empty;
        tailf:cli-reset-container;
        presence "true";
        leaf rfc-compliant {
          tailf:info
            "Comply with RFC 1288";
          type empty;
        }
      }
      container tcp {
        tailf:info
          "Global TCP parameters";
        leaf mss {
          tailf:info
            "TCP initial maximum segment size ";
          type uint16 {
            tailf:info
              "<68-10000>;;MSS";
            range "68..10000";
          }
        }
        container path-mtu-discovery {
          tailf:info
            "Enable path-MTU discovery on new TCP connections";
          presence "true";
          leaf age-timer {
            tailf:info
              "Set PMTU aging timer";
            type union {
              type enumeration {
                enum "infinite" {
                  tailf:info
                    "Disable pathmtu aging timer";
                }
              }
              type uint8 {
                tailf:info
                  "<10-30>;;Aging time";
                range "10..30";
              }
            }
          }
        }
      }
      container telnet {
        tailf:info
          "Specify telnet options";
        container source-interface {
          tailf:info
            "Specify source interface";
          uses interface-name-grouping;
        }
      }
      container ftp {
        tailf:info
          "FTP configuration commands";
        leaf passive {
          tailf:info
            "Connect using passive mode";
          tailf:cli-boolean-no;
          tailf:cli-full-command;
          type boolean;
          default "true";
        }
        container source-interface {
          tailf:info
            "Specify interface for source address in FTP connections";
          uses interface-name-grouping;
        }
        leaf username {
          tailf:info
            "Specify username for FTP connections";
          tailf:cli-full-command;
          type string {
            tailf:info
              "WORD;;Username";
          }
        }
        container password {
          tailf:info
            "Specify password for FTP connections;";
          uses password-grouping;
        }
      }
      container tftp {
        tailf:info
          "tftp configuration commands";
        container source-interface {
          tailf:info
            "Specify interface for source address in TFTP connections";
          tailf:cli-compact-syntax;
          uses interface-name-grouping;
        }
        container boot-interface {
          tailf:info
            "Force interface to use for TFTP booting";
          uses interface-name-grouping;
        }
      }
      container ssh {
        tailf:info
          "Configure ssh options";
        leaf time-out {
          tailf:info
            "Specify SSH time-out interval";
          type uint8 {
            tailf:info
              "<1-120>;;SSH time-out interval (secs)";
            range "1..120";
          }
        }
        leaf authentication-retries {
          tailf:info
            "Specify number of authentication retries";
          type uint8 {
            tailf:info
              "<0-5>;;Number of authentication retries";
            range "0..5";
          }
        }
        leaf dscp {
          tailf:info
            "IP DSCP value for SSH traffic";
          type uint8 {
            tailf:info
              "<0-63>;;ip dscp value (default value 0)";
            range "0..63";
          }
        }
        container logging {
          tailf:info
            "Configure logging for SSH";
          leaf events {
            tailf:info
              "Log SSH events";
            type empty;
          }
        }
        leaf version {
          tailf:info
            "Specify protocol version supported";
          type uint8 {
            tailf:info
              "<1-2>;;Protocol version";
            range "1..2";
          }
        }
        leaf precedence {
          tailf:info
            "IP Precedence value for SSH traffic";
          type uint8 {
            tailf:info
              "<0-7>;;ip precedence value (default value 0)";
            range "0..7";
          }
        }
        leaf stricthostkeycheck {
          tailf:info
            "Enable SSH Server Authentication";
          type empty;
        }
        container source-interface {
          tailf:info
            "Specify interface for source address in SSH connections";
          uses interface-name-grouping;
        }
      }
      container scp {
        tailf:info
          "Scp commands";
        container server {
          tailf:info
            "Configure SCP server-side functionality";
          leaf enable {
            tailf:info
              "Enable server side of SCP";
            type empty;
          }
        }
      }
      container local {
        tailf:info
          "Specify local options";
        list pool {
          tailf:info
            "IP Local address pool lists";
          tailf:cli-suppress-mode;
          tailf:cli-delete-when-empty;
          tailf:cli-compact-syntax;
          tailf:cli-sequence-commands {
            tailf:cli-reset-siblings;
          }
          key "id";
          leaf id {
            type union {
              type string {
                tailf:info
                  "WORD;;Create named local address pool";
              }
              type enumeration {
                enum "default" {
                  tailf:info
                    "Create default local address pool";
                }
              }
            }
          }
          leaf start {
            tailf:cli-drop-node-name;
            type inet:ipv4-address {
              tailf:info
                "A.B.C.D;;First IP address of range";
            }
          }
          leaf last {
            tailf:cli-drop-node-name;
            tailf:cli-optional-in-sequence;
            type inet:ipv4-address {
              tailf:info
                "A.B.C.D;;Last IP address of range";
            }
          }
          leaf group {
            tailf:info
              "Create ip local pool group";
            type string {
              tailf:info
                "WORD;;Group name for this named local address pool";
            }
          }
        }
      }
      leaf default-gateway {
        tailf:info
          "Specify default gateway (if not routing IP)";
        type inet:ipv4-address {
          tailf:info
            "A.B.C.D;;IP address of default gateway";
        }
      }
      leaf classless {
        tailf:info
          "Follow classless routing forwarding rules";
        tailf:cli-boolean-no;
        tailf:cli-full-command;
        type boolean;
        default "true";
      }
      container forward-protocol {
        tailf:info
          "Controls forwarding of physical and directed IP broadcasts";
        leaf nd {
          tailf:info
            "Sun's Network Disk protocol";
          tailf:cli-show-no;
          type empty;
        }
        leaf sdns {
          tailf:info
            "Network Security Protocol";
          tailf:cli-boolean-no;
          type boolean;
        }
        leaf turbo-flood {
          tailf:info
            "Fast flooding of UDP broadcasts";
          tailf:cli-boolean-no;
          type boolean;
        }
        container spanning-tree {
          tailf:info
            "Use transparent bridging to flood UDP broadcasts";
          presence "true";
          leaf any-local-broadcast {
            tailf:info
              "Accept any local broadcast when flooding";
            type empty;
          }
        }
        container udp {
          tailf:info
            "Packets to a specific UDP port";
          presence "true";
          leaf service {
            tailf:cli-drop-node-name;
            type string;
          }
        }
      }
      container http {
        tailf:info
          "HTTP server configuration";
        leaf server {
          tailf:info
            "Enable http server";
          tailf:cli-boolean-no;
          tailf:cli-full-command;
          type boolean;
        }
        leaf access-class {
          tailf:info
            "Restrict http server access by access-class";
          tailf:cli-full-command;
          type uint8 {
            tailf:info
              "<1-99>;;Access list number";
            range "1..99";
          }
        }
        container authentication {
          tailf:info
            "Set http server authentication method";
          choice authentication-choice {
            leaf aaa {
              tailf:info
                "Use AAA access control methods";
              tailf:cli-full-command;
              type empty;
            }
            leaf local {
              tailf:info
                "Use local username and passwords";
              tailf:cli-full-command;
              type empty;
            }
          }
        }
        leaf secure-server {
          tailf:info
            "Enable HTTP secure server";
          tailf:cli-boolean-no;
          tailf:cli-full-command;
          type boolean;
        }
        container timeout-policy {
          tailf:info
            "Set http server time-out policy parameters";
          tailf:cli-compact-syntax;
          tailf:cli-sequence-commands {
            tailf:cli-reset-all-siblings;
          }
          leaf idle {
            tailf:info
              "Idle time-out of a http server connection in seconds";
            tailf:cli-incomplete-command;
            type uint16 {
              tailf:info
                "<1-600>;;Connection idle time-out value in seconds";
              range "1..600";
            }
          }
          leaf life {
            tailf:info
              "Life time of a http server connection in seconds";
            tailf:cli-incomplete-command;
            type uint32 {
              tailf:info
                "<1-86400>;;Connection life time value in seconds";
              range "1..86400";
            }
          }
          leaf requests {
            tailf:info
              "Maximum number of requests allowed on a http server connection";
            type uint32 {
              tailf:info
                "<1-86400>;;Maximum number of requests allowed on a http server connection";
              range "1..86400";
            }
          }
        }
        container client {
          tailf:info
            "Set http client parameters";
          tailf:cli-incomplete-command;
          leaf source-interface {
            tailf:cli-full-command;
            tailf:cli-multi-value;
            tailf:info
              "Specify interface for source address in all HTTP(S) client connections";
            type string {
              tailf:info
                "WORD;;Interface name";
            }
          }
        }
      }
      container bgp-community {
        tailf:info
          "format for BGP community";
        leaf new-format {
          tailf:info
            "select aa:nn format for BGP community";
          type empty;
        }
      }
      container community-list {
        tailf:info
          "Add a community list entry";
        list number-standard {
          tailf:cli-drop-node-name;
          tailf:cli-suppress-mode;
          tailf:cli-delete-when-empty;
          tailf:cli-incomplete-command;
          key "no";
          leaf no {
            type uint16 {
              tailf:info
                "<1-99>;;Community list number (standard)";
              range "1..99";
            }
          }
          uses ip-community-list-standard-grouping;
        }
        list number-expanded {
          tailf:cli-drop-node-name;
          tailf:cli-incomplete-command;
          tailf:cli-suppress-mode;
          tailf:cli-delete-when-empty;
          key "no";
          leaf no {
            type uint16 {
              tailf:info
                "<100-500>;;Community list number (expanded)";
              range "100..500";
            }
          }
          uses ip-community-list-expanded-grouping;
        }
        list expanded {
          tailf:info
            "Add an expanded community-list entry";
          tailf:cli-incomplete-command;
          tailf:cli-suppress-mode;
          tailf:cli-delete-when-empty;
          key "name";
          leaf name {
            type string {
              tailf:info
                "WORD;;Community list name";
            }
          }
          uses ip-community-list-expanded-grouping;
        }
        list standard {
          tailf:info
            "Add a standard community-list entry";
          tailf:cli-incomplete-command;
          tailf:cli-suppress-mode;
          tailf:cli-delete-when-empty;
          key "name";
          leaf name {
            type string {
              tailf:info
                "WORD;;Community list name";
            }
          }
          uses ip-community-list-standard-grouping;
        }
      }
      container as-path {
        tailf:info
          "BGP autonomous system path filter";
        list access-list {
          tailf:info
            "Specify an access list number";
          tailf:cli-suppress-mode;
          tailf:cli-delete-when-empty;
          tailf:cli-incomplete-command;
          tailf:cli-compact-syntax;
          key "name";
          leaf name {
            tailf:cli-incomplete-command;
            type uint16 {
              range "1..500";
              tailf:info
                "<1-500>;;AS path access list number";
            }
          }
          list as-path-rule {
            tailf:cli-suppress-mode;
            tailf:cli-delete-when-empty;
            tailf:cli-drop-node-name;
            tailf:cli-compact-syntax;
            tailf:cli-show-long-obu-diffs;
            ordered-by user;
            key "operation rule";
            leaf operation {
              tailf:cli-drop-node-name;
              tailf:cli-incomplete-command;
              type enumeration {
                enum "deny" {
                  tailf:code-name "operation_deny";
                  tailf:info
                    "Specify packets to reject";
                }
                enum "permit" {
                  tailf:code-name "operation_permit";
                  tailf:info
                    "Specify packets to forward";
                }
              }
            }
            leaf rule {
              tailf:cli-drop-node-name;
              tailf:cli-multi-value;
              tailf:cli-full-command;
              type string {
                tailf:info
                  "LINE;;A regular-expression to match BGP AS paths.";
              }
            }
          }
        }
      }
      container flow-cache {
        tailf:info
          "Configure netflow cache parameters";
        leaf entries {
          tailf:info
            "Specify the number of entries in the flow cache";
          type uint32 {
            tailf:info
              "<1024-524288>;;Entries";
            range "1024..524288";
          }
        }
        container timeout {
          tailf:info
            "Specify flow cache timeout parameters";
          leaf inactive {
            tailf:info
              "Specify the inactive flow timeout";
            tailf:cli-full-command;
            type uint16 {
              tailf:info
                "<10-600>;;Timeout in seconds";
              range "10..600";
            }
          }
          leaf active {
            tailf:info
              "Specify the active flow timeout";
            tailf:cli-full-command;
            type uint16 {
              tailf:info
                "<1-60>;;Timeout in minutes";
              range "1..60";
            }
          }
        }
      }
      container flow-export {
        tailf:info
          "Specify host/port to send flow statistics";
        container source {
          tailf:info
            "Specify the interface for source address";
          uses interface-name-grouping;
        }
        leaf version {
          tailf:info
            "Specify the version number";
          type enumeration {
            enum "1";
            enum "5";
            enum "9";
          }
        }
        container template {
          tailf:info
            "Specify the template specific configurations";
          tailf:cli-diff-dependency "../version" {
            tailf:xpath-root 3;
          }
          container options {
            tailf:info
              "Specify the template option";
            leaf export-stats {
              tailf:info
                "Specify the template option export statistics";
              tailf:cli-full-command;
              type empty;
            }
          }
          leaf timeout-rate {
            tailf:info
              "Specify the time before template is resent";
            tailf:cli-full-command;
            type uint16 {
              tailf:info
                "<1-3600>;;Timeout in minutes (default 30 minutes)";
              range "1..3600";
            }
            default "30";
          }
          leaf refresh-rate {
            tailf:info
              "Specify the number of export packets before template is resent";
            tailf:cli-full-command;
            type uint16 {
              tailf:info
                "<1-600>;;refresh rate in export packets (default 20 packets)";
              range "1..600";
            }
            default "20";
          }
        }
        container destination {
          tailf:info
            "Specify the Destination IP address";
          tailf:cli-compact-syntax;
          tailf:cli-sequence-commands {
            tailf:cli-reset-all-siblings;
          }
          leaf ip {
            tailf:cli-drop-node-name;
            type host-type {
              tailf:info
                "Hostname or A.B.C.D  Destination IP address";
            }
          }
          leaf port {
            tailf:cli-drop-node-name;
            type uint16 {
              tailf:info
                "<1-65535>;;UDP port number";
              range "1..65535";
            }
          }
        }
      }
      container flow-aggregation {
        tailf:info
          "Configure flow aggregation";
        list cache {
          tailf:info
            "Create flow aggregation cache or enter flow-cache command mode";
          tailf:cli-mode-name "config-flow-cache";
          key "name";
          leaf name {
            type string;
          }
          container cache {
            tailf:info
              "Configure netflow cache parameters";
            container timeout {
              tailf:info
                "Specify flow cache timeout parameters";
              leaf active {
                tailf:info
                  "Specify the active flow timeout";
                type uint8 {
                  tailf:info
                    "<1-60>;;Timeout in minutes";
                  range "1..60";
                }
              }
            }
          }
          container export {
            tailf:info
              "Specify host/port to send flow statistics";
            list destination {
              tailf:info
                "Specify the Destination IP address";
              tailf:cli-suppress-mode;
              tailf:cli-delete-when-empty;
              tailf:cli-compact-syntax;
              tailf:cli-incomplete-command;
              key "address";
              leaf address {
                type inet:host {
                  tailf:info
                    "Hostname or A.B.C.D Destination IP addres";
                }
              }
              leaf port {
                tailf:cli-drop-node-name;
                type uint16 {
                  tailf:info
                    "<1-65535>;;UDP/SCTP port number";
                  range "1..65535";
                }
              }
            }
          }
        }
      }
      container dns {
        tailf:info
          "Configure DNS server for a zone";
        container server {
          tailf:info
            "Enable DNS server";
          presence "true";
        }
      }
      container mobile {
        tailf:info
          "Enable Mobile IP services";
        container secure {
          tailf:info
            "Security association";
          list home-agent {
            tailf:info
              "Home agent security association";
            tailf:cli-suppress-mode;
            tailf:cli-delete-when-empty;
            tailf:cli-compact-syntax;
            tailf:cli-sequence-commands {
              tailf:cli-reset-all-siblings;
            }
            tailf:cli-diff-dependency "/ios:router/mobile" {
              tailf:xpath-root 3;
            }
            key "lower-address";
            leaf lower-address {
              type inet:ipv4-address {
                tailf:info
                  "A.B.C.D;;IP address (lower range)";
              }
            }
            leaf upper-address {
              tailf:cli-drop-node-name;
              tailf:cli-optional-in-sequence;
              type inet:ipv4-address {
                tailf:info
                  "A.B.C.D;;Upper range IP address for security";
              }
            }
            choice spi-choice {
              case single-spi {
                container spi {
                  tailf:info
                    "Security parameter index - bidirectional";
                  tailf:cli-flatten-container;
                  tailf:cli-compact-syntax;
                  uses mobile-ip-spi-grouping;
                }
              }
              case range-spi {
                container inbound-spi {
                  tailf:info
                    "Security parameter index - inbound";
                  tailf:cli-flatten-container;
                  tailf:cli-compact-syntax;
                  uses mobile-ip-spi-grouping;
                }
                container outbound-spi {
                  tailf:info
                    "Security parameter index - outbound";
                  tailf:cli-flatten-container;
                  tailf:cli-compact-syntax;
                  uses mobile-ip-spi-grouping;
                }
              }
            }
            container key {
              tailf:info
                "Security key";
              tailf:cli-flatten-container;
              tailf:cli-compact-syntax;
              choice key-choice {
                leaf ascii {
                  tailf:info
                    "Key entered in ASCII string";
                  type string {
                    tailf:info
                      "WORD;;Key entered in ASCII";
                  }
                }
                leaf hex {
                  tailf:info
                    "Key entered in hex string";
                  type string {
                    tailf:info
                      "Hex-string;;Hex string";
                  }
                }
              }
            }
            container algorithm {
              tailf:cli-break-sequence-commands;
              tailf:info
                "Authentication algorithm";
              tailf:cli-flatten-container;
              tailf:cli-compact-syntax;
              choice algorithm-choice {
                leaf hmac-md5 {
                  tailf:info
                    "HMAC MD5 authentication";
                  type empty;
                }
                container md5 {
                  tailf:info
                    "Keyed MD5 authentication";
                  tailf:cli-flatten-container;
                  tailf:cli-compact-syntax;
                  container mode {
                    tailf:info
                      "Authentication mode";
                    tailf:cli-flatten-container;
                    tailf:cli-compact-syntax;
                    leaf prefix-suffix {
                      tailf:info
                        "Prefix-suffix mode";
                      type empty;
                    }
                  }
                }
              }
            }
            leaf ignore-spi {
              tailf:info
                "Ignore SPI for Authentication";
              type empty;
            }
          }
        }
        container router {
          tailf:info
            "Mobile Router commands";
          tailf:cli-add-mode;
          tailf:cli-mode-name "mobile-router";
          tailf:cli-diff-dependency "../../../router/mobile" {
            tailf:xpath-root 3;
          }
          presence "true";
          container address {
            tailf:info
              "Mobile router's home address";
            tailf:cli-compact-syntax;
            tailf:cli-sequence-commands {
              tailf:cli-reset-all-siblings;
            }
            leaf ipv4-address {
              tailf:cli-drop-node-name;
              tailf:cli-incomplete-command;
              tailf:cli-diff-dependency "/ios:router/mobile" {
                tailf:xpath-root 3;
              }
              type inet:ipv4-address {
                tailf:info
                  "A.B.C.D;;IP address";
              }
            }
            leaf ipv4-mask {
              tailf:cli-drop-node-name;
              type inet:ipv4-address {
                tailf:info
                  "A.B.C.D;;Home network mask";
              }
            }
          }
          container collocated {
            tailf:info
              "Collocated CoA parameters";
            leaf single-tunnel {
              tailf:info
                "Optimized tunneling between MR and HA";
              tailf:cli-diff-dependency "/ios:router/mobile" {
                tailf:xpath-root 3;
              }
              type empty;
            }
          }
          list home-agent {
            tailf:info
              "Mobile router's home agent";
            tailf:cli-suppress-mode;
            tailf:cli-delete-when-empty;
            tailf:cli-diff-dependency "/ios:router/mobile" {
              tailf:xpath-root 3;
            }
            key "address";
            leaf address {
              type inet:ipv4-address {
                tailf:info
                  "A.B.C.D;;IP address";
              }
            }
            leaf priority {
              tailf:info
                "Priority level";
              type uint8 {
                tailf:info
                  "<0-255>;;Priority value (default is 100)";
              }
              default "100";
            }
          }
          list mobile-network {
            tailf:info
              "Mobile router's mobile network";
            tailf:cli-suppress-mode;
            tailf:cli-delete-when-empty;
            tailf:cli-diff-dependency "/ios:interface" {
              tailf:xpath-root 3;
            }
            key "name";
            leaf name {
              type string {
                tailf:info
                  "WORD;;Interface name";
              }
            }
            container policy {
              tailf:info
                "Enable MIP policy routing";
              leaf mobile-map {
                tailf:info
                  "Apply mobile-map dyn route-map";
                type string {
                  tailf:info
                    "WORD;;mobile-map tag";
                }
              }
            }
          }
          container register {
            tailf:info
              "Registration settings";
            container extend {
              tailf:info
                "Extend registration lifetime";
              tailf:cli-compact-syntax;
              tailf:cli-sequence-commands {
                tailf:cli-reset-siblings;
              }
              leaf expire {
                tailf:info
                  "Reregister before expiration";
                tailf:cli-incomplete-command;
                tailf:cli-diff-dependency "/ios:router/mobile" {
                  tailf:xpath-root 3;
                }
                type uint16 {
                  tailf:info
                    "<1-3600>;;Number of seconds before expiration";
                }
              }
              leaf retry {
                tailf:info
                  "Number of attempts to extend registration";
                tailf:cli-incomplete-command;
                type uint8 {
                  tailf:info
                    "<0-10>;;Stop after number of retries attempted";
                  range "0..10";
                }
              }
              leaf interval {
                tailf:info
                  "Interval between retries";
                type uint16 {
                  tailf:info
                    "<1-3600>;;Number of seconds between attempts";
                  range "1..3600";
                }
              }
              leaf reverse-tunnel {
                type empty;
              }
            }
          }
          leaf reverse-tunnel {
            tailf:info
              "Reverse Tunnel requested";
            type empty;
          }
          container tunnel {
            tailf:info
              "Tunnel parameters";
            container mode {
              tailf:info
                "Tunnel mode";
              leaf gre {
                tailf:info
                  "GRE encapsulation";
                type empty;
              }
            }
          }
          container template {
            tailf:info
              "Configure a tunnel template for tunnels to the Home Agent";
            leaf Tunnel {
              tailf:info
                "Tunnel interface";
              tailf:cli-allow-join-with-value {
                tailf:cli-display-joined;
              }
              type uint32 {
                tailf:info
                  "<0-2147483647>;;Tunnel interface number";
              }
            }
          }
        }
      }
      container pim {
        tailf:info
          "PIM global commands";
        tailf:cli-diff-dependency "/ios:ip/vrf" {
          tailf:xpath-root 3;
        }
        tailf:cli-diff-dependency "/ios:vrf/definition" {
          tailf:xpath-root 3;
        }
        tailf:cli-diff-dependency "/ios:interface" {
          tailf:xpath-root 3;
        }
        uses ip-pim-grouping;
        list vrf {
          tailf:info
            "Select VPN Routing/Forwarding instance";
          tailf:cli-suppress-mode;
          tailf:cli-delete-when-empty;
          tailf:cli-compact-syntax;
          key "id";
          leaf id {
            type string {
              tailf:info
                "WORD;;VPN Routing/Forwarding instance name";
            }
          }
          uses ip-pim-grouping;
        }
      }
      container rsvp {
        tailf:info
          "Configure static RSVP information";
        container signalling {
          tailf:info
            "RSVP Signalling";
          container hello {
            tailf:info
              "Enable neighbor-down detection";
            tailf:cli-delete-when-empty;
            presence "true";
            container graceful-restart {
              tailf:info
                "Configure RSVP Graceful Restart";
              leaf mode {
                tailf:info
                  "Select Graceful Restart capabilities";
                type enumeration {
                  enum "full" {
                    tailf:info
                      "Capable of recovering self, and helping neighbor recover";
                  }
                  enum "help-neighbor" {
                    tailf:info
                      "Capable of helping neighbor recover";
                  }
                }
              }
            }
          }
        }
      }
      container nat {
        tailf:info
          "NAT configuration commands";
        tailf:cli-diff-dependency "/ios:ip/vrf" {
          tailf:xpath-root 3;
        }
        tailf:cli-diff-dependency "/ios:vrf/definition" {
          tailf:xpath-root 3;
        }
        list pool {
          tailf:info
            "Define pool of addresses";
          tailf:cli-suppress-mode;
          tailf:cli-delete-when-empty;
          tailf:cli-compact-syntax;
          tailf:cli-sequence-commands {
            tailf:cli-reset-siblings;
          }
          key "id";
          leaf id {
            type string {
              tailf:info
                "WORD;;Pool name";
            }
          }
          leaf start-address {
            tailf:cli-drop-node-name;
            tailf:cli-optional-in-sequence;
            type inet:ipv4-address {
              tailf:info
                "A.B.C.D;;Start IP address";
            }
          }
          leaf end-address {
            tailf:cli-drop-node-name;
            when '../start-address' {
              tailf:xpath-root 3;
              tailf:dependency "../start-address";
            }
            type inet:ipv4-address {
              tailf:info
                "A.B.C.D;;End IP address";
            }
          }
          choice prefix-choice {
            leaf netmask {
              tailf:info
                "Specify the network mask";
              type inet:ipv4-address {
                tailf:info
                  "A.B.C.D;;Network mask";
              }
            }
            leaf prefix-length {
              tailf:info
                "Specify the prefix length";
              type uint8 {
                tailf:info
                  "<1-32>;;Prefix length";
                range "1..32";
              }
            }
          }
          leaf accounting {
            tailf:cli-optional-in-sequence;
            tailf:info
              "Specify the accounting";
            type string {
              tailf:info
                "WORD;;Accounting method-list name";
            }
          }
          choice nat-choice {
            leaf arp-ping {
              tailf:info
                "WLAN ARP Ping";
              type empty;
            }
            leaf type {
              tailf:info
                "Specify the pool type";
              type enumeration {
                enum "match-host" {
                  tailf:info
                    "Keep host numbers the same after translation";
                }
                enum "rotary" {
                  tailf:info
                    "Rotary address pool";
                }
              }
            }
            leaf add-route {
              tailf:info
                "Add special route to Virtual Interface";
              type empty;
            }
          }
        }
        container inside {
          tailf:info
            "Inside address translation";
          container source {
            tailf:info
              "Source address translation";
            list list {
              tailf:info
                "Specify access list describing local addresses";
              tailf:cli-suppress-mode;
              tailf:cli-delete-when-empty;
              tailf:cli-compact-syntax;
              tailf:cli-sequence-commands {
                tailf:cli-reset-all-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              uses ip-nat-inside-grouping;
            }
            container static {
              tailf:info
                "Specify static local->global mapping";
              list nat-static-address-list {
                tailf:cli-drop-node-name;
                tailf:cli-suppress-mode;
                tailf:cli-delete-when-empty;
                tailf:cli-compact-syntax;
                tailf:cli-sequence-commands {
                  tailf:cli-reset-siblings;
                }
                key "local-ip global-ip";
                leaf local-ip {
                  type inet:ipv4-address {
                    tailf:info
                      "A.B.C.D;;Inside local IP address";
                  }
                }
                leaf global-ip {
                  type inet:ipv4-address {
                    tailf:info
                      "A.B.C.D;;Inside global IP address";
                  }
                }
                uses ip-nat-inside-souce-static-grouping;
              }
              list nat-static-transport-list {
                tailf:cli-drop-node-name;
                tailf:cli-suppress-mode;
                tailf:cli-delete-when-empty;
                tailf:cli-compact-syntax;
                tailf:cli-sequence-commands {
                  tailf:cli-reset-siblings;
                }
                key "proto local-ip local-port global-ip global-port";
                leaf proto {
                  type enumeration {
                    enum "tcp" {
                      tailf:info
                        "Transmission Control Protocol";
                    }
                    enum "udp" {
                      tailf:info
                        "User Datagram Protocol";
                    }
                  }
                }
                leaf local-ip {
                  type inet:ipv4-address {
                    tailf:info
                      "A.B.C.D;;Inside local IP address";
                  }
                }
                leaf local-port {
                  type uint16 {
                    tailf:info
                      "<1-65535>;;Local UDP/TCP port";
                    range "1..65535";
                  }
                }
                leaf global-ip {
                  type inet:ipv4-address {
                    tailf:info
                      "A.B.C.D;;Inside global IP address";
                  }
                }
                leaf global-port {
                  type uint16 {
                    tailf:info
                      "<1-65535>;;Global UDP/TCP port";
                    range "1..65535";
                  }
                }
                uses ip-nat-inside-souce-static-grouping;
              }
              list nat-static-transport-interface-list {
                tailf:cli-drop-node-name;
                tailf:cli-suppress-mode;
                tailf:cli-delete-when-empty;
                tailf:cli-compact-syntax;
                tailf:cli-sequence-commands {
                  tailf:cli-reset-siblings;
                }
                tailf:cli-incomplete-command;
                key "proto local-ip local-port";
                leaf proto {
                  type enumeration {
                    enum "tcp" {
                      tailf:info
                        "Transmission Control Protocol";
                    }
                    enum "udp" {
                      tailf:info
                        "User Datagram Protocol";
                    }
                  }
                }
                leaf local-ip {
                  type inet:ipv4-address {
                    tailf:info
                      "A.B.C.D;;Inside local IP address";
                  }
                }
                leaf local-port {
                  type uint16 {
                    tailf:info
                      "<1-65535>;;Local UDP/TCP port";
                    range "1..65535";
                  }
                }
                container interface {
                  tailf:info
                    "Specify interface for global address";
                  tailf:cli-flatten-container;
                  tailf:cli-compact-syntax;
                  uses interface-name-grouping;
                }
                leaf global-port {
                  tailf:cli-drop-node-name;
                  type uint16 {
                    tailf:info
                      "<1-65535>;;Global UDP/TCP port";
                    range "1..65535";
                  }
                }
              }
            }
            list route-map {
              tailf:info
                "Specify route-map";
              tailf:cli-suppress-mode;
              tailf:cli-delete-when-empty;
              tailf:cli-compact-syntax;
              tailf:cli-sequence-commands {
                tailf:cli-reset-all-siblings;
              }
              tailf:cli-incomplete-command;
              key "id";
              leaf id {
                type string {
                  tailf:info
                    "WORD;;Route-map name";
                }
              }
              uses ip-nat-inside-grouping;
            }
          }
          container destination {
            tailf:info
              "Destination address translation";
            list list {
              tailf:info
                "Specify access list describing global addresses";
              tailf:cli-suppress-mode;
              tailf:cli-delete-when-empty;
              tailf:cli-compact-syntax;
              tailf:cli-sequence-commands {
                tailf:cli-reset-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              leaf pool {
                tailf:info
                  "Name pool of local addresses";
                type string;
                tailf:non-strict-leafref {
                  path "/ncs:devices/ncs:device/ncs:config/ios:ip/nat/pool/id" {
                    tailf:xpath-root 3;
                  }
                }
              }
              leaf redundancy {
                tailf:info
                  "NAT redundancy operation";
                tailf:cli-optional-in-sequence;
                type uint8 {
                  tailf:info
                    "<1-2>;;IP redundancy ID";
                  range "1..2";
                }
              }
              leaf mapping-id {
                tailf:info
                  "Associate a mapping id to this mapping";
                type uint32 {
                  tailf:info
                    "<1-2147483647>;;Stateful NAT mapping id";
                  range "1..2147483647";
                }
              }
            }
          }
        }
        container outside {
          tailf:info
            "Outside address translation";
          container source {
            tailf:info
              "Source address translation";
            list list {
              tailf:info
                "Specify access list describing global addresses";
              tailf:cli-suppress-mode;
              tailf:cli-delete-when-empty;
              tailf:cli-compact-syntax;
              tailf:cli-sequence-commands {
                tailf:cli-reset-siblings;
              }
              key "id";
              leaf id {
                type union {
                  type uint16 {
                    tailf:info
                      "<1-2699>;;Access list number for global addresses";
                    range "1..2699";
                  }
                  type string {
                    tailf:info
                      "WORD;;Access list name for global addresses";
                  }
                }
              }
              leaf pool {
                tailf:info
                  "Name pool of local addresses";
                type string;
                tailf:non-strict-leafref {
                  path "/ncs:devices/ncs:device/ncs:config/ios:ip/nat/pool/id" {
                    tailf:xpath-root 3;
                  }
                }
              }
              leaf mapping-id {
                tailf:info
                  "Associate a mapping id to this mapping";
                tailf:cli-optional-in-sequence;
                type uint32 {
                  tailf:info
                    "<1-2147483647>;;Stateful NAT mapping id";
                  range "1..2147483647";
                }
              }
              leaf vrf {
                tailf:info
                  "Specify vrf";
                tailf:cli-optional-in-sequence;
                tailf:cli-diff-dependency "/ios:ip/vrf" {
                  tailf:xpath-root 3;
                }
                tailf:cli-diff-dependency "/ios:vrf/definition" {
                  tailf:xpath-root 3;
                }
                type string {
                  tailf:info
                    "WORD;;vrf name";
                }
              }
              leaf add-route {
                tailf:info
                  "Add a static route for outside local address";
                type empty;
              }
            }
            list route-map {
              tailf:info
                "Specify route-map";
              tailf:cli-suppress-mode;
              tailf:cli-delete-when-empty;
              tailf:cli-compact-syntax;
              tailf:cli-sequence-commands {
                tailf:cli-reset-siblings;
              }
              key "id";
              leaf id {
                type string {
                  tailf:info
                    "WORD;;Route-map name";
                }
              }
              leaf pool {
                tailf:info
                  "Name pool of local addresses";
                type string;
                tailf:non-strict-leafref {
                  path "/ncs:devices/ncs:device/ncs:config/ios:ip/nat/pool/id" {
                    tailf:xpath-root 3;
                  }
                }
              }
              leaf mapping-id {
                tailf:info
                  "Associate a mapping id to this mapping";
                tailf:cli-optional-in-sequence;
                type uint32 {
                  tailf:info
                    "<1-2147483647>;;Stateful NAT mapping id";
                  range "1..2147483647";
                }
              }
              leaf vrf {
                tailf:info
                  "Specify vrf";
                tailf:cli-optional-in-sequence;
                tailf:cli-diff-dependency "/ios:ip/vrf" {
                  tailf:xpath-root 3;
                }
                tailf:cli-diff-dependency "/ios:vrf/definition" {
                  tailf:xpath-root 3;
                }
                type string {
                  tailf:info
                    "WORD;;vrf name";
                }
              }
              leaf add-route {
                tailf:info
                  "Add a static route for outside local address";
                type empty;
              }
            }
          }
        }
      }
      container route {
        tailf:info
          "Establish static routes";
        tailf:cli-diff-dependency "/ios:ip/vrf" {
          tailf:xpath-root 3;
        }
        tailf:cli-diff-dependency "/ios:vrf/definition" {
          tailf:xpath-root 3;
        }
        tailf:cli-diff-dependency "/ios:interface" {
          tailf:xpath-root 3;
        }
        container static {
          tailf:info
            "Allow static routes";
          leaf adjust-time {
            tailf:info
              "Time period for adjusting static routes";
            tailf:cli-full-command;
            type uint8 {
              tailf:info
                "<1-60>;;Adjustment time in seconds";
              range "1..60";
            }
          }
          leaf inter-vrf {
            tailf:info
              "Across VRF interfaces";
            tailf:cli-boolean-no;
            tailf:cli-full-command;
            type boolean;
            default "true";
          }
          container bfd {
            tailf:info
              "BFD tracked";
            list ip-route-bfd-forwarding-list {
              tailf:cli-drop-node-name;
              tailf:cli-suppress-mode;
              tailf:cli-delete-when-empty;
              tailf:cli-compact-syntax;
              key "interface ip-address";
              leaf interface {
                type string {
                  tailf:info
                    "WORD;;Interface name";
                }
              }
              leaf ip-address {
                type union {
                  type inet:ipv4-address {
                    tailf:info
                      "A.B.C.D;;Gateway IP address";
                  }
                  type enumeration {
                    enum "multicast" {
                      tailf:info
                        "multicast route";
                    }
                  }
                }
              }
              leaf group {
                tailf:info
                  "assign a bfd group";
                type string {
                  tailf:info
                    "WORD;;bfd group name";
                }
              }
            }
          }
        }
        leaf profile {
          tailf:info
            "Enable IP routing table profile";
          tailf:cli-full-command;
          type empty;
        }
        uses ip-route-grouping;
        list vrf {
          tailf:info
            "Configure static route for a VPN Routing/Forwarding instance";
          tailf:cli-suppress-mode;
          tailf:cli-delete-when-empty;
          tailf:cli-compact-syntax;
          tailf:cli-reset-container;
          tailf:cli-incomplete-command;
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding instance name";
            }
          }
          uses ip-route-grouping;
        }
      }
      container explicit-path {
        tailf:info
          "Configure explicit-path";
        list identifier {
          tailf:info
            "Specify explicit path by number";
          tailf:cli-mode-name "cfg-ip-expl-path";
          key "number";
          leaf number {
            type uint16 {
              tailf:info
                "<1-65535>;;Enter number";
              range "1..65535";
            }
          }
          leaf mode {
            tailf:cli-drop-node-name;
            tailf:cli-hide-in-submode;
            type enumeration {
              enum "enable" {
                tailf:info
                  "enable the explicit path";
              }
              enum "disable" {
                tailf:info
                  "disable the explicit path";
              }
            }
          }
          list index {
            tailf:info
              "Specify entry index ";
            tailf:cli-suppress-mode;
            tailf:cli-delete-when-empty;
            tailf:cli-compact-syntax;
            key "id";
            leaf id {
              type uint16 {
                tailf:info
                  "<1-65535>;;Entry index number";
              }
            }
            choice address-choice {
              leaf next-address {
                tailf:info
                  "Specify the next address in the path";
                tailf:cli-no-name-on-delete;
                tailf:cli-no-value-on-delete;
                type inet:ipv4-address {
                  tailf:info
                    "WORD;;Enter IP address (A.B.C.D)";
                }
              }
              leaf exclude-address {
                tailf:info
                  "Exclude an address from subsequent partial path segments";
                tailf:cli-no-name-on-delete;
                tailf:cli-no-value-on-delete;
                type inet:ipv4-address {
                  tailf:info
                    "WORD;;Enter IP address (A.B.C.D)";
                }
              }
            }
          }
        }
        list name {
          tailf:info
            "Specify explicit path by name";
          tailf:cli-mode-name "cfg-ip-expl-path";
          key "name";
          leaf name {
            type string {
              tailf:info
                "WORD;;Enter name";
            }
          }
          leaf mode {
            tailf:cli-drop-node-name;
            tailf:cli-hide-in-submode;
            type enumeration {
              enum "enable" {
                tailf:info
                  "enable the explicit path";
              }
              enum "disable" {
                tailf:info
                  "disable the explicit path";
              }
            }
          }
          list index {
            tailf:info
              "Specify entry index ";
            tailf:cli-suppress-mode;
            tailf:cli-delete-when-empty;
            tailf:cli-compact-syntax;
            key "id";
            leaf id {
              type uint16 {
                tailf:info
                  "<1-65535>;;Entry index number";
              }
            }
            choice address-choice {
              leaf next-address {
                tailf:info
                  "Specify the next address in the path";
                tailf:cli-no-name-on-delete;
                tailf:cli-no-value-on-delete;
                type inet:ipv4-address {
                  tailf:info
                    "WORD;;Enter IP address (A.B.C.D)";
                }
              }
              leaf exclude-address {
                tailf:info
                  "Exclude an address from subsequent partial path segments";
                tailf:cli-no-name-on-delete;
                tailf:cli-no-value-on-delete;
                type inet:ipv4-address {
                  tailf:info
                    "WORD;;Enter IP address (A.B.C.D)";
                }
              }
            }
          }
        }
      }
      container tacacs {
        tailf:info
          "TACACS configuration commands";
        container source-interface {
          tailf:info
            "Specify interface for source address in TACACS packets";
          uses interface-name-grouping;
        }
      }
      container access-list {
        tailf:info
          "Named access list";
        tailf:cli-incomplete-command;
        tailf:cli-compact-syntax;
        container standard {
          tailf:info
            "Standard Access List";
          tailf:cli-incomplete-command;
          list std-named-acl {
            tailf:cli-drop-node-name;
            tailf:cli-full-command;
            tailf:cli-no-key-completion;
            tailf:cli-mode-name "config-std-nacl";
            key "name";
            leaf name {
              type std-ip-acl-type;
            }
            list std-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-drop-node-name;
                tailf:cli-multi-word-key;
                type string {
                  tailf:info
                    "deny;;Specify packets to reject
                     permit;;Specify packets to forwards
                     remark;;Access list entry comment";
                  pattern '(permit .*)|(deny .*)|(remark .*)|([0-9]+.*)|(dynamic .*)|(evaluate .*)';
                }
              }
            }
          }
        }
        container extended {
          tailf:info
            "Extended Access List";
          tailf:cli-incomplete-command;
          list ext-named-acl {
            tailf:cli-drop-node-name;
            tailf:cli-full-command;
            tailf:cli-mode-name "config-ext-nacl";
            tailf:cli-explicit-exit;
            key "name";
            leaf name {
              type ext-acl-type;
            }
            list ext-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-drop-node-name;
                tailf:cli-multi-word-key;
                type string {
                  tailf:info
                    "deny;;Specify packets to reject
                     permit;;Specify packets to forwards
                     remark;;Access list entry comment";
                  pattern '(permit .*)|(deny .*)|(remark .*)|([0-9]+.*)|(dynamic .*)|(evaluate .*)';
                }
              }
            }
          }
        }
      }
      container prefix-list {
        tailf:info
          "Build a prefix list";
        list prefixes {
          tailf:cli-drop-node-name;
          tailf:cli-suppress-mode;
          tailf:cli-delete-when-empty;
          tailf:cli-compact-syntax;
          key "name";
          leaf name {
            type string {
              tailf:info
                "WORD;;Name of a prefix list";
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            tailf:info
              "Prefix-list specific description";
            tailf:cli-multi-value;
            tailf:cli-full-command;
            type string {
              tailf:info
                "LINE;;Up to 80 characters describing this prefix-list";
              length "1..80";
            }
          }
          leaf permit {
            tailf:info
              "Specify packets to forward";
            type ios:ipv4-prefix {
              tailf:info
                "A.B.C.D  IP prefix <network>/<length>, e.g., 35.0.0.0/8";
            }
          }
          list seq {
            tailf:info
              "sequence number of an entry";
            tailf:cli-suppress-mode;
            tailf:cli-delete-when-empty;
            tailf:cli-compact-syntax;
            tailf:cli-remove-before-change;
            key "no";
            leaf no {
              type uint32 {
                tailf:info
                  "<1-4294967294>;;Sequence number";
                range "1..4294967294";
              }
              tailf:key-default "10";
            }
            container deny {
              tailf:info
                "Specify packets to reject";
              tailf:cli-sequence-commands {
                tailf:cli-reset-all-siblings;
              }
              tailf:cli-compact-syntax;
              leaf ip {
                tailf:cli-drop-node-name;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  range "1..32";
                  tailf:info
                    "<1-32>;;Minimum prefix length";
                }
              }
              leaf le {
                tailf:info
                  "Maximum prefix length to be matched";
                tailf:cli-full-command;
                type uint8 {
                  range "1..32";
                  tailf:info
                    "<1-32>;;Maximum prefix length";
                }
              }
            }
            container permit {
              tailf:info
                "Specify packets to forward";
              tailf:cli-sequence-commands {
                tailf:cli-reset-all-siblings;
              }
              tailf:cli-compact-syntax;
              leaf ip {
                tailf:cli-drop-node-name;
                tailf:cli-remove-before-change;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  tailf:info
                    "<1-32>;;Minimum prefix length";
                  range "1..32";
                }
              }
              leaf le {
                tailf:info
                  "Maximum prefix length to be matched";
                tailf:cli-full-command;
                type uint8 {
                  tailf:info
                    "<1-32>;;Maximum prefix length";
                  range "1..32";
                }
              }
            }
          }
        }
        leaf sequence-number {
          tailf:info
            "Include/exclude sequence numbers in NVGEN";
          tailf:cli-full-command;
          type empty;
        }
      }
      container radius {
        tailf:info
          "RADIUS configuration commands";
        container source-interface {
          tailf:info
            "Specify interface for source address in RADIUS packets";
          uses interface-name-grouping;
        }
      }
      container sla {
        tailf:info
          "IP Service Level Agreement";
        container auto {
          tailf:info
            "IP SLAs Auto Configuration";
          leaf discovery {
            tailf:info
              "Enable auto-discovery";
            type empty;
          }
        }
        container responder {
          tailf:info
            "Enable IP SLAs Responder";
          presence "true";
        }
        container logging {
          tailf:info
            "Enable Syslog";
          leaf traps {
            tailf:info
              "Enable syslog traps";
            type empty;
          }
        }
        list ip-sla-list {
          tailf:cli-drop-node-name;
          tailf:cli-mode-name "config-ip-sla";
          tailf:cli-remove-before-change;
          tailf:cli-full-command;
          key "id";
          leaf id {
            type uint32 {
              tailf:info
                "<1-2147483647>;;Entry Number";
              range "1..2147483647";
            }
          }
          list udp-jitter {
            tailf:info
              "UDP Jitter Operation";
            tailf:cli-mode-name "config-ip-sla-jitter";
            key "destination destination-port";
            leaf destination {
              type union {
                type inet:host {
                  tailf:info
                    "WORD;;Hostname or A.B.C.D IPv4 address";
                }
                type inet:ipv6-address {
                  tailf:info
                    "X:X:X:X::X;;IPv6 address";
                }
              }
            }
            leaf destination-port {
              type uint16 {
                tailf:info
                  "<0-65535>;;Port Number.";
              }
            }
            leaf source-ip {
              tailf:info
                "Source address";
              tailf:cli-hide-in-submode;
              type union {
                type inet:host {
                  tailf:info
                    "Hostname or A.B.C.D IPv4 address";
                }
                type inet:ipv6-address {
                  tailf:info
                    "X:X:X:X::X;;IPv6 address";
                }
              }
            }
            leaf source-port {
              tailf:info
                "Source Port";
              tailf:cli-hide-in-submode;
              type uint16 {
                tailf:info
                  "<1-65535>;;Port Number";
                range "1..65535";
              }
            }
            leaf codec {
              tailf:info
                "codec type to be configured";
              tailf:cli-hide-in-submode;
              type enumeration {
                enum "g711alaw" {
                  tailf:info
                    "G.711 A Law 64000 bps";
                }
                enum "g711ulaw" {
                  tailf:info
                    "G.711 U Law 64000 bps";
                }
                enum "g729a" {
                  tailf:info
                    "G.729 8000 bps";
                }
              }
            }
            leaf codec-numpackets {
              tailf:info
                "Number of Packets to be transmitted";
              tailf:cli-hide-in-submode;
              when '../codec' {
                tailf:xpath-root 3;
              }
              type uint32 {
                tailf:info
                  "<1-60000>;;Number of Packets";
                range "1..60000";
              }
            }
            leaf interval {
              tailf:info
                "Inter Packet Interval";
              tailf:cli-hide-in-submode;
              type uint32 {
                tailf:info
                  "<4-60000>;;Delay (default 20)";
              }
              default "20";
            }
            leaf control {
              tailf:info
                "Enable or disable control packets";
              tailf:cli-hide-in-submode;
              type enumeration {
                enum "disable" {
                  tailf:info
                    "Disable control packets exchange";
                }
                enum "enable" {
                  tailf:info
                    "Enable control packets exchange (default)";
                }
              }
              default "enable";
            }
            uses ip-sla-proto-grouping;
          }
          list icmp-echo {
            tailf:info
              "ICMP Echo Operation";
            tailf:cli-mode-name "config-ip-sla-echo";
            key "host";
            leaf host {
              type inet:host {
                tailf:info
                  "Hostname or A.B.C.D  Destination IP address or hostname, broadcast disallowed";
              }
            }
            choice source-choice {
              container source-interface {
                tailf:info
                  "Source Interface (ingress icmp packet interface)";
                tailf:cli-hide-in-submode;
                tailf:cli-flatten-container;
                uses interface-name-grouping;
              }
              leaf source-ip {
                tailf:info
                  "Source Address";
                tailf:cli-hide-in-submode;
                type inet:host {
                  tailf:info
                    "Hostname or A.B.C.D;;IP address or hostname, broadcast disallowed";
                }
              }
            }
            uses ip-sla-proto-grouping;
          }
          list udp-echo {
            tailf:info
              "UDP Echo Operation";
            tailf:cli-mode-name "config-ip-sla-udp";
            key "host port";
            leaf host {
              type inet:host {
                tailf:info
                  "Hostname or A.B.C.D;;Destination IP address or hostname, broadcast disallowed";
              }
            }
            leaf port {
              type uint16 {
                tailf:info
                  "<0-65535>;;Port Number";
              }
            }
            leaf control {
              tailf:info
                "Enable or disable control packets";
              tailf:cli-hide-in-submode;
              type enumeration {
                enum "disable" {
                  tailf:info
                    "Disable control packets exchange";
                }
                enum "enable" {
                  tailf:info
                    "Enable control packets exchange (default)";
                }
              }
            }
            leaf source-ip {
              tailf:info
                "Source Address";
              tailf:cli-hide-in-submode;
              type inet:host {
                tailf:info
                  "Hostname or A.B.C.D;;IP address or hostname, broadcast disallowed";
              }
            }
            leaf source-port {
              tailf:info
                "source-port;;Source Port";
              tailf:cli-hide-in-submode;
              type uint16 {
                tailf:info
                  "<1-65535>;;Port Number";
                range "1..65535";
              }
            }
            uses ip-sla-proto-grouping;
          }
          container ethernet {
            tailf:info
              "Ethernet Operations";
            container y1731 {
              tailf:info
                "Y1731 Ethernet OAM Performance Measurement Operations";
              list delay {
                tailf:info
                  "Y1731 Delay and Delay Variation Operation";
                tailf:cli-compact-syntax;
                tailf:cli-sequence-commands;
                tailf:cli-mode-name "config-sla-y1731-delay";
                key "name";
                leaf name {
                  type enumeration {
                    enum "1DM" {
                      tailf:info
                        "1DM frames";
                    }
                    enum "DMM" {
                      tailf:info
                        "DMM/DMR frames";
                    }
                    enum "DMMv1" {
                      tailf:info
                        "DMMv1 frames";
                    }
                  }
                }
                leaf burst {
                  tailf:info
                    "enable bursting of delay frames";
                  tailf:cli-optional-in-sequence;
                  type empty;
                }
                leaf domain {
                  tailf:info
                    "Specify Domain name";
                  type string {
                    tailf:info
                      "WORD;;Specify the Ethernet OAM domain";
                  }
                }
                choice evc-or-vlan {
                  leaf evc {
                    tailf:info
                      "Specify the Ethernet Virtual Circuit Identifier";
                    type string {
                      tailf:info
                        "WORD  Specify the EVC Identifier value";
                    }
                  }
                  leaf vlan {
                    tailf:info
                      "Specify the VLAN";
                    type uint16 {
                      tailf:info
                        "<1-4096>;;Specify Vlan value";
                      range "1..4096";
                    }
                  }
                }
                choice mpid-or-mac {
                  leaf mac-address {
                    tailf:info
                      "Specify the remote mac-address";
                    type string {
                      tailf:info
                        "H.H.H;;Destination mac-address value";
                    }
                  }
                  leaf mpid {
                    tailf:info
                      "Specify the remote MPID";
                    type uint16 {
                      tailf:info
                        "<1-8191>;;Specify MPID value";
                      range "1..8191";
                    }
                  }
                }
                leaf cos {
                  tailf:info
                    "Specify the Class of Service";
                  type uint8 {
                    tailf:info
                      "<0-7>;;Specify CoS value";
                    range "0..7";
                  }
                }
                container source {
                  tailf:info
                    "Specify the local MPID or MAC-Address";
                  tailf:cli-flatten-container;
                  choice mpid-or-mac {
                    leaf mac-address {
                      tailf:info
                        "Specify the remote mac-address";
                      type string {
                        tailf:info
                          "H.H.H;;Destination mac-address value";
                      }
                    }
                    leaf mpid {
                      tailf:info
                        "Specify the remote MPID";
                      type uint16 {
                        tailf:info
                          "<1-8191>;;Specify MPID value";
                        range "1..8191";
                      }
                    }
                  }
                }
              }
              container delay-receive {
                tailf:cli-drop-node-name;
                container delay {
                  tailf:info
                    "Y1731 Delay and Delay Variation Operation";
                  list receive {
                    tailf:info
                      "Receive only operation";
                    tailf:cli-compact-syntax;
                    tailf:cli-sequence-commands;
                    tailf:cli-mode-name "config-sla-y1731-delay";
                    key "name";
                    leaf name {
                      type enumeration {
                        enum "1DM" {
                          tailf:info
                            "1DM frames";
                        }
                      }
                    }
                    leaf domain {
                      tailf:info
                        "Specify Domain name";
                      type string {
                        tailf:info
                          "WORD;;Specify the Ethernet OAM domain";
                      }
                    }
                    choice evc-or-vlan {
                      leaf evc {
                        tailf:info
                          "Specify the Ethernet Virtual Circuit Identifier";
                        type string {
                          tailf:info
                            "WORD  Specify the EVC Identifier value";
                        }
                      }
                      leaf vlan {
                        tailf:info
                          "Specify the VLAN";
                        type uint16 {
                          tailf:info
                            "<1-4096>;;Specify Vlan value";
                          range "1..4096";
                        }
                      }
                    }
                    leaf cos {
                      tailf:info
                        "Specify the Class of Service";
                      type uint8 {
                        tailf:info
                          "<0-7>;;Specify CoS value";
                        range "0..7";
                      }
                    }
                    choice mpid-or-mac {
                      leaf mac-address {
                        tailf:info
                          "Specify the remote mac-address";
                        type string {
                          tailf:info
                            "H.H.H;;Destination mac-address value";
                        }
                      }
                      leaf mpid {
                        tailf:info
                          "Specify the remote MPID";
                        type uint16 {
                          tailf:info
                            "<1-8191>;;Specify MPID value";
                          range "1..8191";
                        }
                      }
                    }
                  }
                }
              }
              list loss {
                tailf:info
                  "Y1731 Loss Operation";
                tailf:cli-compact-syntax;
                tailf:cli-sequence-commands;
                tailf:cli-mode-name "config-sla-y1731-loss";
                key "name";
                leaf name {
                  type enumeration {
                    enum "LMM" {
                      tailf:info
                        "LMM/LMR frames";
                    }
                    enum "SLM" {
                      tailf:info
                        "SLM/SLR frames";
                    }
                  }
                }
                leaf burst {
                  tailf:info
                    "enable bursting of SLM frames";
                  tailf:cli-hide-in-submode;
                  tailf:cli-optional-in-sequence;
                  type empty;
                }
                leaf domain {
                  tailf:info
                    "Specify Domain name";
                  tailf:cli-hide-in-submode;
                  type string {
                    tailf:info
                      "WORD;;Specify the Ethernet OAM domain";
                  }
                }
                choice evc-or-vlan {
                  leaf evc {
                    tailf:info
                      "Specify the Ethernet Virtual Circuit Identifier";
                    tailf:cli-hide-in-submode;
                    type string {
                      tailf:info
                        "WORD  Specify the EVC Identifier value";
                    }
                  }
                  leaf vlan {
                    tailf:info
                      "Specify the VLAN";
                    tailf:cli-hide-in-submode;
                    type uint16 {
                      tailf:info
                        "<1-4096>;;Specify Vlan value";
                      range "1..4096";
                    }
                  }
                }
                choice mpid-or-mac {
                  leaf mac-address {
                    tailf:info
                      "Specify the remote mac-address";
                    tailf:cli-hide-in-submode;
                    type string {
                      tailf:info
                        "H.H.H;;Destination mac-address value";
                    }
                  }
                  leaf mpid {
                    tailf:info
                      "Specify the remote MPID";
                    tailf:cli-hide-in-submode;
                    type uint16 {
                      tailf:info
                        "<1-8191>;;Specify MPID value";
                      range "1..8191";
                    }
                  }
                }
                leaf cos {
                  tailf:info
                    "Specify the Class of Service";
                  tailf:cli-hide-in-submode;
                  type uint8 {
                    tailf:info
                      "<0-7>;;Specify CoS value";
                    range "0..7";
                  }
                }
                container source {
                  tailf:info
                    "Specify the local MPID or MAC-Address";
                  tailf:cli-hide-in-submode;
                  tailf:cli-flatten-container;
                  choice mpid-or-mac {
                    leaf mac-address {
                      tailf:info
                        "Specify the remote mac-address";
                      type string {
                        tailf:info
                          "H.H.H;;Destination mac-address value";
                      }
                    }
                    leaf mpid {
                      tailf:info
                        "Specify the remote MPID";
                      type uint16 {
                        tailf:info
                          "<1-8191>;;Specify MPID value";
                        range "1..8191";
                      }
                    }
                  }
                }
                container availability {
                  tailf:info
                    "Specify the availability parameters";
                  leaf algorithm {
                    tailf:info
                      "Specify the algorithm to use";
                    type enumeration {
                      enum "sliding-window" {
                        tailf:info
                          "Use a sliding window";
                      }
                      enum "static-window" {
                        tailf:info
                          "Use a static window";
                      }
                    }
                  }
                }
              }
            }
          }
        }
        list schedule {
          tailf:info
            "IP SLAs Entry Scheduling";
          tailf:cli-suppress-mode;
          tailf:cli-delete-when-empty;
          tailf:cli-compact-syntax;
          tailf:cli-incomplete-command;
          key "operation-number";
          leaf operation-number {
            type uint32 {
              tailf:info
                "<1-2147483647>;;Entry number";
            }
            tailf:non-strict-leafref {
              path "../../ip-sla-list/id";
            }
          }
          leaf life {
            tailf:info
              "Length of time to execute in seconds";
            type union {
              type enumeration {
                enum "forever" {
                  tailf:info
                    "continue running forever";
                }
              }
              type uint32 {
                tailf:info
                  "<0-2147483647>;;Life seconds";
              }
            }
          }
          container start-time {
            tailf:info
              "When to start this entry";
            tailf:cli-flatten-container;
            tailf:cli-compact-syntax;
            choice start-time-choice {
              leaf after {
                tailf:info
                  "Start after a certain amount of time from now";
                type string {
                  tailf:info
                    "hh:mm:ss;;Start after (hh:mm:ss) has elapsed";
                }
              }
              leaf now {
                tailf:info
                  "Start now";
                type empty;
              }
              leaf pending {
                tailf:info
                  "Start pending";
                type empty;
              }
              leaf time {
                tailf:cli-drop-node-name;
                type string {
                  tailf:info
                    "hh:mm[:ss];;Start time (hh:mm:[ss])";
                }
              }
            }
          }
          leaf ageout {
            tailf:info
              "How long to keep this Entry when inactive";
            type uint32 {
              tailf:info
                "<0-2073600>;;Ageout Seconds";
            }
          }
          leaf recurring {
            tailf:info
              "Probe to be scheduled automatically every day";
            type empty;
          }
        }
        list reaction-configuration {
          tailf:info
            "IP SLAs Reaction-Configuration";
          tailf:cli-suppress-mode;
          tailf:cli-delete-when-empty;
          tailf:cli-compact-syntax;
          tailf:cli-sequence-commands {
            tailf:cli-reset-all-siblings;
          }
          tailf:cli-incomplete-command;
          key "operation-number";
          leaf operation-number {
            type uint32 {
              tailf:info
                "<1-2147483647>;;Entry number";
            }
            tailf:non-strict-leafref {
              path "../../ip-sla-list/id";
            }
          }
          leaf react {
            tailf:info
              "Reaction variable to be configured";
            type string {
              tailf:info
                "monitored-element";
            }
          }
          leaf action-type {
            tailf:info
              "IP SLAs Reaction Action Type";
            tailf:cli-break-sequence-commands;
            type enumeration {
              enum "none" {
                tailf:info
                  "No action";
              }
              enum "trapAndTrigger" {
                tailf:info
                  "Trap and Trigger action";
              }
              enum "trapOnly" {
                tailf:info
                  "Trap Only action";
              }
              enum "triggerOnly" {
                tailf:info
                  "Trigger Only action";
              }
            }
          }
          container threshold-value {
            tailf:info
              "Threshold value";
            tailf:cli-flatten-container;
            tailf:cli-compact-syntax;
            tailf:cli-sequence-commands;
            leaf upper-threshold {
              tailf:cli-drop-node-name;
              type uint16 {
                tailf:info
                  "<1-60000>;;Upper limit for Threshold";
              }
            }
            leaf lower-threshold {
              tailf:cli-drop-node-name;
              type uint16 {
                tailf:info
                  "<1-60000>;;Lower limit for Threshold";
              }
            }
          }
          container threshold-type {
            tailf:info
              "Threshold Type";
            tailf:cli-flatten-container;
            tailf:cli-compact-syntax;
            choice threshold-type-choice {
              leaf average {
                tailf:info
                  "Average over N attempts";
                type uint8 {
                  tailf:info
                    "<1-16>;;N Value";
                  range "1..16";
                }
              }
              leaf consecutive {
                tailf:info
                  "Consecutive occurrences";
                type uint8 {
                  tailf:info
                    "<1-16>;;Number of occurrences";
                  range "1..16";
                }
              }
              leaf immediate {
                tailf:info
                  "React immediately";
                type empty;
              }
              leaf never {
                tailf:info
                  "Never react";
                type empty;
              }
              leaf xOfy {
                tailf:info
                  "X out of Y occurrences";
                type uint8 {
                  tailf:info
                    "<1-16>;;X Value";
                  range "1..16";
                }
              }
            }
          }
        }
        container enable {
          tailf:info
            "Enable Event Notifications";
          leaf reaction-alerts {
            tailf:info
              "Enable Reaction Alert Notifications";
            type empty;
          }
        }
      }
    }
    container isdn {
      tailf:ncs-device-type "cli-ned";
      tailf:display-when "not(../../ncs:module) or ../../ncs:module[ncs:name='tailf-ned-cisco-ios']";
      tailf:info
        "ISDN configuration commands";
      leaf switch-type {
        tailf:info
          "Select the ISDN switch type";
        tailf:cli-full-command;
        type string {
          pattern 'primary.*';
        }
      }
    }
    container vmps {
      tailf:ncs-device-type "cli-ned";
      tailf:display-when "not(../../ncs:module) or ../../ncs:module[ncs:name='tailf-ned-cisco-ios']";
      tailf:info
        "VMPS settings";
      leaf reconfirm {
        tailf:info
          "Set VMPS reconfirm interval";
        type uint8 {
          tailf:info
            "Number of minutes between reconfirmations";
          range "0..120";
        }
      }
      leaf retry {
        tailf:info
          "Set VMPS retry count";
        type uint8 {
          tailf:info
            "<1-10>;;Retry count per server";
          range "1..10";
        }
      }
      list server {
        tailf:info
          "Configure server IP address";
        tailf:cli-suppress-mode;
        tailf:cli-delete-when-empty;
        tailf:cli-compact-syntax;
        key "name";
        leaf name {
          type host-type {
            tailf:info
              "Hostname or A.B.C.D;;IP address";
          }
        }
        leaf primary {
          tailf:info
            "Specify primary server";
          type empty;
        }
      }
    }
    container ipv6 {
      tailf:ncs-device-type "cli-ned";
      tailf:display-when "not(../../ncs:module) or ../../ncs:module[ncs:name='tailf-ned-cisco-ios']";
      tailf:info
        "Global IPv6 configuration commands";
      leaf unicast-routing {
        tailf:info
          "Enable unicast routing";
        type empty;
      }
      leaf source-route {
        tailf:info
          "Process packets with source routing header options";
        tailf:cli-show-no;
        type empty;
      }
      container cef {
        tailf:info
          "Cisco Express Forwarding";
        tailf:cli-display-separated;
        tailf:cli-show-no;
        presence "true";
        container accounting {
          tailf:info
            "Enable CEF accounting";
          tailf:cli-compact-syntax;
          leaf per-prefix {
            tailf:info
              "Enable per prefix accounting";
            type empty;
          }
          leaf prefix-length {
            tailf:info
              "Enable prefix length accounting";
            type empty;
          }
        }
        leaf distributed {
          tailf:info
            "Distributed Cisco Express Forwarding";
          tailf:cli-full-command;
          type empty;
        }
      }
      leaf multicast-routing {
        tailf:info
          "Enable IPv6 multicast";
        type empty;
      }
      container multicast {
        tailf:info
          "Configure multicast related commands";
        container rpf {
          tailf:info
            "Configure multicast RPF related commands";
          container backoff {
            tailf:info
              "Backoff delay after unicast routing change";
            tailf:cli-compact-syntax;
            tailf:cli-sequence-commands {
              tailf:cli-reset-siblings;
            }
            leaf initial-delay {
              tailf:cli-drop-node-name;
              type uint16 {
                tailf:info
                  "<200-65535>;;Initial RPF backoff delay in milliseconds";
                range "200..65535";
              }
            }
            leaf max-delay {
              tailf:cli-drop-node-name;
              type uint16 {
                tailf:info
                  "<200-65535>;;Maximum RPF backoff delay in milliseconds";
                range "200..65535";
              }
            }
          }
          leaf use-bgp {
            tailf:info
              "Use BGP routes for multicast RPF lookup";
            type empty;
          }
        }
      }
      container route {
        tailf:info
          "Configure static routes";
        tailf:cli-diff-dependency "/ios:ip/vrf" {
          tailf:xpath-root 3;
        }
        tailf:cli-diff-dependency "/ios:vrf/definition" {
          tailf:xpath-root 3;
        }
        tailf:cli-diff-dependency "/ios:interface" {
          tailf:xpath-root 3;
        }
        list vrf {
          tailf:info
            "Configure static route for a VPN Routing/Forwarding instance";
          tailf:cli-suppress-mode;
          tailf:cli-delete-when-empty;
          tailf:cli-compact-syntax;
          tailf:cli-incomplete-command;
          key "name";
          leaf name {
            type string {
              tailf:info
                "WORD;;VRF name";
            }
          }
          uses ipv6-route-grouping;
        }
        uses ipv6-route-grouping;
      }
      container prefix-list {
        tailf:info
          "Build a prefix list";
        list prefixes {
          tailf:cli-drop-node-name;
          tailf:cli-suppress-mode;
          tailf:cli-delete-when-empty;
          key "name";
          leaf name {
            type string {
              tailf:info
                "WORD;;Name of a prefix list";
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            tailf:info
              "Prefix-list specific description";
            tailf:cli-multi-value;
            tailf:cli-full-command;
            type string {
              tailf:info
                "LINE;;Up to 80 characters describing this prefix-list";
              length "1..80";
            }
          }
          leaf permit {
            tailf:info
              "Specify packets to forward";
            type ios:ipv6-prefix {
              tailf:info
                "X:X:X:X::X/<0-128>;;IPv6 prefix <network>/<length>";
            }
          }
          list seq {
            tailf:info
              "sequence number of an entry";
            tailf:cli-suppress-mode;
            tailf:cli-delete-when-empty;
            key "no";
            leaf no {
              type uint32 {
                tailf:info
                  "<1-4294967294>;;Sequence number";
                range "1..4294967294";
              }
              tailf:key-default "10";
            }
            container deny {
              tailf:info
                "Specify packets to reject";
              tailf:cli-compact-syntax;
              tailf:cli-sequence-commands {
                tailf:cli-reset-all-siblings;
              }
              leaf ip {
                tailf:cli-drop-node-name;
                type ios:ipv6-prefix {
                  tailf:info
                    "X:X:X:X::X/<0-128>;;IPv6 prefix";
                }
              }
              leaf ge {
                tailf:info
                  "Minimum prefix length to be matched";
                tailf:cli-break-sequence-commands;
                type uint16 {
                  tailf:info
                    "<1-128>;;Minimum prefix length";
                  range "1..128";
                }
              }
              leaf le {
                tailf:info
                  "Maximum prefix length to be matched";
                tailf:cli-full-command;
                type uint16 {
                  tailf:info
                    "<1-128>;;Maximum prefix length";
                  range "1..128";
                }
              }
            }
            container permit {
              tailf:info
                "Specify packets to forward";
              tailf:cli-sequence-commands {
                tailf:cli-reset-all-siblings;
              }
              tailf:cli-compact-syntax;
              leaf ip {
                tailf:cli-drop-node-name;
                type ios:ipv6-prefix {
                  tailf:info
                    "X:X:X:X::X/<0-128>;;IPv6 prefix";
                }
              }
              leaf ge {
                tailf:info
                  "Minimum prefix length to be matched";
                tailf:cli-break-sequence-commands;
                type uint16 {
                  tailf:info
                    "<1-128>;;Minimum prefix length";
                  range "1..128";
                }
              }
              leaf le {
                tailf:info
                  "Maximum prefix length to be matched";
                tailf:cli-full-command;
                type uint16 {
                  tailf:info
                    "<1-128>;;Maximum prefix length";
                  range "1..128";
                }
              }
            }
          }
        }
        leaf sequence-number {
          tailf:info
            "Include/exclude sequence numbers in NVGEN";
          tailf:cli-full-command;
          type empty;
        }
      }
      container access-list {
        tailf:info
          "Configure access lists";
        tailf:cli-incomplete-command;
        tailf:cli-compact-syntax;
        list named-acl {
          tailf:cli-drop-node-name;
          tailf:cli-full-command;
          tailf:cli-no-key-completion;
          tailf:cli-mode-name "config-ipv6-acl";
          key "name";
          leaf name {
            type string {
              tailf:info
                "User selected string identifying this access list";
            }
          }
          list access-list-rule {
            tailf:cli-suppress-mode;
            tailf:cli-delete-when-empty;
            tailf:cli-drop-node-name;
            tailf:cli-compact-syntax;
            tailf:cli-show-long-obu-diffs;
            tailf:cli-case-sensitive;
            ordered-by user;
            key "rule";
            leaf rule {
              tailf:cli-drop-node-name;
              tailf:cli-multi-word-key;
              type string {
                tailf:info
                  "deny;;Specify packets to reject
                   permit;;Specify packets to forwards
                   remark;;Access list entry comment
                   sequence;;Sequence number for this entry";
                pattern '(deny .*)|(permit .*)|(remark .*)|(sequence .*)|(evaluate .*)';
              }
            }
          }
        }
      }
    }
    container subscriber {
      tailf:ncs-device-type "cli-ned";
      tailf:display-when "not(../../ncs:module) or ../../ncs:module[ncs:name='tailf-ned-cisco-ios']";
      tailf:info
        "Subscriber configuration";
      leaf templating {
        tailf:info
          "Configure subscriber templating";
        type empty;
      }
    }
    container multilink {
      tailf:ncs-device-type "cli-ned";
      tailf:display-when "not(../../ncs:module) or ../../ncs:module[ncs:name='tailf-ned-cisco-ios']";
      tailf:info
        "PPP multilink global configuration";
      leaf virtual-template {
        tailf:info
          "virtual-template interface";
        tailf:cli-full-command;
        type uint16 {
          tailf:info
            "<1-4095>;;virtual template number";
          range "1..4095";
        }
      }
      leaf bundle-name {
        tailf:info
          "Select method for naming multilink bundles";
        tailf:cli-full-command;
        type enumeration {
          enum "authenticated" {
            tailf:info
              "Use peer's authenticated name";
          }
          enum "both" {
            tailf:info
              "Use peer's authenticated name and endpoint discriminator";
          }
          enum "endpoint" {
            tailf:info
              "Use peer's endpoint discriminator";
          }
          enum "rfc" {
            tailf:info
              "Use peer and local authenticated name and endpoint discriminator";
          }
        }
      }
    }
    container archive {
      tailf:ncs-device-type "cli-ned";
      tailf:display-when "not(../../ncs:module) or ../../ncs:module[ncs:name='tailf-ned-cisco-ios']";
      tailf:info
        "Archive the configuration";
      tailf:cli-add-mode;
      tailf:cli-mode-name "config-archive";
      container log {
        tailf:info
          "Logging commands";
        container config {
          tailf:info
            "Logging changes to the running configuration";
          tailf:cli-add-mode;
          tailf:cli-mode-name "config-archive-log-cfg";
          tailf:cli-full-command;
          tailf:cli-incomplete-no;
          container logging {
            tailf:info
              "Modify config logging parameters";
            leaf enable {
              tailf:info
                "Enable the config logger";
              tailf:cli-full-command;
              type empty;
            }
            leaf size {
              tailf:info
                "Maximum number of logged commands that will be kept by the config log";
              tailf:cli-full-command;
              type uint16 {
                tailf:info
                  "<1-1000>;;Queue length (default 100)";
                range "1..1000";
              }
              default "100";
            }
          }
          leaf hidekeys {
            tailf:info
              "suppress output (e.g. passwords) when displaying logged commands";
            tailf:cli-full-command;
            type empty;
          }
        }
      }
      leaf path {
        tailf:info
          "path for backups";
        tailf:cli-full-command;
        type string {
          tailf:info
            "WORD;;Write archive path";
        }
      }
      leaf maximum {
        tailf:info
          "maximum number of backup copies";
        type uint8 {
          tailf:info
            "<1-14>;;maximum number of backup copies";
          range "1..14";
        }
      }
      leaf write-memory {
        tailf:info
          "Enable automatic backup generation during write memory";
        type empty;
      }
    }
    container key {
      tailf:ncs-device-type "cli-ned";
      tailf:display-when "not(../../ncs:module) or ../../ncs:module[ncs:name='tailf-ned-cisco-ios']";
      tailf:info
        "Key management";
      list chain {
        tailf:info
          "Key-chain management";
        tailf:cli-mode-name "config-keychain";
        key "name";
        leaf name {
          type string {
            tailf:info
              "WORD;;Key-chain name";
          }
        }
        list key {
          tailf:info
            "Configure a key";
          tailf:cli-mode-name "config-keychain-key";
          tailf:cli-full-command;
          key "id";
          leaf id {
            type uint32 {
              tailf:info
                "<0-2147483647>;;Key identifier";
              range "0..2147483647";
            }
          }
          container key-string {
            tailf:info
              "Set key string";
            tailf:cli-compact-syntax;
            tailf:cli-sequence-commands {
              tailf:cli-reset-siblings;
            }
            leaf encryption {
              tailf:cli-drop-node-name;
              tailf:cli-optional-in-sequence;
              type enumeration {
                enum "0" {
                  tailf:info
                    "Specifies an UNENCRYPTED password will follow";
                }
                enum "7" {
                  tailf:info
                    "Specifies HIDDEN password will follow";
                }
              }
            }
            leaf key {
              tailf:cli-drop-node-name;
              tailf:cli-full-command;
              tailf:cli-multi-value;
              type string {
                tailf:info
                  "LINE;;The UNENCRYPTED (cleartext) user password";
              }
            }
          }
        }
      }
    }
    list username {
      tailf:ncs-device-type "cli-ned";
      tailf:display-when "not(../ncs:module) or ../ncs:module[ncs:name='tailf-ned-cisco-ios']";
      tailf:info
        "Establish User Name Authentication";
      tailf:cli-suppress-mode;
      tailf:cli-delete-when-empty;
      tailf:cli-compact-syntax;
      key "name";
      leaf name {
        type string {
          tailf:info
            "WORD;;User name";
        }
      }
      container password {
        tailf:info
          "Specify the password for the user";
        tailf:cli-flatten-container;
        tailf:cli-compact-syntax;
        tailf:cli-sequence-commands;
        tailf:cli-reset-container;
        leaf encryption {
          tailf:cli-drop-node-name;
          tailf:cli-optional-in-sequence;
          tailf:cli-incomplete-command;
          type enumeration {
            enum "0" {
              tailf:info
                "Specifies an UNENCRYPTED password will follow";
            }
            enum "7" {
              tailf:info
                "Specifies a HIDDEN password will follow";
            }
          }
        }
        leaf password {
          tailf:cli-drop-node-name;
          type string {
            tailf:info
              "WORD;;The HIDDEN user password string";
          }
        }
      }
      leaf privilege {
        tailf:info
          "Set user privilege level";
        type uint8 {
          tailf:info
            "<0-15>;;User privilege level";
          range "0..15";
        }
      }
      container secret {
        tailf:info
          "Specify the secret for the user";
        tailf:cli-compact-syntax;
        tailf:cli-flatten-container;
        tailf:cli-sequence-commands;
        tailf:cli-reset-container;
        leaf encryption {
          tailf:cli-optional-in-sequence;
          tailf:cli-drop-node-name;
          tailf:cli-incomplete-command;
          type enumeration {
            enum "0" {
              tailf:info
                "Specifies an UNENCRYPTED secret will follow";
            }
            enum "4" {
              tailf:info
                "Specifies a HIDDEN secret will follow";
            }
            enum "5" {
              tailf:info
                "Specifies a HIDDEN secret will follow";
            }
          }
        }
        leaf secret {
          tailf:cli-drop-node-name;
          type string {
            tailf:info
              "WORD;;The HIDDEN user secret string";
          }
        }
      }
    }
    list table-map {
      tailf:ncs-device-type "cli-ned";
      tailf:display-when "not(../ncs:module) or ../ncs:module[ncs:name='tailf-ned-cisco-ios']";
      tailf:info
        "Configure Table Map";
      tailf:cli-mode-name "config-tablemap";
      key "name";
      leaf name {
        type string {
          tailf:info
            "WORD;;table-map name";
        }
      }
      list map {
        tailf:info
          "map to_value from from_value";
        tailf:cli-compact-syntax;
        tailf:cli-reset-container;
        tailf:cli-suppress-mode;
        tailf:cli-delete-when-empty;
        key "from to";
        leaf from {
          tailf:info
            "map from value";
          tailf:cli-expose-key-name;
          type uint8 {
            tailf:info
              "<0-63>;;tablemap from value";
            range "0..63";
          }
        }
        leaf to {
          tailf:info
            "map to value";
          tailf:cli-expose-key-name;
          type uint8 {
            tailf:info
              "<0-63>;;tablemap to value";
            range "0..63";
          }
        }
      }
      leaf default {
        tailf:info
          "the default behavior for setting value not found in the table map";
        type union {
          type uint8 {
            tailf:info
              "<0-99>;;tablemap default value";
            range "0..99";
          }
          type enumeration {
            enum "copy" {
              tailf:info
                "set the default behavior for value not found in the table map to copy";
            }
            enum "ignore" {
              tailf:info
                "set the default behavior for value not found in the table map to ignore";
            }
          }
        }
      }
    }
    container sdm {
      tailf:ncs-device-type "cli-ned";
      tailf:display-when "not(../../ncs:module) or ../../ncs:module[ncs:name='tailf-ned-cisco-ios']";
      tailf:info
        "Switch database management";
      container prefer {
        tailf:info
          "Config TCAM and ASIC RAM size. Warning: need to reset switch for configuration to take effect";
        tailf:cli-delete-when-empty;
        presence "true";
        choice sdm-prefer-choice {
          leaf default {
            type empty;
          }
          leaf qos {
            type empty;
          }
        }
      }
    }
    container mls {
      tailf:ncs-device-type "cli-ned";
      tailf:display-when "not(../../ncs:module) or ../../ncs:module[ncs:name='tailf-ned-cisco-ios']";
      tailf:info
        "mls global commands";
      tailf:cli-incomplete-no;
      container acl {
        tailf:info
          "MLS ACL operation";
        container tcam {
          tailf:info
            "ACL TCAM";
          leaf default-result {
            tailf:info
              "Default result to be used during tcam programming";
            type enumeration {
              enum "bridge" {
                tailf:info
                  "Bridge result";
              }
              enum "deny" {
                tailf:info
                  "Deny result";
              }
              enum "permit" {
                tailf:info
                  "Permit result";
              }
            }
          }
          container log-update {
            tailf:info
              "Log TCAM updates";
            presence "true";
            leaf rate-limit-msg {
              tailf:info
                "Enable/Disable syslog ratelimiting";
              type enumeration {
                enum "disable" {
                  tailf:info
                    "Disable ratelimiting syslog";
                }
                enum "enable" {
                  tailf:info
                    "Enable syslog ratelimiting at 1 per second";
                }
              }
            }
          }
          leaf share-global {
            tailf:info
              "share global deny or permit any entries";
            tailf:cli-boolean-no;
            tailf:cli-full-command;
            type boolean;
            default "true";
          }
        }
      }
      container cef {
        tailf:info
          "cef keyword";
        container error {
          leaf action {
            type enumeration {
              enum "reset";
              enum "freeze";
            }
          }
        }
      }
      container ip {
        tailf:info
          "ip keyword";
        container multicast {
          tailf:info
            "multicast keyword";
          tailf:cli-display-separated;
          presence "true";
          container consistency-check {
            tailf:info
              "Set consistency checking characteristics";
            presence "true";
            container type {
              tailf:info
                "Set consistency checker type";
              container rp-sp {
                tailf:info
                  "Scan mlsm for Route, Switch Processor consistency";
                presence "true";
              }
            }
            leaf settle-time {
              tailf:info
                "Settle time for entry/oif for consistancy-checker";
              type uint16 {
                tailf:info
                  "<2-3600>;;Settle time for entry/oif in seconds";
                range "2..3600";
              }
            }
          }
          leaf flow-stat-timer {
            tailf:info
              "timer for flow statistic used by mls-msc and mlsm";
            type uint8 {
              tailf:info
                "<1-100>;;#seconds between one batch and another";
              range "1..100";
            }
          }
        }
      }
      container aging {
        tailf:info
          "L3 aging";
        container fast {
          tailf:info
            "L3 fast aging";
          tailf:cli-compact-syntax;
          tailf:cli-delete-when-empty;
          presence "true";
          leaf time {
            tailf:info
              "fast aging timeout value";
            type uint8 {
              tailf:info
                "<1-128>;;L3 fast aging time in seconds";
              range "1..128";
            }
          }
          leaf threshold {
            tailf:info
              "fast aging threshold";
            type uint8 {
              tailf:info
                "<1-128>;;L3 fast aging theshold packet count";
              range "1..128";
            }
          }
        }
        container normal {
          tailf:info
            "normal aging keyword";
          leaf seconds {
            tailf:cli-drop-node-name;
            type uint16 {
              tailf:info
                "<32-4092>;;L3 aging timeout in second";
              range "32..4092";
            }
          }
        }
      }
      container netflow {
        tailf:info
          "netflow keyword";
        tailf:cli-delete-when-empty;
        presence "true";
        leaf interface {
          type empty;
        }
        container usage {
          container notify {
            tailf:cli-compact-syntax;
            tailf:cli-sequence-commands {
              tailf:cli-reset-siblings;
            }
            leaf percentage {
              tailf:cli-drop-node-name;
              type uint8 {
                tailf:info
                  "<20-100>;;threshold percentage";
                range "20..100";
              }
            }
            leaf seconds {
              tailf:cli-drop-node-name;
              type uint32 {
                tailf:info
                  "<120-1000000>;;time interval in seconds";
                range "120..1000000";
              }
            }
          }
        }
      }
      container flow {
        tailf:info
          "flowmask keyword";
        leaf ip {
          tailf:info
            "flowmask ip keyword";
          type enumeration {
            enum "interface-destination" {
              tailf:info
                "interface-destination flow keyword";
            }
            enum "interface-destination-source" {
              tailf:info
                "interface-destination-source flow keyword";
            }
            enum "interface-full" {
              tailf:info
                "interface-full flow keyword";
            }
            enum "interface-source" {
              tailf:info
                "interface-source only flow keyword";
            }
          }
        }
      }
      container mls-qos-conf {
        tailf:cli-drop-node-name;
        leaf qos {
          type empty;
        }
      }
      container qos {
        tailf:info
          "QoS parameters";
        tailf:cli-incomplete-command;
        tailf:cli-incomplete-no;
        list aggregate-policer {
          tailf:info
            "Assign aggregate policer";
          tailf:cli-suppress-mode;
          tailf:cli-delete-when-empty;
          tailf:cli-compact-syntax;
          tailf:cli-sequence-commands {
            tailf:cli-reset-all-siblings;
          }
          key "name";
          leaf name {
            type string {
              tailf:info
                "WORD;;aggregate policer name";
            }
          }
          leaf target-bit-rate {
            tailf:cli-drop-node-name;
            type uint64 {
              tailf:info
                "<32000-60000000000>;;Target Bit Rate (bits per second) (postfix k, m, g optional; decimal point allowed)";
              range "32000..60000000000";
            }
          }
          leaf burst-normal {
            tailf:cli-drop-node-name;
            tailf:cli-optional-in-sequence;
            type uint32 {
              tailf:info
                "<1000-31250000>;;Normal burst bytes";
              range "1000..31250000";
            }
          }
          leaf burst-max {
            tailf:cli-drop-node-name;
            tailf:cli-optional-in-sequence;
            when '../burst-normal' {
              tailf:xpath-root 3;
              tailf:dependency "../burst-normal";
            }
            type uint32 {
              tailf:info
                "<1000-31250000>;;Maximum burst bytes";
              range "1000..31250000";
            }
          }
          leaf pir {
            tailf:info
              "PIR";
            tailf:cli-optional-in-sequence;
            type uint64 {
              tailf:info
                "<32000-60000000000>;;Target Bit Rate (bits per second) (postfix k, m, g optional; decimal point allowed)";
              range "32000..60000000000";
            }
          }
          container conform-action {
            tailf:info
              "action when rate is not exceeded";
            tailf:cli-optional-in-sequence;
            tailf:cli-flatten-container;
            tailf:cli-compact-syntax;
            choice action-choice {
              leaf drop {
                tailf:info
                  "drop packet";
                type empty;
              }
              leaf set-dscp-transmit {
                tailf:info
                  "set dscp and send it";
                type dscp-type;
              }
              leaf set-mpls-exp-imposition-transmit {
                tailf:info
                  "set exp at tag imposition and send it";
                type uint8 {
                  tailf:info
                    "<0-7>;;new exp";
                  range "0..7";
                }
              }
              leaf set-prec-transmit {
                tailf:info
                  "rewrite packet precedence and send it";
                type uint8 {
                  tailf:info
                    "<0-7>;;new precedence";
                  range "0..7";
                }
              }
              leaf transmit {
                tailf:info
                  "transmit packet";
                type empty;
              }
            }
          }
          leaf exceed-action {
            tailf:info
              "action when rate is exceeded";
            tailf:cli-optional-in-sequence;
            type enumeration {
              enum "drop" {
                tailf:info
                  "drop packet";
              }
              enum "policed-dscp-transmit" {
                tailf:info
                  "change dscp per policed-dscp map and send it";
              }
              enum "transmit" {
                tailf:info
                  "transmit packet";
              }
            }
          }
          leaf violate-action {
            tailf:info
              "action when rate violated";
            type enumeration {
              enum "drop" {
                tailf:info
                  "drop packet";
              }
              enum "policed-dscp-transmit" {
                tailf:info
                  "change dscp per policed-dscp map and send it";
              }
              enum "transmit" {
                tailf:info
                  "transmit packet";
              }
            }
          }
        }
        container rewrite {
          tailf:info
            "packet qos rewrite enable/disable";
          container ip {
            tailf:info
              "ip packet qos rewrite enable/disable";
            container dscp {
              tailf:info
                "packet ip dscp rewrite enable/disable";
              presence "true";
              leaf slot {
                tailf:info
                  "slot number";
                type string {
                  tailf:info
                    "WORD;;Slots seperated by commas. Valid slots: 1,2,3,4,5,6,7,8,9";
                }
              }
            }
          }
        }
        container map {
          tailf:info
            "Define QoS mapping";
          leaf-list cos-dscp {
            tailf:info
              "cos-dscp map: eight dscp values for cos 0-7";
            tailf:cli-flat-list-syntax;
            tailf:cli-no-value-on-delete;
            type uint8 {
              tailf:info
                "<0-63>;;8 dscp values separated by spaces";
              range "0..63";
            }
          }
          leaf-list ip-prec-dscp {
            tailf:info
              "dscp values for ip precedences 0 - 7";
            tailf:cli-flat-list-syntax;
            tailf:cli-no-value-on-delete;
            type uint8 {
              tailf:info
                "<0-63>;;8 dscp values separated by spaces";
              range "0..63";
            }
          }
          list exp-mutation {
            tailf:info
              "exp-mutation map keyword";
            tailf:cli-suppress-mode;
            tailf:cli-delete-when-empty;
            tailf:cli-compact-syntax;
            tailf:cli-sequence-commands {
              tailf:cli-reset-siblings;
            }
            tailf:cli-incomplete-command;
            key "name";
            leaf name {
              type string {
                tailf:info
                  "WORD;;exp-mutation map name";
              }
            }
            leaf mutated-exp1 {
              tailf:cli-drop-node-name;
              tailf:cli-incomplete-command;
              type uint8 {
                tailf:info
                  "<0-7>;;exp values separated by spaces (8 values total)";
                range "0..7";
              }
            }
            leaf mutated-exp2 {
              tailf:cli-drop-node-name;
              tailf:cli-incomplete-command;
              type uint8 {
                tailf:info
                  "<0-7>;;exp values separated by spaces (8 values total)";
                range "0..7";
              }
            }
            leaf mutated-exp3 {
              tailf:cli-drop-node-name;
              tailf:cli-incomplete-command;
              type uint8 {
                tailf:info
                  "<0-7>;;exp values separated by spaces (8 values total)";
                range "0..7";
              }
            }
            leaf mutated-exp4 {
              tailf:cli-drop-node-name;
              tailf:cli-incomplete-command;
              type uint8 {
                tailf:info
                  "<0-7>;;exp values separated by spaces (8 values total)";
                range "0..7";
              }
            }
            leaf mutated-exp5 {
              tailf:cli-drop-node-name;
              tailf:cli-incomplete-command;
              type uint8 {
                tailf:info
                  "<0-7>;;exp values separated by spaces (8 values total)";
                range "0..7";
              }
            }
            leaf mutated-exp6 {
              tailf:cli-drop-node-name;
              tailf:cli-incomplete-command;
              type uint8 {
                tailf:info
                  "<0-7>;;exp values separated by spaces (8 values total)";
                range "0..7";
              }
            }
            leaf mutated-exp7 {
              tailf:cli-drop-node-name;
              tailf:cli-incomplete-command;
              type uint8 {
                tailf:info
                  "<0-7>;;exp values separated by spaces (8 values total)";
                range "0..7";
              }
            }
            leaf mutated-exp8 {
              tailf:cli-drop-node-name;
              type uint8 {
                tailf:info
                  "<0-7>;;exp values separated by spaces (8 values total)";
                range "0..7";
              }
            }
          }
        }
        container srr-queue {
          list cos-dscp-list {
            tailf:cli-drop-node-name;
            tailf:cli-suppress-mode;
            tailf:cli-delete-when-empty;
            tailf:cli-compact-syntax;
            key "direction maptype queue threshold";
            leaf direction {
              type enumeration {
                enum "input";
                enum "output";
              }
            }
            leaf maptype {
              type enumeration {
                enum "cos-map";
                enum "dscp-map";
              }
            }
            leaf queue {
              tailf:cli-expose-key-name;
              type uint8;
            }
            leaf threshold {
              tailf:cli-expose-key-name;
              type uint8;
            }
            list values {
              tailf:cli-drop-node-name;
              tailf:cli-suppress-mode;
              tailf:cli-delete-when-empty;
              tailf:cli-show-long-obu-diffs;
              ordered-by user;
              key "value";
              leaf value {
                tailf:cli-multi-word-key;
                type string;
              }
            }
          }
          container input {
            list priority-queue {
              tailf:cli-suppress-mode;
              tailf:cli-delete-when-empty;
              tailf:cli-compact-syntax;
              key "queue";
              leaf queue {
                type uint8;
              }
              leaf bandwidth {
                tailf:cli-no-name-on-delete;
                tailf:cli-no-value-on-delete;
                type uint8;
              }
            }
            container bandwidth {
              tailf:cli-compact-syntax;
              tailf:cli-sequence-commands {
                tailf:cli-reset-siblings;
              }
              leaf weight1 {
                tailf:cli-drop-node-name;
                tailf:cli-no-value-on-delete;
                type uint8;
              }
              leaf weight2 {
                tailf:cli-drop-node-name;
                tailf:cli-no-value-on-delete;
                type uint8;
              }
            }
            list threshold {
              tailf:cli-suppress-mode;
              tailf:cli-delete-when-empty;
              tailf:cli-compact-syntax;
              key "queue";
              leaf queue {
                type uint8;
              }
              leaf threshold-percentage1 {
                tailf:cli-drop-node-name;
                tailf:cli-no-value-on-delete;
                type uint8;
              }
              leaf threshold-percentage2 {
                tailf:cli-drop-node-name;
                tailf:cli-no-value-on-delete;
                type uint8;
              }
            }
            container buffers {
              tailf:cli-compact-syntax;
              tailf:cli-sequence-commands {
                tailf:cli-reset-siblings;
              }
              leaf percentage1 {
                tailf:cli-drop-node-name;
                tailf:cli-no-value-on-delete;
                type uint8;
              }
              leaf percentage2 {
                tailf:cli-drop-node-name;
                tailf:cli-no-value-on-delete;
                type uint8;
              }
            }
          }
        }
        container queue-set {
          container output {
            list threshold-list {
              tailf:cli-drop-node-name;
              tailf:cli-suppress-mode;
              tailf:cli-delete-when-empty;
              tailf:cli-compact-syntax;
              key "queue threshold";
              leaf queue {
                type uint8;
              }
              leaf threshold {
                tailf:cli-expose-key-name;
                type uint8;
              }
              leaf drop-threshold1 {
                tailf:cli-drop-node-name;
                tailf:cli-no-value-on-delete;
                type uint16;
              }
              leaf drop-threshold2 {
                tailf:cli-drop-node-name;
                tailf:cli-no-value-on-delete;
                type uint16;
              }
              leaf reserved-threshold {
                tailf:cli-drop-node-name;
                tailf:cli-no-value-on-delete;
                type uint16;
              }
              leaf maximum-threshold {
                tailf:cli-drop-node-name;
                tailf:cli-no-value-on-delete;
                type uint16;
              }
            }
            list buffers-list {
              tailf:cli-drop-node-name;
              tailf:cli-suppress-mode;
              tailf:cli-delete-when-empty;
              tailf:cli-compact-syntax;
              key "queue";
              leaf queue {
                type uint8;
              }
              container buffers {
                tailf:cli-compact-syntax;
                tailf:cli-sequence-commands {
                  tailf:cli-reset-siblings;
                }
                leaf allocation1 {
                  tailf:cli-drop-node-name;
                  tailf:cli-no-value-on-delete;
                  type uint8;
                }
                leaf allocation2 {
                  tailf:cli-drop-node-name;
                  tailf:cli-no-value-on-delete;
                  type uint8;
                }
                leaf allocation3 {
                  tailf:cli-drop-node-name;
                  tailf:cli-no-value-on-delete;
                  type uint8;
                }
                leaf allocation4 {
                  tailf:cli-drop-node-name;
                  tailf:cli-no-value-on-delete;
                  type uint8;
                }
              }
            }
          }
        }
      }
      container rate-limit {
        tailf:info
          "Rate limit different behaviors";
        container multicast {
          tailf:info
            "Rate limiting for Multicast packets";
          container ipv4 {
            tailf:info
              "Rate limiters for IPv4 traffic";
            container igmp {
              tailf:info
                "Rate limiting of the IGMP protocol packets";
              tailf:cli-compact-syntax;
              tailf:cli-sequence-commands {
                tailf:cli-reset-siblings;
              }
              leaf pps {
                tailf:cli-drop-node-name;
                type uint32 {
                  tailf:info
                    "<10-1000000>;;packets per second";
                  range "10..1000000";
                }
              }
              leaf packets-in-burst {
                tailf:cli-drop-node-name;
                type uint8 {
                  tailf:info
                    "<1-255>;;packets in burst";
                  range "1..255";
                }
              }
            }
          }
        }
        container all {
          tailf:info
            "Rate Limiting for both Unicast and Multicast packets";
          container ttl-failure {
            tailf:info
              "TTL failure cases";
            tailf:cli-compact-syntax;
            tailf:cli-sequence-commands {
              tailf:cli-reset-siblings;
            }
            leaf pps {
              tailf:cli-drop-node-name;
              type uint32 {
                tailf:info
                  "<10-1000000>;;packets per second";
                range "10..1000000";
              }
            }
            leaf packets-in-burst {
              tailf:cli-drop-node-name;
              type uint8 {
                tailf:info
                  "<1-255>;;packets in burst";
                range "1..255";
              }
            }
          }
        }
        container layer2 {
          tailf:info
            "layer2 protocol cases";
          container l2pt {
            tailf:info
              "layer2 protocol tunnelling packets";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
          container pdu {
            tailf:info
              "layer2 protocol data unit packets";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
        }
      }
      container verify {
        tailf:info
          "enable hardware packet parsing error checks";
        container ip {
          tailf:info
            "check on IP packets";
          leaf checksum {
            tailf:info
              "check for packet checksum errors";
            tailf:cli-boolean-no;
            type boolean;
            default "true";
          }
          container length {
            tailf:info
              "check for packet length errors";
            leaf consistent {
              tailf:info
                "check length in header against physical frame length";
              tailf:cli-boolean-no;
              tailf:cli-full-command;
              type boolean;
              default "true";
            }
            leaf minimum {
              tailf:info
                "check for minimum packet length";
              tailf:cli-boolean-no;
              type boolean;
              default "true";
            }
          }
          leaf same-address {
            tailf:info
              "check for packet having equal source and destination IP addresses";
            type empty;
          }
          leaf syslog {
            tailf:info
              "syslog packet parse errors";
            type empty;
          }
        }
      }
    }
    container policer {
      tailf:ncs-device-type "cli-ned";
      tailf:display-when "not(../../ncs:module) or ../../ncs:module[ncs:name='tailf-ned-cisco-ios']";
      tailf:info
        "Switch policer";
      list aggregate {
        tailf:info
          "Named aggregate policer";
        tailf:cli-suppress-mode;
        tailf:cli-delete-when-empty;
        tailf:cli-compact-syntax;
        tailf:cli-sequence-commands {
          tailf:cli-reset-siblings;
        }
        key "name";
        leaf name {
          type string {
            tailf:info
              "WORD;;aggregate policer Name";
          }
        }
        leaf cir {
          tailf:info
            "Committed information rate";
          type uint32 {
            tailf:info
              "<8000-1000000000>;;Bits per second";
            range "8000..1000000000";
          }
        }
        leaf bc {
          tailf:info
            "Conform burst";
          tailf:cli-optional-in-sequence;
          type uint32 {
            tailf:info
              "<8000-1000000000>;;Burst bytes";
            range "8000..1000000000";
          }
        }
        leaf conform-action {
          tailf:info
            "action when rate is within conform and conform + exceed burst";
          tailf:cli-optional-in-sequence;
          type empty;
        }
        leaf set-qos-transmit {
          tailf:info
            "set qos-group and send it";
          when '../conform-action' {
            tailf:xpath-root 3;
          }
          tailf:cli-optional-in-sequence;
          type uint8 {
            tailf:info
              "<0-99>;;new qos-group";
            range "0..99";
          }
        }
        leaf set-dot1ad-dei-transmit {
          tailf:info
            "set dei and send it";
          when '../conform-action' {
            tailf:xpath-root 3;
          }
          tailf:cli-optional-in-sequence;
          type uint8 {
            tailf:info
              "<0-1>;;new dei value";
            range "0..1";
          }
        }
        leaf set-prec-transmit {
          tailf:info
            "rewrite packet precedence and send it";
          when '../conform-action' {
            tailf:xpath-root 3;
          }
          tailf:cli-optional-in-sequence;
          type prec_value-type;
        }
        container set-prec-transmit-table {
          when '../set-prec-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string {
              tailf:info
                "WORD;;table-map name";
            }
            tailf:non-strict-leafref {
              path "/ncs:devices/ncs:device/ncs:config/ios:table-map/name" {
                tailf:xpath-root 3;
              }
            }
          }
        }
        leaf set-dscp-transmit {
          tailf:info
            "set dscp and send it";
          when '../conform-action' {
            tailf:xpath-root 3;
          }
          tailf:cli-optional-in-sequence;
          type dscp-type;
        }
        container set-dscp-transmit-table {
          when '../set-dscp-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string {
              tailf:info
                "WORD;;table-map name";
            }
            tailf:non-strict-leafref {
              path "/ncs:devices/ncs:device/ncs:config/ios:table-map/name" {
                tailf:xpath-root 3;
              }
            }
          }
        }
        leaf set-cos-transmit {
          tailf:info
            "set cos and send it";
          when '../conform-action' {
            tailf:xpath-root 3;
          }
          tailf:cli-optional-in-sequence;
          type cos_value-type;
        }
        container set-cos-transmit-table {
          when '../set-cos-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string {
              tailf:info
                "WORD;;table-map name";
            }
            tailf:non-strict-leafref {
              path "/ncs:devices/ncs:device/ncs:config/ios:table-map/name" {
                tailf:xpath-root 3;
              }
            }
          }
        }
        leaf transmit {
          tailf:info
            "transmit packet";
          when '../conform-action' {
            tailf:xpath-root 3;
          }
          tailf:cli-optional-in-sequence;
          type empty;
        }
        leaf exceed-action {
          tailf:info
            "action when rate is within conform and conform + exceed burst";
          type empty;
        }
        leaf drop {
          tailf:info
            "drop packet";
          when '../exceed-action' {
            tailf:xpath-root 3;
          }
          tailf:cli-optional-in-sequence;
          tailf:cli-full-command;
          type empty;
        }
        container exceed-transmit {
          tailf:cli-no-keyword;
          tailf:cli-drop-node-name;
          tailf:cli-optional-in-sequence;
          tailf:cli-flatten-container;
          leaf transmit {
            tailf:info
              "transmit packet";
            when '../../exceed-action' {
              tailf:xpath-root 3;
            }
            tailf:cli-optional-in-sequence;
            type empty;
          }
        }
      }
    }
    container redundancy {
      tailf:ncs-device-type "cli-ned";
      tailf:display-when "not(../../ncs:module) or ../../ncs:module[ncs:name='tailf-ned-cisco-ios']";
      tailf:info
        "Enter redundancy mode";
      tailf:cli-add-mode;
      tailf:cli-mode-name "config-red";
      presence "true";
      leaf maintenance-mode {
        tailf:info
          "Enable/Disable maintenance mode ";
        type empty;
      }
      list linecard-group {
        tailf:info
          "Enter linecard redundancy submode";
        tailf:cli-mode-name "config-red-lc";
        tailf:cli-incomplete-command;
        tailf:cli-recursive-delete;
        key "id";
        leaf id {
          type uint32 {
            tailf:info
              "ID;;linecard-group identifier";
          }
        }
        leaf cable {
          tailf:info
            "CMTS LC Redundancy type";
          tailf:cli-hide-in-submode;
          tailf:cli-full-command;
          type empty;
        }
        leaf description {
          tailf:info
            "Assign linecard group description";
          tailf:cli-multi-value;
          tailf:cli-full-command;
          type string {
            tailf:info
              "LINE;;Linecard group description";
          }
        }
        container rf-switch {
          tailf:info
            "Specify/Change RF-switch parameters (Optional Command)";
          leaf snmp-community {
            tailf:info
              "SNMP community name";
            type string {
              tailf:info
                "WORD;;snmp community name";
            }
          }
        }
        container member {
          tailf:info
            "Add or remove a member from this LC redundancy";
          list subslot {
            tailf:info
              "subslot number to be added or removed from this linecard group";
            tailf:cli-suppress-mode;
            tailf:cli-delete-when-empty;
            tailf:cli-incomplete-command;
            tailf:cli-compact-syntax;
            tailf:cli-suppress-list-no;
            key "id";
            leaf id {
              type string {
                tailf:info
                  "<5-8>/<0-1>";
              }
            }
            leaf working {
              tailf:info
                "working slot in this linecard group";
              type empty;
            }
            container protect {
              tailf:info
                "protect slot of this linecard group";
              tailf:cli-display-separated;
              presence "true";
              choice config-choice {
                leaf config {
                  tailf:info
                    "Specifiy the subslot for cable upstream config";
                  tailf:cli-incomplete-no;
                  type string {
                    tailf:info
                      "<5-8>/<0-1>;;Slot/Subslot";
                  }
                }
                container no-config {
                  tailf:cli-drop-node-name;
                  leaf config {
                    tailf:cli-incomplete-command;
                    tailf:cli-boolean-no;
                    tailf:cli-full-command;
                    type boolean;
                    default "true";
                  }
                }
              }
            }
          }
        }
        container conf {
          tailf:cli-drop-node-name;
          leaf revertive {
            tailf:info
              "Make redundancy relationship revertive";
            type empty;
          }
        }
      }
      leaf mode {
        tailf:info
          "redundancy mode for this chassis";
        type enumeration {
          enum "rpr" {
            tailf:info
              "Route Processor Redundancy";
          }
          enum "rpr-plus" {
            tailf:info
              "Route Processor Redundancy Plus";
          }
          enum "sso" {
            tailf:info
              "Stateful Switchover";
          }
          enum "none" {
            tailf:info
              "None";
          }
        }
      }
      container main-cpu {
        tailf:info
          "Enter main-cpu mode";
        tailf:cli-add-mode;
        tailf:cli-mode-name "config-r-mc";
        container auto-sync {
          leaf running-config {
            type empty;
          }
          leaf config-register {
            type empty;
          }
          leaf bootvar {
            type empty;
          }
        }
        container switchover {
          tailf:info
            "Configuration of switchover";
          container pxf {
            tailf:info
              "PXF switchover options";
            container restart {
              tailf:info
                "PXF restarts";
              tailf:cli-compact-syntax;
              tailf:cli-sequence-commands;
              leaf number-of-crashes {
                tailf:cli-drop-node-name;
                tailf:cli-incomplete-command;
                type uint8 {
                  tailf:info
                    "<1-25>;;Number of PXF restarts before a switchover";
                  range "1..25";
                }
              }
              leaf time-period {
                tailf:cli-drop-node-name;
                type uint8 {
                  tailf:info
                    "<0-120>;;Interval (in hours) over which restart count is accumulated";
                  range "0..120";
                }
              }
            }
          }
        }
      }
      container interchassis {
        tailf:info
          "Enter interchassis mode";
        list group {
          tailf:info
            "Enter the redundancy group number";
          tailf:cli-mode-name "conppfig-r-ic";
          key "id";
          leaf id {
            type uint32 {
              tailf:info
                "<1-4294967295>;;The redundancy group number";
              range "1..4294967295";
            }
          }
          container member {
            tailf:info
              "specify a redundancy group member";
            leaf ip {
              tailf:info
                "specify the redundancy group member using an ip address";
              type inet:ipv4-address {
                tailf:info
                  "A.B.C.D;;the ip address of the remote redundancy group member";
              }
            }
          }
          container mlacp {
            tailf:info
              "mLACP interchassis redundancy group subcommands";
            leaf system-mac {
              tailf:info
                "mLACP redundancy group mac address";
              type string {
                tailf:info
                  "H.H.H;;mLACP redundancy group mac address";
              }
            }
            leaf system-priority {
              tailf:info
                "mLACP system priority";
              type uint16 {
                tailf:info
                  "<0-65535>;;Priority value";
              }
            }
            leaf node-id {
              tailf:info
                "mLACP node-id, appended to LACP port ids";
              type uint8 {
                tailf:info
                  "<0-7>;;mLACP node-id";
                range "0..7";
              }
            }
          }
        }
      }
    }
    list class-map {
      tailf:ncs-device-type "cli-ned";
      tailf:display-when "not(../ncs:module) or ../ncs:module[ncs:name='tailf-ned-cisco-ios']";
      tailf:info
        "Configure QoS Class Map";
      tailf:cli-mode-name "config-cmap";
      tailf:cli-suppress-list-no;
      tailf:cli-delete-when-empty;
      tailf:cli-no-key-completion;
      tailf:cli-sequence-commands;
      tailf:cli-full-command;
      key "name";
      leaf name {
        tailf:cli-disallow-value "type|match-any|match-all";
        type string {
          tailf:info
            "WORD;;class-map name";
        }
      }
      leaf type {
        tailf:info
          "type of the class-map";
        tailf:cli-optional-in-sequence;
        tailf:cli-prefix-key;
        type enumeration {
          enum "access-control" {
            tailf:info
              "access-control specific class-map";
          }
          enum "inspect" {
            tailf:info
              "Configure Firewall Class Map";
          }
          enum "logging" {
            tailf:info
              "Class map for control-plane packet logging";
          }
          enum "port-filter" {
            tailf:info
              "Class map for port filter";
          }
          enum "queue-threshold" {
            tailf:info
              "Class map for queue threshold";
          }
          enum "stack" {
            tailf:info
              "class-map for protocol header stack specification";
          }
        }
      }
      leaf protocol {
        when "../type = 'inspect'" {
          tailf:xpath-root 3;
        }
        tailf:cli-drop-node-name;
        tailf:cli-prefix-key;
        tailf:cli-optional-in-sequence;
        type enumeration {
          enum "aol" {
            tailf:info
              "Configure CBAC class-map for IM-AOL protocol";
          }
          enum "edonkey" {
            tailf:info
              "eDonkey";
          }
          enum "fasttrack" {
            tailf:info
              "FastTrack Traffic - KaZaA, Morpheus, Grokster...";
          }
          enum "gnutella" {
            tailf:info
              "Gnutella Version2 Traffic - BearShare, Shareeza, Morpheus ...";
          }
          enum "http" {
            tailf:info
              "Configure CBAC class-map for HTTP protocol";
          }
          enum "imap" {
            tailf:info
              "Configure CBAC class-map for IMAP protocol";
          }
          enum "kazaa2" {
            tailf:info
              "Kazaa Version 2";
          }
          enum "msnmsgr" {
            tailf:info
              "Configure CBAC class-map for IM-MSN protocol";
          }
          enum "pop3" {
            tailf:info
              "Configure CBAC class-map for POP3 protocol";
          }
          enum "smtp" {
            tailf:info
              "Configure CBAC class-map for SMTP protocol";
          }
          enum "sunrpc" {
            tailf:info
              "Configure CBAC class-map for RPC protocol";
          }
          enum "ymsgr" {
            tailf:info
              "Configure CBAC class-map for IM-YAHOO protocol";
          }
        }
      }
      leaf prematch {
        tailf:cli-drop-node-name;
        tailf:cli-no-keyword;
        tailf:cli-prefix-key;
        type enumeration {
          enum "match-all" {
            tailf:info
              "Logical-AND all matching statements under this classmap";
          }
          enum "match-any" {
            tailf:info
              "Logical-OR all matching statements under this classmap";
          }
        }
        mandatory true;
      }
      leaf description {
        tailf:info
          "Class-Map description";
        tailf:cli-break-sequence-commands;
        tailf:cli-multi-value;
        type string {
          tailf:info
            "LINE;;Description of this class-map (up to 200 characters)";
        }
      }
      container match {
        tailf:info
          "classification criteria";
        uses class-map-match-grouping;
        container not {
          tailf:info
            "Negate this match result";
          uses class-map-match-grouping;
        }
      }
    }
    list policy-map {
      tailf:ncs-device-type "cli-ned";
      tailf:display-when "not(../ncs:module) or ../ncs:module[ncs:name='tailf-ned-cisco-ios']";
      tailf:info
        "Configure QoS Policy Map";
      tailf:cli-mode-name "config-pmap";
      tailf:cli-diff-dependency "../class-map" {
        tailf:xpath-root 3;
      }
      tailf:cli-diff-dependency "../mls/qos/aggregate-policer" {
        tailf:xpath-root 3;
      }
      tailf:cli-diff-dependency "../policer/aggregate" {
        tailf:xpath-root 3;
      }
      tailf:cli-diff-dependency "../tailfned/police" {
        tailf:xpath-root 3;
      }
      key "name";
      leaf name {
        tailf:cli-disallow-value "(type)|(http)|(im)|(imap)|(p2p)|(pop3)|(smtp)|(sunrpc)";
        type string {
          tailf:info
            "WORD;;policy-map name";
        }
      }
      leaf type {
        tailf:info
          "type of the policy-map";
        tailf:cli-prefix-key;
        type enumeration {
          enum "inspect";
        }
      }
      leaf protocol {
        tailf:cli-drop-node-name;
        tailf:cli-prefix-key;
        type enumeration {
          enum "http" {
            tailf:info
              "Configure CBAC policy-map for HTTP protocol";
          }
          enum "im" {
            tailf:info
              "Configure CBAC policy-map for IM protocol";
          }
          enum "imap" {
            tailf:info
              "Configure CBAC policy-map for IMAP protocol";
          }
          enum "p2p" {
            tailf:info
              "Configure CBAC policy-map for P2P protocols";
          }
          enum "pop3" {
            tailf:info
              "Configure CBAC policy-map for POP3 protocol";
          }
          enum "smtp" {
            tailf:info
              "Configure CBAC policy-map for SMTP protocol";
          }
          enum "sunrpc" {
            tailf:info
              "Configure CBAC policy-map for RPC protocol";
          }
        }
      }
      leaf description {
        tailf:info
          "Policy-Map description";
        tailf:cli-multi-value;
        type string {
          tailf:info
            "LINE;;Description of this policy-map (up to 200 characters)";
          length "1..200";
        }
      }
      list class {
        tailf:info
          "policy criteria";
        tailf:cli-mode-name "config-pmap-c";
        key "name";
        leaf name {
          tailf:cli-disallow-value "type";
          type union {
            type string {
              tailf:info
                "WORD;;class-map name";
            }
            type enumeration {
              enum "class-default" {
                tailf:info
                  "System default class matching otherwise unclassified packet";
              }
            }
          }
        }
        leaf type {
          tailf:info
            "type of the class-map";
          tailf:cli-prefix-key;
          type enumeration {
            enum "inspect" {
              tailf:info
                "Configure CBAC Class Map";
            }
          }
        }
        container policy {
          when "../../type = 'inspect'" {
            tailf:xpath-root 3;
          }
          tailf:cli-drop-node-name;
          tailf:cli-sequence-commands {
            tailf:cli-reset-siblings;
          }
          leaf action {
            tailf:cli-drop-node-name;
            tailf:cli-remove-before-change;
            type enumeration {
              enum "drop" {
                tailf:info
                  "Drop the packet";
              }
              enum "inspect" {
                tailf:info
                  "Context-based Access Control Engine";
              }
              enum "pass" {
                tailf:info
                  "Pass the packet";
              }
            }
          }
          leaf log {
            tailf:info
              "Send logging message for drop";
            when "../action = 'drop'" {
              tailf:xpath-root 3;
            }
            type empty;
          }
          leaf parameter-map {
            tailf:cli-drop-node-name;
            when "../action = 'inspect'" {
              tailf:xpath-root 3;
            }
            type string;
            tailf:non-strict-leafref {
              path "/ncs:devices/ncs:device/ncs:config/ios:parameter-map/type/inspect/name" {
                tailf:xpath-root 3;
              }
            }
          }
        }
        container inspect-police {
          when "../policy/action = 'inspect'" {
            tailf:xpath-root 3;
          }
          tailf:cli-drop-node-name;
          container police {
            tailf:info
              "Police";
            tailf:cli-compact-syntax;
            tailf:cli-sequence-commands {
              tailf:cli-reset-siblings;
            }
            leaf rate {
              tailf:info
                "Specify police rate";
              type uint32 {
                tailf:info
                  "<8000-2000000000>;;Rate value in bps";
                range "8000..2000000000";
              }
            }
            leaf burst {
              tailf:info
                "Specify 'burst' parameter";
              type uint32 {
                tailf:info
                  "<1000-512000000>;;Burst value in bytes";
                range "1000..512000000";
              }
            }
          }
        }
        container bandwidth {
          tailf:info
            "Bandwidth";
          leaf bits {
            tailf:cli-drop-node-name;
            type uint32 {
              range "8..2000000";
              tailf:info
                "<8-2000000>;;Kilo Bits per second";
            }
          }
          leaf percent {
            tailf:info
              "% of total Bandwidth";
            tailf:cli-remove-before-change;
            type percentage-type;
          }
          container remaining {
            tailf:info
              "% of the remaining bandwidth";
            leaf percent {
              tailf:info
                "% of the remaining bandwidth";
              type percentage-type;
            }
          }
        }
        container compression {
          tailf:info
            "Activate Compression";
          presence "Activate Compression";
          container header {
            tailf:info
              "configure header compression";
            presence "configure header compression";
            leaf ip {
              tailf:info
                "configure ip header compression";
              type enumeration {
                enum "rtp" {
                  tailf:code-name "header_rtp";
                  tailf:info
                    "configure rtp header compression";
                }
                enum "tcp" {
                  tailf:info
                    "configure tcp header compression";
                }
              }
            }
          }
        }
        leaf drop {
          tailf:info
            "Drop all packets";
          tailf:cli-full-command;
          type empty;
        }
        container estimate {
          tailf:info
            "estimate resources required for this class";
          container bandwidth {
            presence "bandwidth required to service this class";
            tailf:info
              "bandwidth required to service this class";
            tailf:cli-sequence-commands;
            tailf:cli-compact-syntax;
            container delay-one-in {
              tailf:info
                "specify QoS target delay";
              tailf:cli-compact-syntax;
              tailf:cli-sequence-commands;
              leaf doi {
                tailf:cli-drop-node-name;
                tailf:cli-incomplete-command;
                type uint32 {
                  range "50..1000000";
                  tailf:info
                    "<50-1000000>;;delay one packet of N";
                }
              }
              leaf milliseconds {
                type uint32 {
                  range "8..1000" {
                    tailf:info
                      "<8-1000>;;worst-case milliseconds of delay";
                  }
                }
              }
            }
            leaf drop-one-in {
              tailf:info
                "specify QoS target loss rate";
              type uint32 {
                tailf:info
                  "<50-1000000>;;drop one packet of N";
              }
            }
          }
        }
        container fair-queue {
          tailf:info
            "Enable Flow-based Fair Queuing in this Class";
          tailf:cli-reset-container;
          presence "true";
          leaf dynamic-queues {
            tailf:cli-drop-node-name;
            tailf:cli-full-command;
            type uint32 {
              range "16|32|64|128|256|512|1024|2048|4096" {
                tailf:info
                  "<16-4096>;;Number Dynamic Conversation Queues";
              }
            }
          }
          leaf queue-limit {
            tailf:info
              "per flow queue limit";
            tailf:cli-full-command;
            type uint16 {
              tailf:info
                "<1-32768>;;packets";
              range "1..32768";
            }
          }
        }
        leaf netflow-sampler {
          tailf:info
            "NetFlow action";
          tailf:cli-full-command;
          type string {
            tailf:info
              "WORD;;Name of the flow sampler";
          }
        }
        container police-aggregate {
          tailf:cli-no-keyword;
          tailf:cli-drop-node-name;
          container police {
            tailf:info
              "Police";
            leaf aggregate {
              tailf:info
                "Choose aggregate policer for current class";
              tailf:cli-diff-dependency "../../../police-policy-map/police/cir" {
                tailf:xpath-root 3;
                tailf:cli-trigger-on-set;
              }
              type string {
                tailf:info
                  "WORD;;enter aggregate-policer name";
              }
            }
          }
        }
        choice police-choice {
          case police-cirmode-case {
            container police-policy-map {
              tailf:cli-no-keyword;
              tailf:cli-drop-node-name;
              container police {
                tailf:cli-add-mode;
                tailf:cli-mode-name "config-pmap-c-police";
                tailf:cli-flatten-container;
                tailf:cli-sequence-commands {
                  tailf:cli-reset-siblings;
                }
                when "contains(../../../../tailfned/police, 'cirmode')" {
                  tailf:xpath-root 3;
                  tailf:dependency "../../../../tailfned/police";
                }
                leaf cir {
                  tailf:info
                    "Committed information rate";
                  tailf:cli-hide-in-submode;
                  tailf:cli-diff-dependency "../../../police-aggregate/police/aggregate" {
                    tailf:xpath-root 3;
                    tailf:cli-trigger-on-set;
                  }
                  type police-bps-type;
                }
                leaf bc {
                  tailf:info
                    "Conform burst";
                  tailf:cli-optional-in-sequence;
                  tailf:cli-hide-in-submode;
                  type police-burst-type;
                }
                leaf be {
                  when '../bc' {
                    tailf:xpath-root 3;
                  }
                  tailf:info
                    "Excess burst";
                  tailf:cli-optional-in-sequence;
                  tailf:cli-hide-in-submode;
                  type police-burst-type;
                }
                leaf pir {
                  tailf:info
                    "Peak Information Rate";
                  tailf:cli-optional-in-sequence;
                  tailf:cli-hide-in-submode;
                  type police-bps-type;
                }
                container pir-be {
                  when '../pir' {
                    tailf:xpath-root 3;
                  }
                  tailf:cli-drop-node-name;
                  tailf:cli-optional-in-sequence;
                  tailf:cli-flatten-container;
                  tailf:cli-hide-in-submode;
                  leaf be {
                    tailf:info
                      "Excess burst";
                    type police-burst-type;
                  }
                }
                uses police-action-grouping;
              }
            }
          }
          case police-cir-percent-case {
            container police-cir-percent {
              tailf:cli-no-keyword;
              tailf:cli-drop-node-name;
              container police {
                container cir {
                  tailf:info
                    "Committed information rate";
                  container percent {
                    tailf:info
                      "% of interface bandwidth for Committed information rate";
                    tailf:cli-add-mode;
                    tailf:cli-mode-name "config-pmap-c-police";
                    tailf:cli-incomplete-command;
                    tailf:cli-flatten-container;
                    tailf:cli-sequence-commands {
                      tailf:cli-reset-siblings;
                    }
                    leaf percentage {
                      tailf:cli-drop-node-name;
                      tailf:cli-hide-in-submode;
                      type percentage-type;
                    }
                    leaf bc {
                      tailf:info
                        "Conform burst";
                      tailf:cli-optional-in-sequence;
                      tailf:cli-hide-in-submode;
                      type uint16 {
                        tailf:info
                          "<1-2000>;;Burst ms";
                      }
                    }
                    container bc-ms {
                      when '../bc' {
                        tailf:xpath-root 3;
                      }
                      tailf:cli-drop-node-name;
                      tailf:cli-optional-in-sequence;
                      tailf:cli-hide-in-submode;
                      tailf:cli-flatten-container;
                      tailf:cli-compact-syntax;
                      leaf ms {
                        tailf:info
                          "Milli seconds";
                        tailf:cli-no-keyword;
                        type empty;
                      }
                    }
                    leaf be {
                      when '../bc-ms/ms' {
                        tailf:xpath-root 3;
                        tailf:dependency "../bc-ms/ms";
                      }
                      tailf:info
                        "Excess burst";
                      tailf:cli-optional-in-sequence;
                      tailf:cli-hide-in-submode;
                      type uint16 {
                        tailf:info
                          "<1-2000>;;Burst ms";
                      }
                    }
                    container be-ms {
                      when '../be' {
                        tailf:xpath-root 3;
                      }
                      tailf:cli-drop-node-name;
                      tailf:cli-hide-in-submode;
                      tailf:cli-flatten-container;
                      tailf:cli-compact-syntax;
                      leaf ms {
                        tailf:info
                          "Milli seconds";
                        tailf:cli-no-keyword;
                        type empty;
                      }
                    }
                    container pir {
                      tailf:info
                        "Peak Information Rate";
                      tailf:cli-flatten-container;
                      tailf:cli-compact-syntax;
                      tailf:cli-hide-in-submode;
                      tailf:cli-optional-in-sequence;
                      leaf percent {
                        tailf:info
                          "% of interface bandwidth for Peak Information Rate";
                        type percentage-type;
                      }
                    }
                    container pir-be {
                      when '../pir' {
                        tailf:xpath-root 3;
                      }
                      tailf:cli-drop-node-name;
                      tailf:cli-optional-in-sequence;
                      tailf:cli-flatten-container;
                      tailf:cli-hide-in-submode;
                      leaf be {
                        tailf:info
                          "Excess burst";
                        type uint16 {
                          tailf:info
                            "<1-2000>;;Burst ms";
                        }
                      }
                    }
                    container pir-be-ms {
                      when '../pir-be/be' {
                        tailf:xpath-root 3;
                        tailf:dependency "../pir-be/be";
                      }
                      tailf:cli-drop-node-name;
                      tailf:cli-optional-in-sequence;
                      tailf:cli-hide-in-submode;
                      tailf:cli-flatten-container;
                      leaf ms {
                        tailf:info
                          "Milli seconds";
                        tailf:cli-no-keyword;
                        type empty;
                      }
                    }
                    uses police-action-grouping;
                  }
                }
              }
            }
          }
          case police-rate-unit-case {
            container police-rate-unit {
              tailf:cli-no-keyword;
              tailf:cli-drop-node-name;
              container police {
                container rate {
                  tailf:info
                    "Specify police rate";
                  tailf:cli-add-mode;
                  tailf:cli-mode-name "config-pmap-c-police";
                  tailf:cli-flatten-container;
                  tailf:cli-compact-syntax;
                  tailf:cli-sequence-commands {
                    tailf:cli-reset-siblings;
                  }
                  leaf units {
                    tailf:cli-drop-node-name;
                    tailf:cli-hide-in-submode;
                    type uint64 {
                      tailf:info
                        "<1-2000000000>;;Rate value in the range 8000-2,000,000,000 bps or 1-2,000,000 pps";
                    }
                  }
                  leaf xps {
                    tailf:cli-no-keyword;
                    tailf:cli-drop-node-name;
                    tailf:cli-hide-in-submode;
                    type police-pps-bps-type;
                  }
                  container burst {
                    tailf:info
                      "Specify 'burst' parameter";
                    tailf:cli-optional-in-sequence;
                    tailf:cli-hide-in-submode;
                    tailf:cli-flatten-container;
                    tailf:cli-compact-syntax;
                    tailf:cli-sequence-commands;
                    leaf burst-value {
                      tailf:cli-no-keyword;
                      tailf:cli-drop-node-name;
                      tailf:cli-incomplete-command;
                      type uint32 {
                        tailf:info
                          "<1-512000000>;;Burst value in packets/bytes";
                      }
                    }
                    leaf burst-type {
                      tailf:cli-no-keyword;
                      tailf:cli-drop-node-name;
                      tailf:cli-hide-in-submode;
                      type police-packets-bytes-type;
                    }
                  }
                  container peak-rate {
                    tailf:info
                      "Specify peak rate";
                    tailf:cli-optional-in-sequence;
                    tailf:cli-flatten-container;
                    tailf:cli-compact-syntax;
                    tailf:cli-sequence-commands;
                    tailf:cli-hide-in-submode;
                    leaf peak-rate-value {
                      tailf:cli-no-keyword;
                      tailf:cli-drop-node-name;
                      tailf:cli-incomplete-command;
                      type uint32 {
                        tailf:info
                          "<1-512000000>;;Peak-rate value in packets or bytes per second";
                        range "1..512000000";
                      }
                    }
                    leaf xps {
                      tailf:cli-no-keyword;
                      tailf:cli-drop-node-name;
                      type police-pps-bps-type;
                    }
                  }
                  container peak-burst {
                    tailf:info
                      "Specify 'peak-burst' parameter for peak-rate";
                    tailf:cli-optional-in-sequence;
                    tailf:cli-flatten-container;
                    tailf:cli-compact-syntax;
                    tailf:cli-sequence-commands;
                    tailf:cli-hide-in-submode;
                    leaf burst-value {
                      tailf:cli-no-keyword;
                      tailf:cli-drop-node-name;
                      tailf:cli-incomplete-command;
                      type uint32 {
                        tailf:info
                          "<1-512000000>;;Burst value in packets/bytes";
                      }
                    }
                    leaf burst-type {
                      tailf:cli-no-keyword;
                      tailf:cli-drop-node-name;
                      type police-packets-bytes-type;
                    }
                  }
                  uses police-action-grouping;
                }
              }
            }
          }
          case police-rate-percent-case {
            container police-rate-percent {
              tailf:cli-no-keyword;
              tailf:cli-drop-node-name;
              container police {
                container rate {
                  tailf:info
                    "Specify police rate";
                  container percent {
                    tailf:info
                      "% of interface bandwidth for rate";
                    tailf:cli-add-mode;
                    tailf:cli-mode-name "config-pmap-c-police";
                    tailf:cli-flatten-container;
                    tailf:cli-compact-syntax;
                    tailf:cli-sequence-commands {
                      tailf:cli-reset-siblings;
                    }
                    leaf percentage {
                      tailf:cli-drop-node-name;
                      tailf:cli-hide-in-submode;
                      type percentage-type;
                    }
                    leaf burst {
                      tailf:info
                        "Specify 'burst' parameter";
                      tailf:cli-optional-in-sequence;
                      tailf:cli-hide-in-submode;
                      type uint16 {
                        tailf:info
                          "<1-2000>;;Burst value in milliseconds";
                      }
                    }
                    leaf ms {
                      when '../burst' {
                        tailf:xpath-root 3;
                      }
                      tailf:info
                        "Treat 'burst' value in milliseconds";
                      tailf:cli-hide-in-submode;
                      type empty;
                    }
                    container peak-rate {
                      tailf:info
                        "Specify peak rate";
                      tailf:cli-hide-in-submode;
                      tailf:cli-optional-in-sequence;
                      tailf:cli-flatten-container;
                      leaf percent {
                        tailf:info
                          "% of interface bandwidth for peak-rate";
                        type percentage-type;
                      }
                    }
                    leaf peak-burst {
                      tailf:info
                        "Specify 'peak-burst' parameter for 'peak-rate'";
                      tailf:cli-hide-in-submode;
                      tailf:cli-optional-in-sequence;
                      type uint16 {
                        tailf:info
                          "<1-2000>;;Peak burst value in milliseconds";
                      }
                    }
                    container peak-burst-ms {
                      when '../peak-burst' {
                        tailf:xpath-root 3;
                      }
                      tailf:cli-drop-node-name;
                      tailf:cli-optional-in-sequence;
                      tailf:cli-hide-in-submode;
                      tailf:cli-flatten-container;
                      leaf ms {
                        tailf:info
                          "Milli seconds";
                        tailf:cli-no-keyword;
                        type empty;
                      }
                    }
                    uses police-action-grouping;
                  }
                }
              }
            }
          }
          case police-rate-pdp-case {
            container police-rate-pdp {
              tailf:cli-no-keyword;
              tailf:cli-drop-node-name;
              container police {
                container rate {
                  tailf:info
                    "Specify police rate";
                  container pdp {
                    tailf:info
                      "% of interface bandwidth for rate";
                    tailf:cli-add-mode;
                    tailf:cli-mode-name "config-pmap-c-police";
                    tailf:cli-flatten-container;
                    tailf:cli-sequence-commands {
                      tailf:cli-reset-siblings;
                    }
                    leaf burst {
                      tailf:info
                        "Conform burst";
                      tailf:cli-hide-in-submode;
                      tailf:cli-optional-in-sequence;
                      type police-burst-type;
                    }
                    leaf peak-rate {
                      tailf:info
                        "Specify peak rate";
                      tailf:cli-hide-in-submode;
                      tailf:cli-optional-in-sequence;
                      type enumeration {
                        enum "pdp";
                      }
                    }
                    leaf peak-burst {
                      when '../peak-rate' {
                        tailf:xpath-root 3;
                      }
                      tailf:info
                        "Specify 'peak-burst' parameter for 'peak-rate'";
                      tailf:cli-hide-in-submode;
                      tailf:cli-optional-in-sequence;
                      type police-burst-type;
                    }
                    uses police-action-grouping;
                  }
                }
              }
            }
          }
          case police-flow-case {
            container police-flow {
              tailf:cli-no-keyword;
              tailf:cli-drop-node-name;
              container police {
                container flow {
                  tailf:info
                    "police each flow";
                  tailf:cli-add-mode;
                  tailf:cli-mode-name "config-pmap-c-police";
                  tailf:cli-flatten-container;
                  tailf:cli-sequence-commands {
                    tailf:cli-reset-siblings;
                  }
                  leaf mask {
                    tailf:info
                      "flow mask to be used for policing";
                    tailf:cli-hide-in-submode;
                    tailf:cli-optional-in-sequence;
                    type enumeration {
                      enum "dest-only" {
                        tailf:info
                          "destination-address only flow mask";
                      }
                      enum "full-flow" {
                        tailf:info
                          "full flow mask";
                      }
                      enum "src-only" {
                        tailf:info
                          "source-address only flow mask";
                      }
                    }
                  }
                  leaf bps {
                    tailf:cli-drop-node-name;
                    tailf:cli-hide-in-submode;
                    type police-bps-type;
                  }
                  leaf burst-normal {
                    when '../bps' {
                      tailf:xpath-root 3;
                    }
                    tailf:cli-drop-node-name;
                    tailf:cli-hide-in-submode;
                    tailf:cli-optional-in-sequence;
                    type police-burst-type;
                  }
                  uses police-action-grouping;
                }
              }
            }
          }
          case police-bpsflat-case {
            container police-catalyst {
              tailf:cli-no-keyword;
              tailf:cli-drop-node-name;
              container police {
                tailf:cli-add-mode;
                tailf:cli-mode-name "config-pmap-c-police";
                tailf:cli-flatten-container;
                tailf:cli-sequence-commands {
                  tailf:cli-reset-siblings;
                }
                when "contains(../../../../tailfned/police, 'bpsflat')" {
                  tailf:xpath-root 3;
                  tailf:dependency "../../../../tailfned/police";
                }
                leaf bps-value {
                  tailf:cli-no-keyword;
                  tailf:cli-drop-node-name;
                  tailf:cli-hide-in-submode;
                  tailf:cli-incomplete-command;
                  type string {
                    tailf:info
                      "<32000-32000000000>;;Rate in bits per second (postfix k, m, g optional; decimal point allowed)";
                  }
                }
                leaf bps {
                  when '../bps-value' {
                    tailf:xpath-root 3;
                    tailf:dependency "../bps-value";
                  }
                  tailf:cli-hide-in-submode;
                  tailf:cli-incomplete-command;
                  type empty;
                }
                leaf byte-value {
                  tailf:cli-no-keyword;
                  tailf:cli-drop-node-name;
                  tailf:cli-hide-in-submode;
                  tailf:cli-incomplete-command;
                  type string {
                    tailf:info
                      "<32000-32000000000>;;(postfix k, m, g optional; decimal point allowed)";
                  }
                }
                leaf byte {
                  when '../byte-value' {
                    tailf:xpath-root 3;
                    tailf:dependency "../byte-value";
                  }
                  tailf:cli-hide-in-submode;
                  type empty;
                }
                container actions {
                  tailf:cli-no-keyword;
                  tailf:cli-break-sequence-commands;
                  tailf:cli-drop-node-name;
                  tailf:cli-flatten-container;
                  tailf:cli-hide-in-submode;
                  uses police-conform-action-grouping;
                  uses police-exceed-action-grouping;
                  uses police-violate-action-grouping;
                }
              }
            }
          }
          case police-switch-case {
            container police-switch {
              tailf:cli-no-keyword;
              tailf:cli-drop-node-name;
              container police {
                tailf:cli-compact-syntax;
                tailf:cli-sequence-commands {
                  tailf:cli-reset-siblings;
                }
                when "contains(../../../../tailfned/police, 'numflat')" {
                  tailf:xpath-root 3;
                  tailf:dependency "../../../../tailfned/police";
                }
                leaf cir {
                  tailf:cli-incomplete-command;
                  tailf:cli-drop-node-name;
                  tailf:cli-diff-dependency "../../../police-aggregate/police/aggregate" {
                    tailf:xpath-root 3;
                    tailf:cli-trigger-on-set;
                  }
                  type uint32 {
                    tailf:info
                      "<8000-1000000000>;;Bits per second";
                    range "8000..1000000000";
                  }
                }
                leaf bc {
                  tailf:cli-drop-node-name;
                  type uint32 {
                    tailf:info
                      "<8000-2000000>;;Normal burst bytes";
                    range "8000..2000000";
                  }
                }
                leaf exceed-action {
                  tailf:info
                    "action when rate is exceeded";
                  type enumeration {
                    enum "drop" {
                      tailf:info
                        "drop packet";
                    }
                    enum "policed-dscp-transmit" {
                      tailf:info
                        "change dscp per policed-dscp map and send it";
                    }
                  }
                }
              }
            }
          }
          case police-numflat-case {
            container police-numflat {
              tailf:cli-no-keyword;
              tailf:cli-drop-node-name;
              container police {
                tailf:cli-compact-syntax;
                tailf:cli-sequence-commands {
                  tailf:cli-reset-siblings;
                }
                when "contains(../../../../tailfned/police, 'numflat')" {
                  tailf:xpath-root 3;
                  tailf:dependency "../../../../tailfned/police";
                }
                leaf cir {
                  tailf:cli-drop-node-name;
                  tailf:cli-diff-dependency "../../../police-aggregate/police/aggregate" {
                    tailf:xpath-root 3;
                    tailf:cli-trigger-on-set;
                  }
                  type police-bps-type;
                }
                leaf bc {
                  tailf:cli-drop-node-name;
                  type police-burst-type;
                }
                leaf be {
                  tailf:cli-drop-node-name;
                  type police-burst-type;
                }
                container actions {
                  tailf:cli-break-sequence-commands;
                  tailf:cli-no-keyword;
                  tailf:cli-drop-node-name;
                  tailf:cli-flatten-container;
                  uses police-conform-action-grouping;
                  uses police-exceed-action-grouping;
                  uses police-violate-action-grouping;
                }
              }
            }
          }
          case police-cirflat-case {
            container police-cirflat {
              tailf:cli-no-keyword;
              tailf:cli-drop-node-name;
              container police {
                tailf:cli-compact-syntax;
                tailf:cli-sequence-commands {
                  tailf:cli-reset-siblings;
                }
                when "contains(../../../../tailfned/police, 'cirflat')" {
                  tailf:xpath-root 3;
                  tailf:dependency "../../../../tailfned/police";
                }
                leaf cir {
                  tailf:info
                    "Committed information rate";
                  tailf:cli-diff-dependency "../../../police-aggregate/police/aggregate" {
                    tailf:xpath-root 3;
                    tailf:cli-trigger-on-set;
                  }
                  type police-bps-type;
                }
                leaf bc {
                  tailf:info
                    "Conform burst";
                  type police-burst-type;
                }
                container actions {
                  tailf:cli-break-sequence-commands;
                  tailf:cli-no-keyword;
                  tailf:cli-drop-node-name;
                  tailf:cli-flatten-container;
                  uses police-conform-action-grouping;
                  uses police-exceed-action-grouping;
                  uses police-violate-action-grouping;
                }
              }
            }
          }
        }
        container priority {
          tailf:info
            "Strict Scheduling Priority for this Class";
          tailf:cli-compact-syntax;
          tailf:cli-sequence-commands;
          presence "true";
          leaf level {
            tailf:info
              "Multi-Level Priority Queue";
            tailf:cli-optional-in-sequence;
            type uint8 {
              tailf:info
                "<1-2>;;Multi-Level Priority Queue";
              range "1..2";
            }
          }
          choice priority-type {
            leaf kilo-bits {
              tailf:cli-drop-node-name;
              type uint32 {
                tailf:info
                  "<8-2000000>;;Kilo Bits per second";
                range "8..2000000";
              }
            }
            leaf percent {
              tailf:info
                "% of total bandwidth";
              tailf:cli-remove-before-change;
              type uint16 {
                tailf:info
                  "<1-100>;;percentage";
                range "1..100";
              }
            }
          }
          leaf burst {
            tailf:cli-drop-node-name;
            type uint32 {
              tailf:info
                "<32-64000000>;;Burst in bytes";
              range "32..64000000";
            }
          }
        }
        container queue-limit {
          tailf:info
            "Queue Max Threshold for Tail Drop";
          tailf:cli-compact-syntax;
          tailf:cli-sequence-commands {
            tailf:cli-reset-siblings;
          }
          leaf queue-limit-value {
            tailf:cli-drop-node-name;
            type uint32 {
              tailf:info
                "<1-8192000>;;in bytes, <1-3400> in ms, <1-32768> in packets by default";
              range "1..8192000";
            }
          }
          leaf queue-limit-type {
            tailf:cli-drop-node-name;
            type enumeration {
              enum "bytes" {
                tailf:info
                  "in bytes";
              }
              enum "ms" {
                tailf:info
                  "in milliseconds";
              }
              enum "us" {
                tailf:info
                  "in microseconds";
              }
              enum "packets" {
                tailf:info
                  "in packets";
              }
            }
          }
        }
        container random-detect {
          tailf:info
            "Enable Random Early Detection as drop policy";
          tailf:cli-display-separated;
          presence "true";
          container aggregate {
            tailf:info
              "aggregate subclasses";
            tailf:cli-compact-syntax;
            tailf:cli-sequence-commands {
              tailf:cli-reset-siblings;
            }
            presence "true";
            leaf minimum-thresh {
              tailf:info
                "minimum threshold for red aggregate";
              type uint32 {
                tailf:info
                  "<0-1000000>;;minimum threshold (number of packets)";
                range "0..1000000";
              }
            }
            leaf maximum-thresh {
              tailf:info
                "maximum threshold for red aggregate";
              type uint32 {
                tailf:info
                  "<0-1000000>;;maximum threshold (number of packets)";
                range "0..1000000";
              }
            }
            leaf mark-probability {
              tailf:info
                "mark-probability for red aggregate";
              type empty;
            }
            leaf denominator {
              tailf:cli-drop-node-name;
              type uint32 {
                tailf:info
                  "<0-65535>;;mark probability denominator";
                range "0..65535";
              }
            }
          }
          leaf cos-based {
            tailf:cli-reset-container;
            tailf:cli-full-command;
            tailf:cli-diff-dependency "../precedence-based" {
              tailf:xpath-root 3;
              tailf:cli-trigger-on-set;
            }
            tailf:cli-diff-dependency "../precedence" {
              tailf:xpath-root 3;
              tailf:cli-trigger-on-set;
            }
            tailf:cli-diff-dependency "../discard-class-based" {
              tailf:xpath-root 3;
              tailf:cli-trigger-on-set;
            }
            tailf:cli-diff-dependency "../discard-class" {
              tailf:xpath-root 3;
              tailf:cli-trigger-on-set;
            }
            tailf:cli-diff-dependency "../dscp-based" {
              tailf:xpath-root 3;
              tailf:cli-trigger-on-set;
            }
            tailf:cli-diff-dependency "../dscp" {
              tailf:xpath-root 3;
              tailf:cli-trigger-on-set;
            }
            type empty;
          }
          leaf precedence-based {
            tailf:info
              "Enable precedence-based WRED as drop policy";
            tailf:cli-reset-container;
            tailf:cli-full-command;
            tailf:cli-diff-dependency "../discard-class-based" {
              tailf:xpath-root 3;
              tailf:cli-trigger-on-set;
            }
            tailf:cli-diff-dependency "../discard-class" {
              tailf:xpath-root 3;
              tailf:cli-trigger-on-set;
            }
            tailf:cli-diff-dependency "../dscp-based" {
              tailf:xpath-root 3;
              tailf:cli-trigger-on-set;
            }
            tailf:cli-diff-dependency "../dscp" {
              tailf:xpath-root 3;
              tailf:cli-trigger-on-set;
            }
            type empty;
          }
          leaf discard-class-based {
            tailf:info
              "Enable discard-class-based WRED as drop policy";
            tailf:cli-reset-container;
            tailf:cli-full-command;
            tailf:cli-diff-dependency "../dscp-based" {
              tailf:xpath-root 3;
              tailf:cli-trigger-on-set;
            }
            tailf:cli-diff-dependency "../dscp" {
              tailf:xpath-root 3;
              tailf:cli-trigger-on-set;
            }
            type empty;
          }
          leaf dscp-based {
            tailf:info
              "Enable dscp-based WRED as drop policy";
            tailf:cli-reset-container;
            tailf:cli-full-command;
            type empty;
          }
          leaf exponential-weighting-constant {
            tailf:info
              "weight for mean queue depth calculation";
            tailf:cli-full-command;
            type uint16 {
              tailf:info
                "<1-16>;;integer in 1..16 used in weighted average to mean 2^number";
              range "1..16";
            }
          }
          leaf ecn {
            tailf:info
              "explicit congestion notification";
            tailf:cli-full-command;
            type empty;
          }
          list cos {
            tailf:info
              "parameters for each cos value";
            tailf:cli-suppress-mode;
            tailf:cli-delete-when-empty;
            tailf:cli-compact-syntax;
            tailf:cli-sequence-commands;
            tailf:cli-incomplete-command;
            tailf:cli-diff-dependency "../cos-based" {
              tailf:xpath-root 3;
            }
            key "cos";
            leaf cos {
              type uint8 {
                tailf:info
                  "<0-7>;;cos value";
                range "0..7";
              }
            }
            uses random-detect-grouping;
          }
          list precedence {
            tailf:info
              "parameters for each precedence value";
            tailf:cli-suppress-mode;
            tailf:cli-delete-when-empty;
            tailf:cli-compact-syntax;
            tailf:cli-sequence-commands;
            tailf:cli-incomplete-command;
            tailf:cli-diff-dependency "../precedence-based" {
              tailf:xpath-root 3;
            }
            key "prec";
            leaf prec {
              type union {
                type uint8 {
                  tailf:info
                    "<0-7>;;IP precedence";
                  range "0..7";
                }
                type enumeration {
                  enum "rsvp" {
                    tailf:info
                      "rsvp traffic";
                  }
                }
              }
            }
            uses random-detect-grouping;
          }
          list discard-class {
            tailf:info
              "parameters for each discard-class value";
            tailf:cli-suppress-mode;
            tailf:cli-delete-when-empty;
            tailf:cli-compact-syntax;
            tailf:cli-sequence-commands;
            tailf:cli-incomplete-command;
            tailf:cli-diff-dependency "../discard-class-based" {
              tailf:xpath-root 3;
            }
            key "dclass";
            leaf dclass {
              type uint16 {
                tailf:info
                  "<0-7>;;discard-class value";
                range "0..7";
              }
            }
            uses random-detect-grouping;
          }
          list dscp {
            tailf:info
              "parameters for each dscp value";
            tailf:cli-suppress-mode;
            tailf:cli-delete-when-empty;
            tailf:cli-compact-syntax;
            tailf:cli-sequence-commands;
            tailf:cli-incomplete-command;
            tailf:cli-diff-dependency "../dscp-based" {
              tailf:xpath-root 3;
            }
            key "dscpvalue";
            leaf dscpvalue {
              type dscp-type;
            }
            uses random-detect-grouping;
          }
        }
        container set {
          tailf:info
            "Set QoS values";
          leaf atm-clp {
            tailf:info
              "Set ATM CLP bit to 1";
            tailf:cli-full-command;
            type empty;
          }
          container cos {
            tailf:info
              "Set IEEE 802.1Q/ISL class of service/user priority";
            tailf:cli-compact-syntax;
            tailf:cli-sequence-commands;
            choice cos-type {
              case a {
                leaf val {
                  tailf:cli-drop-node-name;
                  type uint16 {
                    range "0..7";
                    tailf:info
                      "<0-7>;;cos value";
                  }
                }
              }
              case b {
                leaf pack {
                  tailf:cli-drop-node-name;
                  type enumeration {
                    enum "dscp" {
                      tailf:code-name "pack_dscp";
                      tailf:info
                        "Set value from packet dscp";
                    }
                    enum "precedence" {
                      tailf:code-name "pack_precedence";
                      tailf:info
                        "Set value from packet precedence.";
                    }
                  }
                }
                leaf table {
                  tailf:info
                    "Set codepoint value based on tablemap.";
                  type string {
                    tailf:info
                      "WORD;;table-map name";
                  }
                  tailf:non-strict-leafref {
                    path "/ncs:devices/ncs:device/ncs:config/ios:table-map/name" {
                      tailf:xpath-root 3;
                    }
                  }
                }
              }
            }
          }
          leaf discard-class {
            tailf:info
              "Discard behavior identifier";
            tailf:cli-full-command;
            type uint16 {
              range "0..7";
              tailf:info
                "<0-7>;;Discard Class value";
            }
          }
          leaf dscp {
            tailf:info
              "Set DSCP in IP(v4) and IPv6 packets";
            tailf:cli-full-command;
            type dscp-type;
          }
          leaf fr-de {
            tailf:info
              "Set FR DE bit to 1";
            tailf:cli-full-command;
            type empty;
          }
          container ip {
            tailf:info
              "Set IP specific values";
            choice ip-choice {
              leaf dscp {
                tailf:info
                  "Set IP DSCP (DiffServ CodePointint)";
                type dscp-type;
              }
              container precedence {
                tailf:info
                  "Set IP precedence";
                presence "Set IP precedence";
                leaf precedence-val {
                  tailf:cli-drop-node-name;
                  type precedence-type;
                }
              }
            }
          }
          container mpls {
            tailf:info
              "Set MPLS specific values";
            container experimental {
              tailf:info
                "Set Experimental value";
              container imposition {
                tailf:info
                  "Set Experimental value at tag imposition";
                leaf exp-value {
                  tailf:cli-drop-node-name;
                  tailf:cli-full-command;
                  type uint8 {
                    tailf:info
                      "<0-7>;;Experimental value";
                    range "0..7";
                  }
                }
              }
            }
          }
          container qos-group {
            tailf:info
              "Set QoS Group";
            leaf qos-group-value {
              tailf:cli-drop-node-name;
              tailf:cli-full-command;
              type uint8 {
                range "0..99";
              }
            }
          }
          container precedence {
            tailf:info
              "Set precedence in IP(v4) and IPv6 packets";
            tailf:cli-sequence-commands;
            tailf:cli-compact-syntax;
            choice precedence-choice {
              case precedence-value {
                leaf precedence-value {
                  tailf:cli-drop-node-name;
                  tailf:cli-no-keyword;
                  type precedence-type;
                }
              }
              case precedence-from-field {
                leaf from-field {
                  tailf:cli-drop-node-name;
                  tailf:cli-no-keyword;
                  type enumeration {
                    enum "cos" {
                      tailf:info
                        "Set packet precedence from L2 COS";
                    }
                    enum "qos-group" {
                      tailf:info
                        "Set packet precedence from QoS Group.";
                    }
                  }
                }
                leaf table {
                  tailf:info
                    "Set packet precedence based on table map.";
                  type string {
                    tailf:info
                      "WORD;;table-map name";
                  }
                  tailf:non-strict-leafref {
                    path "/ncs:devices/ncs:device/ncs:config/ios:table-map/name" {
                      tailf:xpath-root 3;
                    }
                  }
                }
              }
            }
          }
        }
        container shape {
          tailf:info
            "Traffic Shaping";
          leaf adaptive {
            tailf:info
              "Enable Traffic Shaping adaptation to BECN";
            tailf:cli-full-command;
            type uint32 {
              range "8000..154400000";
              tailf:info
                "<8000-154400000>;;Lower Bound Target Bit Rate (bits per second)";
            }
          }
          container average {
            tailf:info
              "configure token bucket: CIR (bps) [Bc (bits) [Be (bits)]], send out Bc only per interval";
            tailf:cli-sequence-commands;
            tailf:cli-compact-syntax;
            choice average-choice {
              case a {
                leaf bit-rate {
                  tailf:cli-drop-node-name;
                  type uint32 {
                    tailf:info
                      "<8000-max>;;Target Bit Rate (bits per second), the value needs to be a multiple of 8000";
                  }
                }
                leaf bits-per-interval-sustained {
                  tailf:cli-drop-node-name;
                  type uint32 {
                    range "256..154400000";
                    tailf:info
                      "<256-154400000>;;bits per interval, sustained. Needs to be multiple of 128. Recommend not to configure it, the algorithm will find out the best value";
                  }
                }
                leaf bits-per-interval-excess {
                  tailf:cli-drop-node-name;
                  type uint32 {
                    range "0..154400000";
                    tailf:info
                      "<0-154400000>;;bits per interval, excess. Needs to be multiple of 128. Bc will be used if you don't configure it.";
                  }
                }
              }
              case b {
                leaf percent {
                  tailf:info
                    "% of interface bandwidth for Committed information rate";
                  type percentage-type;
                }
                leaf burst-size-sustained {
                  tailf:cli-incomplete-command;
                  tailf:cli-drop-node-name;
                  type uint16 {
                    tailf:info
                      "<10-2000>;;Sustained burst size in msec";
                    range "10..2000";
                  }
                }
                leaf ms {
                  tailf:info
                    "milliseconds";
                  type empty;
                }
                container bse {
                  tailf:cli-drop-node-name;
                  tailf:cli-flatten-container;
                  tailf:cli-compact-syntax;
                  tailf:cli-sequence-commands;
                  leaf burst-size-excess {
                    tailf:cli-incomplete-command;
                    type uint16 {
                      tailf:info
                        "<10-2000>;;Excess burst size in msec";
                      range "10..2000";
                    }
                  }
                  leaf ms {
                    tailf:info
                      "milliseconds";
                    type empty;
                  }
                }
              }
            }
          }
          leaf fecn-adapt {
            tailf:info
              "Enable Traffic Shaping reflection of FECN as BECN";
            tailf:cli-full-command;
            type empty;
          }
          container fr-voice-adapt {
            tailf:info
              "Enable rate adjustment depending on voice presence";
            presence "true";
            leaf deactivation {
              type uint16 {
                range "1..10000";
                tailf:info
                  "<1-10000>;;de-activation delay in seconds";
              }
            }
          }
          leaf max-buffers {
            tailf:cli-full-command;
            tailf:info
              "Set Maximum Buffer Limit";
            type uint16 {
              tailf:info
                "<1-4096>;;Maximum Buffer Limit";
              range "1..4096";
            }
          }
        }
        leaf service-policy {
          tailf:info
            "Configure Flow Next";
          tailf:cli-full-command;
          type string;
          tailf:non-strict-leafref {
            path "/ncs:devices/ncs:device/ncs:config/ios:policy-map/name" {
              tailf:xpath-root 3;
            }
          }
        }
        leaf trust {
          tailf:info
            "Set trust value for the class";
          type enumeration {
            enum "cos" {
              tailf:info
                "trust value for the class";
            }
            enum "dscp" {
              tailf:info
                "trust value for the class";
            }
            enum "ip-precedence" {
              tailf:info
                "trust value for the class";
            }
          }
        }
      }
    }
    container bridge-domain {
      tailf:ncs-device-type "cli-ned";
      tailf:display-when "not(../../ncs:module) or ../../ncs:module[ncs:name='tailf-ned-cisco-ios']";
      tailf:info
        "Bridge-domain global configuration commands";
      list bridge-domain-list {
        tailf:cli-drop-node-name;
        tailf:cli-mode-name "config-bdomain";
        tailf:cli-full-command;
        key "id";
        leaf id {
          type uint16 {
            tailf:info
              "<1-8000>;;bridge-domain ID";
            range "1..8000";
          }
        }
        container member {
          tailf:info
            "bridge-domain member";
          leaf vfi {
            tailf:info
              "Configure the Virtual Forwarding Instance (VFI) member";
            type string {
              tailf:info
                "WORD;;Enter VFI name (Max Size 31)";
            }
            tailf:non-strict-leafref {
              path "/ncs:devices/ncs:device/ncs:config/ios:l2vpn-vfi/l2vpn/vfi/context/name" {
                tailf:xpath-root 3;
              }
            }
          }
          list interface-list {
            tailf:cli-drop-node-name;
            tailf:cli-suppress-mode;
            tailf:cli-delete-when-empty;
            tailf:cli-incomplete-command;
            key "name";
            leaf name {
              tailf:cli-disallow-value "vfi";
              type string {
                tailf:info
                  "WORD;;Interface name";
              }
            }
            leaf service-instance {
              tailf:info
                "ethernt service instance";
              type uint16 {
                tailf:info
                  "<1-8000>;;Service Instance Identifier";
                range "1..8000";
              }
            }
          }
        }
        container mac {
          tailf:info
            "MAC Address related commands";
          leaf aging-time {
            tailf:info
              "Set age time of mac addresses per bridge domain";
            type uint16 {
              tailf:info
                "<10-600>;;Aging time in seconds, default 300 seconds (or 1800 seconds for overlay bridge domains)";
            }
          }
        }
      }
    }
    list service-group {
      tailf:ncs-device-type "cli-ned";
      tailf:display-when "not(../ncs:module) or ../ncs:module[ncs:name='tailf-ned-cisco-ios']";
      key "id";
      leaf id {
        type uint32;
      }
      leaf description {
        tailf:cli-multi-value;
        type string;
      }
      container service-policy {
        tailf:info
          "Configure Service Policy";
        uses service-policy-grouping;
      }
    }
    container vlan {
      tailf:ncs-device-type "cli-ned";
      tailf:display-when "not(../../ncs:module) or ../../ncs:module[ncs:name='tailf-ned-cisco-ios']";
      tailf:info
        "VLAN commands";
      choice vlan-accounting-choice {
        leaf accounting {
          tailf:info
            "VLAN accounting configuration";
          tailf:cli-boolean-no;
          tailf:cli-full-command;
          type boolean;
          default "true";
        }
        container accounting-input {
          tailf:cli-drop-node-name;
          container accounting {
            leaf input {
              tailf:cli-boolean-no;
              tailf:cli-full-command;
              type boolean;
              default "true";
            }
          }
        }
        container accounting-output {
          tailf:cli-drop-node-name;
          container accounting {
            leaf output {
              tailf:cli-boolean-no;
              tailf:cli-full-command;
              type boolean;
              default "true";
            }
          }
        }
      }
      container internal {
        tailf:info
          "internal VLAN";
        container allocation {
          tailf:info
            "internal VLAN allocation";
          leaf policy {
            type enumeration {
              enum "ascending" {
                tailf:info
                  "Allocates internal VLANs from 1006 to 4094";
              }
              enum "descending" {
                tailf:info
                  "Allocates internal VLANs from 4094 to 1006.";
              }
            }
          }
        }
      }
      container dot1q {
        tailf:info
          "dot1q parameters";
        container tag {
          tailf:info
            "tag parameters";
          leaf native {
            tailf:info
              "tag native vlan";
            type empty;
          }
        }
      }
      container access-log {
        tailf:info
          "Configure VACL logging";
        leaf maxflow {
          tailf:info
            "Set vacl logging maximum flow number";
          type uint16 {
            tailf:info
              "<0-2048>;;Maximum flow number";
            range "0..2048";
          }
        }
        leaf ratelimit {
          tailf:info
            "Set vacl logging rate limiter";
          type uint16 {
            tailf:info
              "<10-5000>;;Maximum number of packets logged per second";
            range "10..5000";
          }
        }
        leaf threshold {
          tailf:info
            "Set vacl log-update threshold";
          type uint32 {
            tailf:info
              "<0-2147483647>;;log-update threshold (number of hits)";
            range "0..2147483647";
          }
        }
      }
      list vlan-list {
        tailf:cli-drop-node-name;
        tailf:cli-mode-name "config-vlan";
        tailf:cli-range-list-syntax;
        key "id";
        leaf id {
          type uint16 {
            range "1..4094";
            tailf:info
              "<1-3967,4048-4094>;;VLAN ID 1-4094 or range(s): 1-5, 10 or 2-5,7-19";
          }
        }
        leaf name {
          tailf:info
            "Ascii name of the VLAN";
          tailf:cli-multi-value;
          tailf:cli-full-command;
          type string {
            tailf:info
              "The ascii name for the VLAN (Max Size 32)";
            length "1..32";
          }
        }
        leaf remote-span {
          tailf:info
            "Configure as Remote SPAN VLAN";
          tailf:cli-full-command;
          type empty;
        }
        leaf uni-vlan {
          tailf:info
            "Configure a UNI VLAN";
          tailf:cli-full-command;
          type enumeration {
            enum "community" {
              tailf:info
                "UNI/ENI community VLAN";
            }
            enum "isolated" {
              tailf:info
                "UNI/ENI isolated VLAN";
            }
          }
        }
      }
    }
    container lldp {
      tailf:ncs-device-type "cli-ned";
      tailf:display-when "not(../../ncs:module) or ../../ncs:module[ncs:name='tailf-ned-cisco-ios']";
      tailf:info
        "Global LLDP configuration subcommands";
      leaf run {
        tailf:info
          "Enable LLDP";
        type empty;
      }
    }
    container EXEC {
      tailf:ncs-device-type "cli-ned";
      tailf:display-when "not(../../ncs:module) or ../../ncs:module[ncs:name='tailf-ned-cisco-ios']";
      tailf:cli-drop-node-name;
      tailf:action default {
        tailf:actionpoint ncsproxy {
          tailf:internal;
        }
        tailf:info
          "Set a command to its defaults";
        // NCS drop tailf:actionpoint
        input {
          leaf-list args {
            tailf:cli-drop-node-name;
            tailf:cli-flat-list-syntax;
            type string {
              tailf:info
                "default argument(s)";
            }
          }
        }
        output {
          leaf result {
            type string;
          }
        }
      }
      container crypto-key {
        tailf:cli-drop-node-name;
        tailf:action crypto {
          tailf:actionpoint ncsproxy {
            tailf:internal;
          }
          tailf:info
            "Encryption module";
          // NCS drop tailf:actionpoint
          input {
            leaf-list key {
              tailf:info
                "Long term key operations";
              tailf:cli-flat-list-syntax;
              type string {
                tailf:info
                  "crypto key argument(s)";
              }
            }
          }
          output {
            leaf result {
              type string;
            }
          }
        }
      }
      container crypto-pki {
        tailf:cli-drop-node-name;
        container crypto {
          container pki {
            tailf:info
              "Public Key components";
            tailf:action server {
              tailf:actionpoint ncsproxy {
                tailf:internal;
              }
              // NCS drop tailf:actionpoint
              input {
                leaf-list arguments {
                  tailf:cli-drop-node-name;
                  tailf:cli-flat-list-syntax;
                  type string {
                    tailf:info
                      "ACTION:;;crypto pki server <cs-label> [rollover [cancel]]";
                  }
                }
              }
              output {
                leaf result {
                  type string;
                }
              }
            }
            tailf:action enroll {
              tailf:actionpoint ncsproxy {
                tailf:internal;
              }
              tailf:info
                "Request a certificate from a CA";
              // NCS drop tailf:actionpoint
              input {
                leaf-list arguments {
                  tailf:cli-drop-node-name;
                  tailf:cli-flat-list-syntax;
                  type string {
                    tailf:info
                      "ACTION:;;crypto pki enroll <name>";
                  }
                }
              }
              output {
                leaf result {
                  type string;
                }
              }
            }
          }
        }
      }
    }
    container crypto {
      tailf:ncs-device-type "cli-ned";
      tailf:display-when "not(../../ncs:module) or ../../ncs:module[ncs:name='tailf-ned-cisco-ios']";
      tailf:info
        "Encryption module";
      list keyring {
        tailf:info
          "Key ring commands";
        tailf:cli-mode-name "conf-keyring";
        key "name";
        leaf name {
          type string {
            tailf:info
              "WORD;;name of the key ring";
          }
        }
        leaf vrf {
          tailf:info
            "Mention a vrf it belongs to";
          tailf:cli-hide-in-submode;
          type string {
            tailf:info
              "WORD;;the VRF name";
          }
        }
      }
      container logging {
        tailf:info
          "logging messages";
        leaf session {
          tailf:info
            "logging up/down session";
          type empty;
        }
        leaf ikev2 {
          tailf:info
            "logging IKEv2 sessions";
          type empty;
        }
      }
      container ikev2 {
        tailf:info
          "Configure IKEv2 Options";
        list name-mangler {
          tailf:info
            "Name mangler";
          tailf:cli-mode-name "config-ikev2-name-mangler";
          key "name";
          leaf name {
            type string {
              tailf:info
                "WORD;;Name of the mangler";
            }
          }
          leaf fqdn {
            tailf:info
              "Derive name from FQDN identity";
            type enumeration {
              enum "all" {
                tailf:info
                  "entire portion of fqdn identity";
              }
              enum "domain" {
                tailf:info
                  "domain portion of fqdn identity";
              }
              enum "hostname" {
                tailf:info
                  "hostname portion of fqdn identity";
              }
            }
          }
        }
        container authorization {
          tailf:info
            "IKEv2 authorization";
          list policy {
            tailf:info
              "IKEv2 authorization policy";
            tailf:cli-mode-name "config-ikev2-author-policy";
            tailf:cli-full-command;
            key "name";
            leaf name {
              type string {
                tailf:info
                  "WORD;;Name of the policy";
              }
            }
            container aaa {
              tailf:info
                "Specify aaa attribute list";
              container attribute {
                tailf:info
                  "AAA attribute list";
                leaf list {
                  tailf:info
                    "AAA attribute list";
                  type string {
                    tailf:info
                      "WORD;;AAA attribute list name";
                  }
                }
              }
            }
            container route {
              tailf:info
                "specify route parameters";
              container set {
                tailf:info
                  "Specify route set parameters";
                container access-list {
                  tailf:info
                    "Specify the route access-list";
                  leaf ipv4 {
                    tailf:cli-drop-node-name;
                    type std-ip-acl-type;
                  }
                  leaf ipv6 {
                    tailf:info
                      "ipv6 access-list";
                    type string {
                      tailf:info
                        "WORD;;access-list name";
                    }
                  }
                }
                container interface {
                  tailf:info
                    "Specify the route interface [interface-name]";
                  tailf:cli-display-separated;
                  presence "true";
                  list interface-list {
                    tailf:cli-drop-node-name;
                    tailf:cli-suppress-mode;
                    tailf:cli-delete-when-empty;
                    key "name";
                    leaf name {
                      type string {
                        tailf:info
                          "WORD;;Interface name";
                      }
                    }
                  }
                }
              }
              container accept {
                tailf:info
                  "Route accept parameters";
                container any {
                  tailf:info
                    "Accept all subnets from peer";
                  choice any-choice {
                    leaf distance {
                      tailf:info
                        "Specify distance for routes to remote subnets";
                      type uint8 {
                        tailf:info
                          "<1-255>;;Routing distance";
                        range "1..255";
                      }
                      default "1";
                    }
                    leaf tag {
                      tailf:info
                        "Specify tag for routes to remote subnets";
                      type uint32 {
                        tailf:info
                          "<1-497777>;;Routing tag ID";
                        range "1..497777";
                      }
                    }
                  }
                }
              }
            }
          }
        }
        list keyring {
          tailf:info
            "Define IKEv2 Keyring";
          tailf:cli-mode-name "config-ikev2-keyring";
          key "name";
          leaf name {
            type string {
              tailf:info
                "WORD;;Name of IKEv2 Keyring";
            }
          }
          list peer {
            tailf:info
              "Configure a Peer and associated keys";
            tailf:cli-mode-name "config-ikev2-keyring-peer";
            key "name";
            leaf name {
              type string {
                tailf:info
                  "WORD;;Name of the peer block";
              }
            }
            leaf description {
              tailf:info
                "Specify a description of this peer";
              tailf:cli-multi-value;
              tailf:cli-full-command;
              type string {
                tailf:info
                  "LINE;;description of the peer";
              }
            }
            container address {
              tailf:info
                "Specify IPv4/IPv6 address of peer";
              tailf:cli-compact-syntax;
              tailf:cli-sequence-commands {
                tailf:cli-reset-siblings;
              }
              choice address-choice {
                case ipv4 {
                  leaf ipv4-address {
                    tailf:cli-drop-node-name;
                    type inet:ipv4-address {
                      tailf:info
                        "A.B.C.D;;IPv4 Address";
                    }
                  }
                  leaf ipv4-mask {
                    tailf:cli-drop-node-name;
                    type inet:ipv4-address {
                      tailf:info
                        "A.B.C.D;;specify mask";
                    }
                  }
                }
                case ipv6 {
                  leaf ipv6-address {
                    tailf:cli-drop-node-name;
                    type ipv6-prefix {
                      tailf:info
                        "X:X:X:X::X/<0-128>;;IPv6 address/prefix";
                    }
                  }
                }
              }
            }
            container identity {
              tailf:info
                "Specify IKE identity to use";
              container fqdn {
                tailf:info
                  "Use FQDN";
                tailf:cli-compact-syntax;
                tailf:cli-sequence-commands {
                  tailf:cli-reset-siblings;
                }
                leaf domain {
                  tailf:info
                    "email Domain Name";
                  tailf:cli-optional-in-sequence;
                  tailf:cli-incomplete-command;
                  type empty;
                }
                leaf name {
                  tailf:cli-drop-node-name;
                  type string {
                    tailf:info
                      "WORD;;Specify the name string";
                  }
                }
              }
            }
            container pre-shared-key {
              tailf:info
                "specify the pre-shared key";
              tailf:cli-flatten-container;
              tailf:cli-compact-syntax;
              tailf:cli-sequence-commands {
                tailf:cli-reset-siblings;
              }
              uses crypto-key-grouping;
            }
            container pre-shared-key-local {
              tailf:cli-drop-node-name;
              container pre-shared-key {
                container local {
                  tailf:cli-flatten-container;
                  tailf:cli-compact-syntax;
                  tailf:cli-sequence-commands {
                    tailf:cli-reset-siblings;
                  }
                  uses crypto-key-grouping;
                }
              }
            }
            container pre-shared-key-remote {
              tailf:cli-drop-node-name;
              container pre-shared-key {
                container remote {
                  tailf:cli-flatten-container;
                  tailf:cli-compact-syntax;
                  tailf:cli-sequence-commands {
                    tailf:cli-reset-siblings;
                  }
                  uses crypto-key-grouping;
                }
              }
            }
          }
        }
        list profile {
          tailf:info
            "Define IKEv2 Profiles";
          tailf:cli-mode-name "config-ikev2-profile";
          key "name";
          leaf name {
            type string {
              tailf:info
                "WORD;;Name of IKEv2 Profile";
            }
          }
          leaf description {
            tailf:info
              " Specify a description of this profile";
            tailf:cli-multi-value;
            type string {
              tailf:info
                "LINE;;a 1 line description of the profile";
            }
          }
          container match {
            tailf:info
              "Match values of peer";
            leaf fvrf {
              tailf:info
                "fvrf of the profile";
              type union {
                type string {
                  tailf:info
                    "WORD;;fvrf name (default: global)";
                }
                type enumeration {
                  enum "any" {
                    tailf:info
                      "any fvrf";
                  }
                }
              }
            }
            container identity {
              tailf:info
                "IKE identity";
              container remote {
                tailf:info
                  "Remote identity";
                container fqdn {
                  tailf:info
                    "Fully qualified domain name string";
                  list fqdn-list {
                    tailf:cli-drop-node-name;
                    tailf:cli-suppress-mode;
                    tailf:cli-delete-when-empty;
                    key "name";
                    leaf name {
                      type string {
                        tailf:info
                          "WORD;;Specify the name string";
                      }
                    }
                  }
                  list domain {
                    tailf:info
                      "match domain instead of exact";
                    tailf:cli-suppress-mode;
                    tailf:cli-delete-when-empty;
                    key "name";
                    leaf name {
                      type string {
                        tailf:info
                          "WORD;;Specify the name string";
                      }
                    }
                  }
                }
                list address {
                  tailf:info
                    "match address";
                  tailf:cli-suppress-mode;
                  tailf:cli-delete-when-empty;
                  tailf:cli-compact-syntax;
                  key "name";
                  leaf name {
                    type union {
                      type inet:ipv4-address {
                        tailf:info
                          "A.B.C.D;;IP address";
                      }
                      type ipv6-prefix {
                        tailf:info
                          "X:X:X:X::X/<0-128>;;IPv6 prefix x:x::y/<z>";
                      }
                    }
                  }
                  leaf mask {
                    tailf:cli-drop-node-name;
                    type inet:ipv4-address {
                      tailf:info
                        "A.B.C.D;;IP mask";
                    }
                  }
                }
              }
            }
          }
          container identity {
            tailf:info
              "Specify IKE identity to use";
            container local {
              tailf:info
                "Specify the local IKE identity to use for the negotiation";
              choice local-choice {
                leaf email {
                  tailf:info
                    "Fully qualified email string";
                  type string {
                    tailf:info
                      "WORD;;email <user@domain>";
                  }
                }
                leaf fqdn {
                  tailf:info
                    "Fully qualified domain name string";
                  type string {
                    tailf:info
                      "WORD;;FQDN <host.domain>";
                  }
                }
              }
            }
          }
          container authentication {
            tailf:info
              "Set authentication method";
            container local {
              tailf:info
                "Set local authentication method";
              choice method-choice {
                container eap {
                  tailf:info
                    "Extended Authentication Protocol";
                  presence "true";
                }
                leaf ecdsa-sig {
                  tailf:info
                    "ECDSA Signature";
                  type empty;
                }
                container pre-share {
                  tailf:info
                    "Pre-Shared Key";
                  tailf:cli-flatten-container;
                  tailf:cli-compact-syntax;
                  tailf:cli-delete-when-empty;
                  presence "true";
                  container key {
                    tailf:cli-flatten-container;
                    tailf:cli-compact-syntax;
                    tailf:cli-sequence-commands {
                      tailf:cli-reset-siblings;
                    }
                    uses crypto-key-grouping;
                  }
                }
                leaf rsa-sig {
                  tailf:info
                    "Rivest-Shamir-Adleman Signature";
                  type empty;
                }
              }
            }
            container remote {
              tailf:info
                "Set remote authentication method";
              tailf:cli-delete-when-empty;
              presence "true";
              choice method-choice {
                container eap {
                  tailf:info
                    "Extended Authentication Protocol";
                  presence "true";
                }
                leaf ecdsa-sig {
                  tailf:info
                    "ECDSA Signature";
                  type empty;
                }
                container pre-share {
                  tailf:info
                    "Pre-Shared Key";
                  tailf:cli-flatten-container;
                  tailf:cli-compact-syntax;
                  tailf:cli-delete-when-empty;
                  presence "true";
                  container key {
                    tailf:cli-flatten-container;
                    tailf:cli-compact-syntax;
                    tailf:cli-sequence-commands {
                      tailf:cli-reset-siblings;
                    }
                    uses crypto-key-grouping;
                  }
                }
                leaf rsa-sig {
                  tailf:info
                    "Rivest-Shamir-Adleman Signature";
                  type empty;
                }
              }
            }
          }
          container keyring {
            tailf:info
              "Specify keyring to use";
            choice keyring-choice {
              container aaa {
                tailf:info
                  "AAA based keyring";
                tailf:cli-compact-syntax;
                tailf:cli-sequence-commands {
                  tailf:cli-reset-siblings;
                }
                leaf name {
                  tailf:cli-drop-node-name;
                  type string {
                    tailf:info
                      "WORD;;AAA list name";
                  }
                }
                leaf name-mangler {
                  tailf:info
                    "Specify the name-mangler to derive username";
                  type string {
                    tailf:info
                      "WORD;;mangler name";
                  }
                  tailf:non-strict-leafref {
                    path "/ncs:devices/ncs:device/ncs:config/ios:crypto/ikev2/name-mangler/name" {
                      tailf:xpath-root 3;
                    }
                  }
                }
              }
              leaf local {
                tailf:info
                  "Local keyring";
                type string {
                  tailf:info
                    "WORD;;Keyring name";
                }
                tailf:non-strict-leafref {
                  path "/ncs:devices/ncs:device/ncs:config/ios:crypto/ikev2/keyring/name" {
                    tailf:xpath-root 3;
                  }
                }
              }
            }
          }
          container nat {
            tailf:info
              "NAT-transparency";
            leaf keepalive {
              tailf:info
                "NAT keepalive interval";
              type uint16 {
                tailf:info
                  "<5-3600>;;NAT keepalive interval in seconds";
                range "5..3600";
              }
            }
          }
          container aaa {
            tailf:info
              "Specify AAA related configs";
            container authorization {
              tailf:info
                "AAA authorization";
              container group {
                tailf:info
                  "AAA group authorization";
                container psk {
                  tailf:info
                    "AAA list to use when IKEv2 remote auth method is PSK";
                  container list {
                    tailf:info
                      "AAA method list";
                    tailf:cli-compact-syntax;
                    tailf:cli-sequence-commands {
                      tailf:cli-reset-siblings;
                    }
                    leaf list-name {
                      tailf:cli-drop-node-name;
                      type string {
                        tailf:info
                          "WORD;;AAA list name";
                      }
                    }
                    leaf aaa-username {
                      tailf:cli-break-sequence-commands;
                      tailf:cli-drop-node-name;
                      type string {
                        tailf:info
                          "WORD;;AAA username";
                      }
                    }
                    leaf name-mangler {
                      tailf:info
                        "Specify the name-mangler to derive AAA username";
                      type string {
                        tailf:info
                          "WORD;;mangler name";
                      }
                      tailf:non-strict-leafref {
                        path "/ncs:devices/ncs:device/ncs:config/ios:crypto/ikev2/name-mangler/name" {
                          tailf:xpath-root 3;
                        }
                      }
                    }
                    container password {
                      tailf:info
                        "Specify the AAA password";
                      tailf:cli-flatten-container;
                      tailf:cli-compact-syntax;
                      tailf:cli-sequence-commands {
                        tailf:cli-reset-siblings;
                      }
                      uses crypto-key-grouping;
                    }
                  }
                }
              }
              container user {
                tailf:info
                  "AAA user authorization";
                container psk {
                  tailf:info
                    "AAA list to use when IKEv2 remote auth method is PSK";
                  leaf cached {
                    tailf:info
                      "Use cached attributes from EAP authentication or AAA pre-shared key fetch";
                    type empty;
                  }
                  leaf list {
                    tailf:info
                      "AAA method list";
                    type string {
                      tailf:info
                        "WORD;;AAA list name";
                    }
                  }
                }
              }
            }
          }
          leaf virtual-template {
            tailf:info
              "Specify the virtual-template for dynamic interface creation";
            type uint16 {
              tailf:info
                "<1-4095>;;Virtual-template number";
            }
          }
          container dpd {
            tailf:info
              "Enable IKE liveness check for peers";
            tailf:cli-compact-syntax;
            tailf:cli-sequence-commands;
            leaf interval {
              tailf:cli-drop-node-name;
              tailf:cli-incomplete-command;
              type uint16 {
                tailf:info
                  "<10-3600>;;DPD R-U-THERE interval";
                range "10..3600";
              }
            }
            leaf retry-interval {
              tailf:cli-drop-node-name;
              tailf:cli-incomplete-command;
              type uint8 {
                tailf:info
                  "<2-60>;;DPD Retry Interval";
              }
            }
            leaf queries {
              tailf:cli-drop-node-name;
              type enumeration {
                enum "on-demand" {
                  tailf:info
                    "Send DPD queries only as needed";
                }
                enum "periodic" {
                  tailf:info
                    "Send DPD queries at regular intervals";
                }
              }
            }
          }
        }
        container dpd {
          tailf:cli-compact-syntax;
          tailf:cli-sequence-commands {
            tailf:cli-reset-siblings;
          }
          leaf interval {
            tailf:cli-drop-node-name;
            type uint32;
          }
          leaf retry-interval {
            tailf:cli-drop-node-name;
            type uint32;
          }
          leaf mode {
            tailf:cli-drop-node-name;
            type enumeration {
              enum "on-demand";
              enum "periodic";
            }
          }
        }
      }
      container pki {
        tailf:info
          "Public Key components";
        list server {
          tailf:info
            "Enable IOS Certificate server";
          tailf:cli-mode-name "cs-server";
          tailf:cli-compact-syntax;
          tailf:cli-full-command;
          max-elements 1;
          key "cs-label";
          leaf cs-label {
            type string {
              tailf:info
                "WORD;;Certificate Server Name";
            }
          }
          leaf shutdown {
            tailf:info
              "Shutdown the Certificate Server";
            type empty;
          }
          container database {
            tailf:info
              "Certificate Server database config parameters";
            container archive {
              tailf:info
                "Backup Certificate Server Signing Certificate and Keys";
              tailf:cli-compact-syntax;
              tailf:cli-sequence-commands;
              leaf format {
                tailf:cli-drop-node-name;
                type enumeration {
                  enum "pem" {
                    tailf:info
                      "PEM format";
                  }
                  enum "pkcs12" {
                    tailf:info
                      "PKCS12 format";
                  }
                }
              }
              container password {
                tailf:info
                  "Passphrase to protect the private key archive";
                tailf:cli-flatten-container;
                tailf:cli-compact-syntax;
                tailf:cli-sequence-commands {
                  tailf:cli-reset-siblings;
                }
                leaf type {
                  tailf:cli-drop-node-name;
                  tailf:cli-optional-in-sequence;
                  type uint8 {
                    tailf:info
                      "<0-9>;;Encryption type";
                    range "0..9";
                  }
                }
                leaf secret {
                  tailf:cli-drop-node-name;
                  type string {
                    tailf:info
                      "LINE;;Password";
                  }
                }
              }
            }
          }
          leaf grant {
            tailf:info
              "Certificate granting options";
            type enumeration {
              enum "auto" {
                tailf:info
                  "Automatically grant incoming SCEP enrollment requests";
              }
              enum "none" {
                tailf:info
                  "Automatically reject any incoming SCEP enrollment request";
              }
              enum "ra-auto" {
                tailf:info
                  "Automatically grant RA-authorized incoming SCEP enrollment request";
              }
            }
          }
          leaf hash {
            tailf:info
              "Hash algorithm";
            type enumeration {
              enum "md5" {
                tailf:info
                  "use md5 hash algorithm";
              }
              enum "sha1" {
                tailf:info
                  "use sha1 hash algorithm";
              }
              enum "sha256" {
                tailf:info
                  "use sha256 hash algorithm";
              }
              enum "sha384" {
                tailf:info
                  "use sha384 hash algorithm";
              }
              enum "sha512" {
                tailf:info
                  "use sha512 hash algorithm";
              }
            }
          }
        }
        list trustpoint {
          tailf:info
            "Define a CA trustpoint";
          tailf:cli-mode-name "ca-trustpoint";
          tailf:callpoint crypto-pki-trustpoint-hook {
            tailf:set-hook node;
          }
          key "id";
          leaf id {
            type string {
              tailf:info
                "WORD;;CA Server Name";
            }
          }
          container serial-number {
            tailf:info
              "include serial number";
            tailf:cli-reset-container;
            presence "true";
            leaf none {
              tailf:info
                "do not include serial number";
              type empty;
            }
          }
          leaf ip-address {
            tailf:info
              "include ip address";
            tailf:cli-diff-dependency "/ios:interface" {
              tailf:xpath-root 3;
            }
            type union {
              type string {
                tailf:info
                  "LINE;;interface name or ip address";
              }
              type enumeration {
                enum "none" {
                  tailf:info
                    "do not include ip address";
                }
              }
            }
          }
          container enrollment {
            tailf:info
              "Enrollment parameters";
            leaf http-proxy {
              tailf:info
                "HTTP proxy server for enrollment";
              type string {
                tailf:info
                  "WORD;;host-name";
              }
            }
            container mode {
              tailf:info
                "Mode supported by the Certificate Authority";
              leaf ra {
                tailf:info
                  "Registration Authority mode";
                type empty;
              }
            }
            leaf profile {
              tailf:info
                "Specify an profile for enrollment";
              type string {
                tailf:info
                  "WORD;;Profile name";
              }
            }
            container retry {
              tailf:info
                "Polling parameters";
              leaf count {
                tailf:info
                  "How many times to poll CA for our certificate";
                type uint8 {
                  tailf:info
                    "<1-100>;;Number of times to poll a CA for a certificate";
                  range "1..100";
                }
              }
              leaf period {
                tailf:info
                  "How long to wait between requests to CA for our certificate";
                type uint8 {
                  tailf:info
                    "<1-60>;;Period in minutes between attempts to contact a CA";
                  range "1..60";
                }
              }
            }
            leaf selfsigned {
              tailf:info
                "Generate a Self Signed Certificate";
              type empty;
            }
            container terminal {
              tailf:info
                "Enroll via the terminal (cut-and-paste)";
              leaf pem {
                tailf:info
                  "Include PEM encapsulation boundaries";
                type empty;
              }
            }
            leaf url {
              tailf:info
                "CA server enrollment URL";
              type string {
                tailf:info
                  "WORD;;HTTP URL";
              }
            }
          }
          leaf subject-name {
            tailf:info
              "Subject Name";
            type string {
              tailf:info
                "LINE;;Subject Name";
            }
          }
          leaf revocation-check {
            tailf:info
              "Revocation checking options";
            type enumeration {
              enum "crl" {
                tailf:info
                  "Revocation check by CRL";
              }
              enum "none" {
                tailf:info
                  "Ignore revocation check";
              }
              enum "ocsp" {
                tailf:info
                  "Revocation check by OCSP";
              }
            }
          }
          leaf rsakeypair {
            tailf:info
              "Specify rsakeypair for this identity";
            type string {
              tailf:info
                "WORD;;RSA keypair label";
            }
          }
        }
        container certificate {
          tailf:info
            "Actions on certificates";
          list chain {
            tailf:info
              "Identify certificates";
            tailf:cli-mode-name "config-cert-chain";
            key "name";
            leaf name {
              type string {
                tailf:info
                  "WORD;;CA Server Name";
              }
            }
            list certificate {
              tailf:info
                "Certificate issued by the CA";
              tailf:cli-mode-name "config-pki-hexmode-quotedstring";
              tailf:cli-delete-when-empty;
              tailf:cli-exit-command "quit";
              tailf:cli-compact-syntax;
              tailf:cli-sequence-commands;
              tailf:cli-full-command;
              tailf:cli-reset-container;
              key "serial";
              leaf serial {
                tailf:cli-disallow-value "rollover|ca|ra-encrypt|ra-general|ra-sign|self-signed";
                type string {
                  tailf:info
                    "WORD;;Certificate serial number";
                }
              }
              leaf cert-type {
                tailf:cli-optional-in-sequence;
                tailf:cli-drop-node-name;
                tailf:cli-prefix-key;
                type enumeration {
                  enum "ca" {
                    tailf:info
                      "A certificate";
                  }
                  enum "ra-encrypt" {
                    tailf:info
                      "A encryption certificate";
                  }
                  enum "ra-general" {
                    tailf:info
                      "A general purpose certificate";
                  }
                  enum "ra-sign" {
                    tailf:info
                      "A signing certificate";
                  }
                  enum "rollover" {
                    tailf:info
                      "Shadow rollover certificate";
                  }
                  enum "self-signed" {
                    tailf:info
                      "Self-signed certificate";
                  }
                }
              }
              leaf rollover {
                tailf:info
                  "Shadow rollover certificate";
                tailf:cli-optional-in-sequence;
                tailf:cli-prefix-key;
                type empty;
              }
              leaf cert {
                tailf:cli-drop-node-name;
                tailf:cli-disallow-value "rollover|ca|ra-encrypt|ra-general|ra-sign|self-signed";
                type string {
                  tailf:info
                    "WORD;;file specification";
                }
              }
            }
          }
        }
        container token {
          tailf:info
            "Configure cryptographic token";
          list token-name {
            tailf:cli-suppress-mode;
            tailf:cli-delete-when-empty;
            tailf:cli-drop-node-name;
            tailf:cli-compact-syntax;
            key "name";
            leaf name {
              type string {
                tailf:info
                  "WORD;;token name";
              }
            }
            uses crypto-pki-token-grouping;
          }
        }
        container default {
          tailf:info
            "set default values for tokens";
          uses crypto-pki-token-grouping;
        }
      }
      container isakmp {
        tailf:info
          "Configure ISAKMP policy";
        leaf enable {
          tailf:info
            "Enable ISAKMP";
          tailf:cli-boolean-no;
          tailf:cli-full-command;
          type boolean;
          default "true";
        }
        list profile {
          tailf:info
            "Define ISAKMP Profiles";
          tailf:cli-mode-name "conf-isa-prof";
          key "name";
          leaf name {
            type string {
              tailf:info
                "WORD;;Name of ISAKMP Profile";
            }
          }
          leaf vrf {
            tailf:info
              "Specify the VRF it is related to";
            type string {
              tailf:info
                "WORD;;VRF Name";
            }
          }
          list keyring {
            tailf:info
              "Specify keyring to use";
            tailf:cli-suppress-mode;
            tailf:cli-delete-when-empty;
            key "name";
            leaf name {
              type union {
                type enumeration {
                  enum "default" {
                    tailf:info
                      "Use global keyring";
                  }
                }
                type string {
                  tailf:info
                    "WORD;;Name of the keyring to use";
                }
              }
            }
          }
          container match {
            tailf:info
              "Match values of peer";
            leaf fvrf {
              tailf:info
                "fvrf of the profile";
              type union {
                type string {
                  tailf:info
                    "WORD;;fvrf name (default: global)";
                }
                type enumeration {
                  enum "any" {
                    tailf:info
                      "any fvrf";
                  }
                }
              }
            }
            container identity {
              tailf:info
                "Peer identity";
              container address {
                tailf:info
                  "IP Address(es)";
                container ipv4 {
                  tailf:cli-drop-node-name;
                  tailf:cli-compact-syntax;
                  tailf:cli-sequence-commands {
                    tailf:cli-reset-siblings;
                  }
                  leaf address {
                    tailf:cli-drop-node-name;
                    type inet:ipv4-address {
                      tailf:info
                        "A.B.C.D;;IP address prefix";
                    }
                  }
                  leaf mask {
                    tailf:cli-drop-node-name;
                    type inet:ipv4-address {
                      tailf:info
                        "A.B.C.D;;specify mask";
                    }
                  }
                }
              }
            }
          }
        }
        list policy {
          tailf:info
            "Set policy for an ISAKMP protection suite";
          tailf:cli-mode-name "config-isakmp";
          key "priority";
          leaf priority {
            type uint16 {
              tailf:info
                "<1-10000>;;Priority of protection suite";
            }
          }
          container encryption {
            tailf:info
              "Set encryption algorithm for protection suite";
            tailf:cli-compact-syntax;
            tailf:cli-sequence-commands {
              tailf:cli-reset-siblings;
            }
            leaf algorithm {
              tailf:cli-drop-node-name;
              type enumeration {
                enum "des" {
                  tailf:info
                    "DES - Data Encryption Standard (56 bit keys).";
                }
                enum "3des" {
                  tailf:info
                    "Three key triple DES";
                }
                enum "aes" {
                  tailf:info
                    "AES - Advanced Encryption Standard.";
                }
              }
              default "des";
            }
            leaf bits {
              when "../algorithm = 'aes'" {
                tailf:xpath-root 3;
              }
              tailf:cli-drop-node-name;
              type enumeration {
                enum "128" {
                  tailf:info
                    "128 bit keys.";
                }
                enum "192" {
                  tailf:info
                    "192 bit keys.";
                }
                enum "256" {
                  tailf:info
                    "256 bit keys.";
                }
              }
              default "128";
            }
          }
          leaf hash {
            tailf:info
              "Set hash algorithm for protection suite";
            type enumeration {
              enum "md5" {
                tailf:info
                  "Message Digest 5";
              }
              enum "sha" {
                tailf:info
                  "Secure Hash Standard";
              }
              enum "sha256" {
                tailf:info
                  "Secure Hash Standard";
              }
            }
            default "sha";
          }
          leaf authentication {
            tailf:info
              "Set authentication method for protection suite";
            type enumeration {
              enum "pre-share" {
                tailf:info
                  "Pre-Shared Key";
              }
              enum "rsa-encr" {
                tailf:info
                  "Rivest-Shamir-Adleman Encryption";
              }
              enum "rsa-sig" {
                tailf:info
                  "Rivest-Shamir-Adleman Signature";
              }
            }
          }
          leaf group {
            tailf:info
              "Set the Diffie-Hellman group";
            type enumeration {
              enum "1" {
                tailf:info
                  "Diffie-Hellman group 1 (768 bit)";
              }
              enum "2" {
                tailf:info
                  "Diffie-Hellman group 2 (1024 bit)";
              }
              enum "5" {
                tailf:info
                  "Diffie-Hellman group 5 (1536 bit)";
              }
              enum "14" {
                tailf:info
                  "Diffie-Hellman group 14 (2048 bit)";
              }
              enum "15" {
                tailf:info
                  "Diffie-Hellman group 15 (3072 bit)";
              }
              enum "16" {
                tailf:info
                  "Diffie-Hellman group 16 (4096 bit)";
              }
              enum "19" {
                tailf:info
                  "Diffie-Hellman group 19 (256 bit ecp)";
              }
              enum "20" {
                tailf:info
                  "Diffie-Hellman group 20 (384 bit ecp)";
              }
              enum "21" {
                tailf:info
                  "Diffie-Hellman group 21 (521 bit ecp)";
              }
              enum "24" {
                tailf:info
                  "Diffie-Hellman group 24 (2048 bit, 256 bit subgroup)";
              }
            }
          }
          leaf lifetime {
            tailf:info
              "Set lifetime for ISAKMP security association";
            type uint32 {
              tailf:info
                "<60-86400>;;lifetime in seconds";
              range "60..86400";
            }
            default "86400";
          }
        }
        container keepalive {
          tailf:info
            "Set a keepalive interval for use with IOS peers";
          tailf:cli-compact-syntax;
          tailf:cli-sequence-commands {
            tailf:cli-reset-siblings;
          }
          leaf seconds {
            tailf:cli-drop-node-name;
            type uint16 {
              tailf:info
                "<10-3600>;;Number of seconds between keep alives";
              range "10..3600";
            }
          }
          leaf periodic {
            tailf:info
              "When using Dead Peer Detection (DPD), send periodic DPD messages";
            type empty;
          }
        }
        container nat {
          tailf:info
            "Set a nat  keepalive interval for use with IOS peers";
          container keepalive {
            tailf:info
              "Set a keepalive interval for use with IOS peers";
            leaf seconds {
              tailf:cli-drop-node-name;
              type uint16 {
                tailf:info
                  "<5-3600>;;Number of seconds between keep alives";
                range "5..3600";
              }
            }
          }
        }
        list key {
          tailf:info
            "Set pre-shared key for remote peer";
          tailf:cli-suppress-mode;
          tailf:cli-delete-when-empty;
          tailf:cli-compact-syntax;
          tailf:cli-sequence-commands {
            tailf:cli-reset-siblings;
          }
          tailf:cli-incomplete-command;
          key "keystring";
          leaf keystring {
            type string {
              tailf:info
                "WORD;;The UNENCRYPTED (cleartext) user password";
            }
          }
          leaf encrypted {
            tailf:cli-drop-node-name;
            tailf:cli-prefix-key;
            tailf:cli-optional-in-sequence;
            type enumeration {
              enum "6" {
                tailf:info
                  "Specifies an ENCRYPTED password will follow";
              }
            }
          }
          choice peer-choice {
            container address {
              tailf:info
                "define shared key with IP address";
              tailf:cli-flatten-container;
              tailf:cli-compact-syntax;
              tailf:cli-sequence-commands;
              choice address-choice {
                case a {
                  leaf ipv4 {
                    tailf:cli-drop-node-name;
                    type inet:ipv4-address {
                      tailf:info
                        "A.B.C.D;;Peer IP address";
                    }
                  }
                }
                case b {
                  leaf ipv4-address {
                    tailf:cli-drop-node-name;
                    type inet:ipv4-address {
                      tailf:info
                        "A.B.C.D;;Peer IP address";
                    }
                  }
                  leaf ipv4-mask {
                    tailf:cli-drop-node-name;
                    type inet:ipv4-address {
                      tailf:info
                        "A.B.C.D;;Peer IP subnet mask";
                    }
                  }
                }
                case c {
                  leaf ipv6 {
                    tailf:info
                      "define shared key with IPv6 address";
                    type ipv6-prefix {
                      tailf:info
                        "X:X:X:X::X/<0-128>;;Peer IPv6 prefix";
                    }
                  }
                }
              }
            }
            leaf hostname {
              tailf:info
                "define shared key with hostname";
              type string {
                tailf:info
                  "WORD;;hostname of peer with whom the key is shared";
              }
            }
          }
          leaf no-xauth {
            tailf:info
              "Bypasses XAuth for this peer";
            type empty;
          }
        }
      }
      container ipsec {
        tailf:info
          "Configure IPSEC policy";
        container optional {
          tailf:info
            "Enable optional encryption for IPSec";
          tailf:cli-delete-when-empty;
          presence "true";
          leaf retry {
            tailf:info
              "Configure length of IPSec retry interval";
            type uint32 {
              tailf:info
                "<60-86400>;;Number of seconds between IPSec retries";
              range "60..86400";
            }
          }
        }
        container security-association {
          tailf:info
            "Security association parameters";
          leaf idle-time {
            tailf:info
              "Automatically delete IPSec SAs after a given idle period.";
            type uint32 {
              tailf:info
                "<60-86400>;;Idle time at which IPSec SAs are deleted";
              range "60..86400";
            }
          }
          container lifetime {
            tailf:info
              "security association lifetime";
            leaf kilobytes {
              tailf:info
                "Volume-based key duration";
              type union {
                type uint32 {
                  tailf:info
                    "<2560-4294967295>;;Security association duration in kilobytes encrypted";
                }
                type enumeration {
                  enum "disable" {
                    tailf:info
                      "Disable Volume-based Rekey";
                  }
                }
              }
            }
            leaf seconds {
              tailf:info
                "Time-based key duration";
              type uint32 {
                tailf:info
                  "<120-86400>;;Security association duration in seconds";
                range "120..86400";
              }
            }
          }
          container replay {
            tailf:info
              "Set replay checking.";
            leaf disable {
              tailf:info
                "Disable replay checking";
              type empty;
            }
            leaf window-size {
              tailf:info
                "Set replay window size.";
              type ipsec-window-size-type;
            }
          }
        }
        list transform-set {
          tailf:info
            "Define transform and settings";
          tailf:cli-mode-name "cfg-crypto-trans";
          tailf:cli-compact-syntax;
          tailf:cli-sequence-commands;
          tailf:cli-incomplete-command;
          key "name";
          leaf name {
            type string {
              tailf:info
                "WORD;;Transform set tag";
            }
          }
          leaf transform1 {
            tailf:cli-drop-node-name;
            tailf:cli-hide-in-submode;
            type crypto-ipsec-transform-type;
          }
          leaf transform1-bits {
            when "../transform1 = 'esp-aes'" {
              tailf:xpath-root 3;
            }
            tailf:cli-drop-node-name;
            tailf:cli-optional-in-sequence;
            tailf:cli-hide-in-submode;
            type crypto-ipsec-transform-bits-type;
          }
          leaf transform2 {
            tailf:cli-drop-node-name;
            tailf:cli-hide-in-submode;
            type crypto-ipsec-transform-type;
          }
          leaf transform2-bits {
            when "../transform2 = 'esp-aes'" {
              tailf:xpath-root 3;
            }
            tailf:cli-drop-node-name;
            tailf:cli-optional-in-sequence;
            tailf:cli-hide-in-submode;
            type crypto-ipsec-transform-bits-type;
          }
          leaf transform3 {
            tailf:cli-drop-node-name;
            tailf:cli-hide-in-submode;
            type crypto-ipsec-transform-type;
          }
          leaf transform3-bits {
            when "../transform3 = 'esp-aes'" {
              tailf:xpath-root 3;
            }
            tailf:cli-drop-node-name;
            tailf:cli-optional-in-sequence;
            tailf:cli-hide-in-submode;
            type crypto-ipsec-transform-bits-type;
          }
          leaf transform4 {
            tailf:cli-drop-node-name;
            tailf:cli-hide-in-submode;
            type crypto-ipsec-transform-type;
          }
          leaf transform4-bits {
            when "../transform4 = 'esp-aes'" {
              tailf:xpath-root 3;
            }
            tailf:cli-drop-node-name;
            tailf:cli-optional-in-sequence;
            tailf:cli-hide-in-submode;
            type crypto-ipsec-transform-bits-type;
          }
          leaf mode {
            tailf:info
              "encapsulation mode (transport/tunnel)";
            type enumeration {
              enum "transport" {
                tailf:info
                  "transport (payload encapsulation) mode";
              }
              enum "tunnel" {
                tailf:info
                  "tunnel (datagram encapsulation) mode";
              }
            }
            default "tunnel";
          }
        }
        container default {
          tailf:info
            "Default transform-set";
          leaf transform-set {
            tailf:cli-boolean-no;
            tailf:cli-full-command;
            type boolean;
            default "true";
          }
        }
        leaf fragmentation {
          tailf:info
            "Handling of fragmentation of near-MTU sized packets";
          type enumeration {
            enum "after-encryption" {
              tailf:info
                "Perform fragmentation of large packets after IPSec encapsulation.";
            }
            enum "before-encryption" {
              tailf:info
                "Perform fragmentation of large packets before IPSec encapsulation.";
            }
          }
        }
        leaf df-bit {
          tailf:info
            "Handling of encapsulated DF bit.";
          type enumeration {
            enum "clear" {
              tailf:info
                "Clear DF bit for encapsulated packets.";
            }
            enum "copy" {
              tailf:info
                "Copy DF bit from inner for encapsulated packets.";
            }
            enum "set" {
              tailf:info
                "Set DF bit for encapsulated packets.";
            }
          }
        }
        leaf nat-transparency {
          tailf:info
            "IPsec NAT transparency model";
          type enumeration {
            enum "spi-matching" {
              tailf:info
                "Match inbound SPI to outbound SPI for IPsec aware NAT";
            }
            enum "udp-encapsulation" {
              tailf:info
                "UDP encapsulation of IPsec protocols";
            }
          }
        }
        list profile {
          tailf:info
            "Configure an ipsec policy profile";
          tailf:cli-mode-name "ipsec-profile";
          key "name";
          leaf name {
            type string {
              tailf:info
                "WORD;;Profile name";
            }
          }
          container set {
            tailf:info
              "Set values for encryption/decryption";
            container security-association {
              tailf:info
                "Security association parameters";
              container lifetime {
                tailf:info
                  "security association lifetime";
                leaf kilobytes {
                  tailf:info
                    "Volume-based key duration";
                  type union {
                    type uint32 {
                      tailf:info
                        "<2560-4294967295>;;Security association duration in kilobytes encrypted";
                    }
                    type enumeration {
                      enum "disable" {
                        tailf:info
                          "Disable Volume-based Rekey";
                      }
                    }
                  }
                }
                leaf seconds {
                  tailf:info
                    "Time-based key duration";
                  type uint32 {
                    tailf:info
                      "<120-86400>;;Security association duration in seconds";
                    range "120..86400";
                  }
                }
              }
            }
            leaf transform-set {
              tailf:info
                "Specify list of transform sets in priority order";
              type string {
                tailf:info
                  "WORD;;Proposal tag";
              }
              tailf:non-strict-leafref {
                path "/ncs:devices/ncs:device/ncs:config/ios:crypto/ipsec/transform-set/name" {
                  tailf:xpath-root 3;
                }
              }
            }
            leaf ikev2-profile {
              type string {
                tailf:info
                  "WORD;;Profile name";
              }
              tailf:non-strict-leafref {
                path "/ncs:devices/ncs:device/ncs:config/ios:crypto/ikev2/profile/name" {
                  tailf:xpath-root 3;
                }
              }
            }
          }
        }
      }
      container gdoi {
        tailf:info
          "Configure GDOI policy";
        list group {
          tailf:info
            "Define a GDOI group";
          tailf:cli-mode-name "config-gdoi-group";
          key "name";
          leaf name {
            tailf:cli-disallow-value "ipv6";
            type string {
              tailf:info
                "WORD;;Group Name";
            }
          }
          leaf ipv6 {
            tailf:cli-prefix-key;
            type empty;
          }
          container identity {
            tailf:info
              "Set the identity of the group";
            choice identify-choice {
              leaf number {
                tailf:info
                  "Set the identity of the group as a number";
                type uint32 {
                  tailf:info
                    "<0-2147483647>;;Set the group number";
                }
              }
              container address {
                tailf:info
                  "Set the identity of the group as an address";
                leaf ipv4 {
                  tailf:info
                    "Set the identity of the group as an IPv4 address";
                  type inet:ipv4-address {
                    tailf:info
                      "A.B.C.D;;Group IPv4 address";
                  }
                }
              }
            }
          }
          container server {
            tailf:info
              "Set the group server for of the group";
            container local {
              tailf:info
                "Identify a group server defined locally";
              tailf:cli-add-mode;
              tailf:cli-mode-name "gdoi-local-server";
              tailf:cli-delete-when-empty;
              presence "true";
              must 'not(../address/ipv4/name)' {
                tailf:xpath-root 3;
                error-message "Cannot Configure the key server as local.";
                tailf:dependency "../address/ipv4/name";
              }
              tailf:cli-diff-dependency "../address/ipv4/name" {
                tailf:xpath-root 3;
                tailf:cli-trigger-on-set;
              }
              container rekey {
                tailf:info
                  "Configure rekey policy for the group";
                container lifetime {
                  tailf:info
                    "Define the rekey lifetime";
                  choice lifetime-choice {
                    leaf seconds {
                      tailf:info
                        "Time-based key duration";
                      type uint32 {
                        tailf:info
                          "<300-86400>;;Lifetime in seconds";
                      }
                      default "86400";
                    }
                    leaf days {
                      type uint32 {
                        tailf:info
                          "Lifetime in days";
                      }
                    }
                    default "seconds";
                  }
                }
                container retransmit {
                  tailf:info
                    "Define the rekey retransmission parameters";
                  tailf:cli-compact-syntax;
                  tailf:cli-sequence-commands {
                    tailf:cli-reset-siblings;
                  }
                  leaf number-of-seconds {
                    tailf:cli-drop-node-name;
                    type uint8 {
                      tailf:info
                        "<10-60>;;Retransmit after this many seconds";
                      range "10..60";
                    }
                  }
                  choice retransmit-choice {
                    leaf number {
                      tailf:info
                        "Retransmit this many times";
                      type uint8 {
                        tailf:info
                          "<1-10>;;Number of retransmissions";
                        range "1..10";
                      }
                    }
                    leaf periodic {
                      type empty;
                    }
                  }
                }
                container authentication {
                  tailf:info
                    "Identify the rekey authentication keypair";
                  tailf:cli-compact-syntax;
                  tailf:cli-sequence-commands {
                    tailf:cli-reset-siblings;
                  }
                  choice authentication-choice {
                    leaf mypubkey {
                      tailf:info
                        "Identify a keypair associated with this device";
                      type empty;
                    }
                    leaf pubkey {
                      type empty;
                    }
                  }
                  leaf rsa {
                    tailf:info
                      "Identify an RSA keypair";
                    type string {
                      tailf:info
                        "WORD;;Key name";
                    }
                  }
                }
                container transport {
                  tailf:info
                    "Specify the rekey distribution method";
                  leaf unicast {
                    tailf:info
                      "specify unicast rekey distribution";
                    type empty;
                  }
                }
              }
              container replay {
                container time {
                  leaf window-size {
                    type uint32;
                  }
                }
              }
              container sa {
                tailf:info
                  "Configure a security association";
                list ipsec {
                  tailf:info
                    "Configure an IPsec SA";
                  tailf:cli-mode-name "gdoi-sa-ipsec";
                  key "id";
                  leaf id {
                    type uint32 {
                      tailf:info
                        "<1-65535>;;Sequence to insert into SA list";
                      range "1..65535";
                    }
                  }
                  leaf profile {
                    tailf:info
                      "Configure an ipsec profile for the SA";
                    type string {
                      tailf:info
                        "WORD;;Profile name";
                    }
                    tailf:non-strict-leafref {
                      path "/ncs:devices/ncs:device/ncs:config/ios:crypto/ipsec/profile/name" {
                        tailf:xpath-root 3;
                      }
                    }
                  }
                  container match {
                    tailf:info
                      "Match characteristics of packets to encrypt";
                    container address {
                      tailf:info
                        "Match addresses of packets to encrypt";
                      choice address-choice {
                        leaf ipv4 {
                          tailf:info
                            "Match ipv4 packets";
                          type ext-ip-acl-type;
                        }
                        leaf ipv6 {
                          tailf:info
                            "Match ipv6 packets";
                          type string {
                            tailf:info
                              "WORD;;IPv6 access list";
                          }
                          tailf:non-strict-leafref {
                            path "/ncs:devices/ncs:device/ncs:config/ios:ipv6/access-list/named-acl/name" {
                              tailf:xpath-root 3;
                            }
                          }
                        }
                      }
                    }
                  }
                  container replay {
                    tailf:info
                      "Set replay method";
                    container counter {
                      tailf:info
                        "Enable anti-replay check for single source traffic by using sequence number";
                      leaf window-size {
                        tailf:info
                          "Set replay window size.";
                        type ipsec-window-size-type;
                      }
                    }
                  }
                }
              }
              container address {
                tailf:info
                  "Configure server source address";
                leaf ipv4 {
                  tailf:info
                    "Set ipv4 address of local server";
                  type union {
                    type inet:ipv4-address {
                      tailf:info
                        "A.B.C.D;;IPv4 local address";
                    }
                    type string {
                      tailf:info
                        "WORD;;Interface name";
                    }
                  }
                }
              }
              container redundancy {
                tailf:info
                  "Enter cooperative key server configuration mode";
                tailf:cli-add-mode;
                tailf:cli-mode-name "gdoi-coop-ks-config";
                tailf:cli-full-command;
                container local {
                  tailf:info
                    "Local key server configurations";
                  tailf:cli-delete-when-empty;
                  presence "true";
                  leaf priority {
                    tailf:info
                      "Set local server priority";
                    type uint8 {
                      tailf:info
                        "<1-255>;;Local server priority";
                    }
                  }
                }
                container peer {
                  tailf:info
                    "Peer server configurations";
                  container address {
                    tailf:info
                      "Peer server address";
                    leaf ipv4 {
                      tailf:info
                        "Set peer server ipv4 address";
                      type inet:ipv4-address {
                        tailf:info
                          "A.B.C.D;;Peer server ipv4 address";
                      }
                    }
                  }
                }
              }
            }
            container address {
              tailf:info
                "Identify the group server by address";
              list ipv4 {
                tailf:info
                  "Set the IPv4 address of the group server";
                tailf:cli-suppress-mode;
                tailf:cli-delete-when-empty;
                must 'not(../../local)' {
                  tailf:xpath-root 3;
                  error-message "Key server is already configured as local";
                  tailf:dependency "../../local";
                }
                tailf:cli-diff-dependency "../../local" {
                  tailf:xpath-root 3;
                  tailf:cli-trigger-on-set;
                }
                key "name";
                leaf name {
                  type inet:ipv4-address {
                    tailf:info
                      "A.B.C.D;;Group server IPv4 address";
                  }
                }
              }
            }
          }
          container client {
            tailf:info
              "Set the group client management/register interface";
            container registration {
              tailf:info
                "Set the group client management/register interface";
              container interface {
                tailf:info
                  "Set the group client management/register interface";
                uses interface-name-grouping;
              }
            }
          }
        }
      }
      list dynamic-map {
        tailf:info
          "Specify a dynamic crypto map template";
        tailf:cli-mode-name "config-crypto-map";
        key "name map-entry";
        leaf name {
          type string {
            tailf:info
              "WORD;;Dynamic crypto map template tag";
          }
        }
        leaf map-entry {
          type uint32 {
            tailf:info
              "<1-65535>;;Sequence to insert into dynamic-map entry";
          }
        }
        container set {
          tailf:info
            "Set values for encryption/decryption";
          leaf isakmp-profile {
            tailf:info
              " Specify isakmp Profile";
            type string {
              tailf:info
                "WORD;;Name the isakmp profile";
            }
            tailf:non-strict-leafref {
              path "/ncs:devices/ncs:device/ncs:config/ios:crypto/isakmp/profile/name" {
                tailf:xpath-root 3;
              }
            }
          }
          leaf-list transform-set {
            tailf:info
              "Specify list of transform sets in priority order";
            tailf:cli-replace-all;
            tailf:cli-flat-list-syntax;
            type string {
              tailf:info
                "WORD;;Proposal tag";
            }
            tailf:non-strict-leafref {
              path "/ncs:devices/ncs:device/ncs:config/ios:crypto/ipsec/transform-set/name" {
                tailf:xpath-root 3;
              }
            }
          }
        }
        container match {
          tailf:info
            "Match values.";
          leaf address {
            tailf:info
              "Match address of packets to encrypt";
            type ext-acl-type;
          }
        }
      }
      list map {
        tailf:info
          "Enter a crypto map";
        tailf:cli-suppress-mode;
        tailf:cli-delete-when-empty;
        tailf:cli-compact-syntax;
        tailf:cli-sequence-commands;
        tailf:cli-incomplete-command;
        key "name";
        leaf name {
          tailf:cli-disallow-value "ipv6";
          type string {
            tailf:info
              "WORD;;Crypto map tag";
          }
        }
        leaf ipv6 {
          tailf:cli-prefix-key;
          tailf:cli-optional-in-sequence;
          type empty;
        }
        container local-address {
          tailf:info
            "Interface to use for local address for this crypto map";
          tailf:cli-optional-in-sequence;
          uses interface-name-grouping;
        }
        list seq-list {
          tailf:cli-drop-node-name;
          tailf:cli-mode-name "config-crypto-map";
          tailf:cli-compact-syntax;
          tailf:cli-sequence-commands;
          tailf:cli-incomplete-command;
          key "id";
          leaf id {
            tailf:cli-suppress-range;
            type uint16 {
              tailf:info
                "<1-65535>;;Sequence to insert into crypto map entry";
            }
          }
          leaf policy {
            tailf:cli-drop-node-name;
            tailf:cli-hide-in-submode;
            type enumeration {
              enum "ipsec-isakmp" {
                tailf:info
                  "IPSEC w/ISAKMP";
              }
              enum "ipsec-manual" {
                tailf:info
                  "IPSEC w/manual keying";
              }
              enum "gdoi" {
                tailf:info
                  "GDOI";
              }
            }
          }
          leaf dynamic {
            tailf:info
              "Enable dynamic crypto map support";
            tailf:cli-hide-in-submode;
            tailf:cli-optional-in-sequence;
            tailf:cli-full-command;
            when "../policy = 'ipsec-isakmp'" {
              tailf:xpath-root 3;
              tailf:dependency "../policy";
            }
            type string {
              tailf:info
                "WORD;;Name of dynamic-map template";
            }
            tailf:non-strict-leafref {
              path "/ncs:devices/ncs:device/ncs:config/ios:crypto/dynamic-map/name" {
                tailf:xpath-root 3;
              }
            }
          }
          leaf profile {
            tailf:info
              "Enable crypto map as a crypto-profile";
            tailf:cli-hide-in-submode;
            tailf:cli-optional-in-sequence;
            tailf:cli-full-command;
            when "../policy = 'ipsec-isakmp'" {
              tailf:xpath-root 3;
              tailf:dependency "../policy";
            }
            type string {
              tailf:info
                "WORD;;Name for this crypto profile";
            }
            tailf:non-strict-leafref {
              path "/ncs:devices/ncs:device/ncs:config/ios:crypto/isakmp/profile/name" {
                tailf:xpath-root 3;
              }
            }
          }
          container set {
            tailf:cli-break-sequence-commands;
            tailf:info
              "Set values for encryption/decryption";
            when "../policy != 'gdoi'" {
              tailf:xpath-root 3;
              tailf:dependency "../policy";
            }
            leaf transform-set {
              tailf:info
                "Specify list of transform sets in priority order";
              tailf:cli-full-command;
              type string {
                tailf:info
                  "WORD;; Proposal tag";
              }
              tailf:non-strict-leafref {
                path "/ncs:devices/ncs:device/ncs:config/ios:crypto/ipsec/transform-set/name" {
                  tailf:xpath-root 3;
                }
              }
            }
            leaf isakmp-profile {
              tailf:info
                "Specify isakmp Profile";
              type string {
                tailf:info
                  "WORD;;Name the isakmp profile";
              }
              tailf:non-strict-leafref {
                path "/ncs:devices/ncs:device/ncs:config/ios:crypto/isakmp/profile/name" {
                  tailf:xpath-root 3;
                }
              }
            }
            leaf peer {
              tailf:info
                " Allowed Encryption/Decryption peer";
              type union {
                type inet:ipv4-address {
                  tailf:info
                    "A.B.C.D;;IP address of peer";
                }
                type string {
                  tailf:info
                    "WORD;;Host name of the peer";
                }
                type inet:ipv6-address {
                  tailf:info
                    "X:X:X:X::X;;IPv6 address of peer";
                }
              }
            }
          }
          container gdoi-set {
            tailf:cli-break-sequence-commands;
            tailf:cli-drop-node-name;
            when "../policy = 'gdoi'" {
              tailf:xpath-root 3;
              tailf:dependency "../policy";
            }
            container set {
              tailf:info
                "Set values for encryption/decryption";
              leaf group {
                tailf:info
                  "Set the secure group parameters";
                type string {
                  tailf:info
                    "WORD;;Set the group name";
                }
                tailf:non-strict-leafref {
                  path "/ncs:devices/ncs:device/ncs:config/ios:crypto/gdoi/group/name" {
                    tailf:xpath-root 3;
                  }
                }
              }
            }
          }
          container match {
            tailf:info
              "Match values.";
            leaf address {
              tailf:info
                "Match address of packets to encrypt";
              type ext-ip-acl-type;
            }
          }
        }
      }
      container ssl {
        tailf:info
          "Configure Crypto SSL Options";
        list proposal {
          tailf:info
            "Define ssl Proposal";
          tailf:cli-mode-name "config-crypto-ssl-proposal";
          key "name";
          leaf name {
            type string {
              tailf:info
                "WORD;;Name of ssl Proposal";
            }
          }
          leaf-list protection {
            tailf:info
              "Specify the protection algorithms";
            tailf:cli-flat-list-syntax;
            type enumeration {
              enum "rsa-3des-ede-sha1" {
                tailf:info
                  "RSA, 3DES and SHA1";
              }
              enum "rsa-rc4128-md5" {
                tailf:info
                  "RSA, RC4 and MD5";
              }
              enum "rsa-aes128-sha1" {
                tailf:info
                  "RSA, AES128 and SHA1";
              }
              enum "rsa-aes256-sha1" {
                tailf:info
                  "RSA, AES256 and SHA1";
              }
            }
          }
        }
        container authorization {
          tailf:info
            "ssl authorization";
          list policy {
            tailf:info
              "Crypto SSL authorization policy";
            tailf:cli-mode-name "config-crypto-ssl-auth-policy";
            key "name";
            leaf name {
              type string {
                tailf:info
                  "WORD;;Name of the policy";
              }
            }
            leaf pool {
              tailf:info
                "Specify pool";
              type string {
                tailf:info
                  "WORD;;pool";
              }
            }
            container dns {
              tailf:info
                "Specify DNS Addresses";
              tailf:cli-compact-syntax;
              tailf:cli-sequence-commands {
                tailf:cli-reset-siblings;
              }
              leaf primary-server {
                tailf:cli-drop-node-name;
                type inet:ipv4-address {
                  tailf:info
                    "A.B.C.D;;Primary DNS IP address";
                }
              }
              leaf secondary-server {
                tailf:cli-drop-node-name;
                type inet:ipv4-address {
                  tailf:info
                    "A.B.C.D;;Secondary DNS IP address";
                }
              }
            }
            leaf banner {
              tailf:info
                "Specify banner";
              tailf:cli-multi-value;
              type string {
                tailf:info
                  "LINE;;banner string";
              }
            }
            leaf def-domain {
              tailf:info
                "Specify def_domain";
              type string {
                tailf:info
                  "WORD;;def_domain string";
              }
            }
          }
        }
        list policy {
          tailf:info
            "Define SSL policies";
          tailf:cli-mode-name "config-crypto-ssl-policy";
          key "name";
          leaf name {
            type string {
              tailf:info
                "WORD;;Name of ssl policy";
            }
          }
          container ssl {
            tailf:info
              "Specify ssl proposal";
            leaf proposal {
              tailf:info
                "Specify Proposal";
              type string {
                tailf:info
                  "WORD;;Specify the name of proposal to be attached";
              }
            }
          }
          container pki {
            tailf:info
              "Trustpoint options";
            tailf:cli-compact-syntax;
            tailf:cli-sequence-commands {
              tailf:cli-reset-all-siblings;
            }
            leaf trustpoint {
              tailf:info
                "Certificate Trustpoint to authenticate clients";
              tailf:cli-incomplete-command;
              type string {
                tailf:info
                  "WORD;;Trustpoint name";
              }
            }
            leaf sign {
              tailf:info
                "Sign";
              type empty;
            }
          }
          container ip {
            tailf:info
              "ip options";
            container address {
              tailf:info
                "ip address";
              tailf:cli-compact-syntax;
              tailf:cli-sequence-commands {
                tailf:cli-reset-all-siblings;
              }
              leaf local {
                tailf:info
                  "ip address local";
                type inet:ipv4-address {
                  tailf:info
                    "A.B.C.D;;IP address";
                }
              }
              leaf port {
                tailf:info
                  "port configuration";
                type union {
                  type uint16 {
                    tailf:info
                      "443;;Default secure port";
                    range "443";
                  }
                  type uint16 {
                    tailf:info
                      "<1025-65535>;;Port number";
                    range "1025..65535";
                  }
                }
              }
            }
          }
          leaf shutdown {
            tailf:info
              "shutdown";
            type empty;
          }
        }
        list profile {
          tailf:info
            "Define ssl Profiles";
          tailf:cli-mode-name "config-crypto-ssl-profile";
          key "name";
          leaf name {
            type string {
              tailf:info
                "WORD;;Name of ssl profile";
            }
          }
          container match {
            tailf:info
              "Specify the type to match";
            leaf policy {
              tailf:info
                "Specify Policy";
              tailf:cli-remove-before-change;
              type string {
                tailf:info
                  "WORD;;Specify the name of policy to be attached";
              }
              tailf:non-strict-leafref {
                path "/ncs:devices/ncs:device/ncs:config/ios:crypto/ssl/policy/name" {
                  tailf:xpath-root 3;
                }
              }
            }
            leaf url {
              tailf:info
                "Specify url";
              type string {
                tailf:info
                  "WORD;;gateway[:port]/domain (specify port if not 443)";
              }
            }
          }
          container aaa {
            tailf:info
              "aaa";
            container authentication {
              tailf:info
                "aaa authentication";
              leaf list {
                tailf:info
                  "aaa authentication list";
                type string {
                  tailf:info
                    "WORD;;Specify the list name";
                }
              }
            }
            container authorization {
              tailf:info
                "aaa authorization";
              container user {
                tailf:info
                  "AAA user authorization";
                tailf:cli-compact-syntax;
                tailf:cli-sequence-commands {
                  tailf:cli-reset-siblings;
                }
                leaf list {
                  tailf:info
                    "AAA method list";
                  type string {
                    tailf:info
                      "WORD;;AAA list name";
                  }
                }
                leaf aaa-username {
                  tailf:cli-drop-node-name;
                  type string {
                    tailf:info
                      "WORD;;AAA username";
                  }
                }
              }
            }
          }
          container authentication {
            tailf:info
              "Specify authentication mode";
            container remote {
              tailf:info
                "remote server";
              leaf user-credentials {
                tailf:info
                  "User credential mode";
                type empty;
              }
            }
          }
          leaf shutdown {
            tailf:info
              "shutdown";
            type empty;
          }
        }
      }
    }
    container buffers {
      tailf:ncs-device-type "cli-ned";
      tailf:display-when "not(../../ncs:module) or ../../ncs:module[ncs:name='tailf-ned-cisco-ios']";
      tailf:info
        "Adjust system buffer pool parameters";
      container huge {
        tailf:info
          "Huge buffers";
        leaf size {
          tailf:info
            "Size of huge buffers";
          type uint32 {
            tailf:info
              "<18024-65535>;;Size of huge buffers";
            range "18024..65535";
          }
        }
      }
    }
    container track {
      tailf:ncs-device-type "cli-ned";
      tailf:display-when "not(../../ncs:module) or ../../ncs:module[ncs:name='tailf-ned-cisco-ios']";
      tailf:info
        "Object tracking configuration commands";
      list track-object {
        tailf:cli-drop-node-name;
        tailf:cli-mode-name "config-track";
        tailf:cli-compact-syntax;
        tailf:cli-remove-before-change;
        key "object-number";
        leaf object-number {
          type uint16 {
            tailf:info
              "<1-1000>;;Tracked object";
            range "1..1000";
          }
        }
        container list {
          tailf:info
            "Group objects in a list";
          tailf:cli-flatten-container;
          tailf:cli-compact-syntax;
          tailf:cli-hide-in-submode;
          leaf boolean {
            tailf:info
              "List state based on a boolean calculation on objects";
            type enumeration {
              enum "and" {
                tailf:info
                  "Boolean AND operation on list";
              }
              enum "or" {
                tailf:info
                  "Boolean OR operation on list";
              }
            }
          }
        }
        container interface {
          tailf:info
            "Select an interface to track";
          tailf:cli-flatten-container;
          tailf:cli-compact-syntax;
          tailf:cli-sequence-commands;
          tailf:cli-hide-in-submode;
          uses interface-name-grouping;
          leaf line-protocol {
            tailf:info
              "Track interface line-protocol";
            tailf:cli-full-command;
            type empty;
          }
        }
        container ip {
          tailf:info
            "IP protocol";
          tailf:cli-flatten-container;
          tailf:cli-compact-syntax;
          tailf:cli-hide-in-submode;
          container route {
            tailf:info
              "IP route";
            tailf:cli-flatten-container;
            tailf:cli-compact-syntax;
            tailf:cli-sequence-commands;
            leaf prefix {
              tailf:cli-drop-node-name;
              type inet:ipv4-address {
                tailf:info
                  "A.B.C.D;;Prefix";
              }
            }
            leaf mask {
              tailf:cli-drop-node-name;
              type inet:ipv4-address {
                tailf:info
                  "A.B.C.D;;mask";
              }
            }
            leaf reachability {
              tailf:info
                "Route reachability state";
              tailf:cli-full-command;
              type empty;
            }
            container metric {
              tailf:info
                "Route metric";
              tailf:cli-flatten-container;
              leaf threshold {
                tailf:info
                  "Route metric threshold";
                tailf:cli-full-command;
                type empty;
              }
            }
          }
        }
        list object {
          tailf:info
            "Add a tracked object to list";
          tailf:cli-suppress-mode;
          tailf:cli-delete-when-empty;
          tailf:cli-compact-syntax;
          key "id";
          leaf id {
            type uint16 {
              tailf:info
                "<1-1000>;;Tracked object number";
              range "1..1000";
            }
          }
          leaf not {
            tailf:info
              "Negate the state of object";
            type empty;
          }
        }
        container delay {
          tailf:info
            "Tracking delay";
          tailf:cli-compact-syntax;
          leaf down {
            tailf:info
              "Delay down change notification";
            type uint8 {
              tailf:info
                "<0-180>;;Seconds to delay";
              range "0..180";
            }
          }
          leaf up {
            tailf:info
              "Delay up change notification";
            type uint8 {
              tailf:info
                "<0-180>;;Seconds to delay";
              range "0..180";
            }
          }
        }
      }
    }
    container csdb {
      tailf:ncs-device-type "cli-ned";
      tailf:display-when "not(../../ncs:module) or ../../ncs:module[ncs:name='tailf-ned-cisco-ios']";
      tailf:info
        "Common Session Database";
      container tcp {
        tailf:info
          "CSDB TCP protocol";
        leaf finwait-time {
          tailf:info
            "CSDB TCP protocol: FIN/RST timeout";
          type uint8 {
            tailf:info
              "<1-50>;;fin/rst timeout value (sec), default 5 sec";
            range "1..50";
          }
          default "5";
        }
        leaf idle-time {
          tailf:info
            "CSDB TCP protocol: idle timeout";
          type uint16 {
            tailf:info
              "<1-36000>;;idle timeout value (sec), default 3600 sec";
            range "1..36000";
          }
          default "3600";
        }
        container reassembly {
          tailf:info
            "CSDB Out-of-Order Module";
          leaf max-memory {
            tailf:info
              "CSDB Out-of-Order: Queue Memory";
            type uint32 {
              tailf:info
                "<1-102400>;;OoO memory (KB), default 1024 KB";
              range "1..102400";
            }
            default "1024";
          }
          leaf max-queue-length {
            tailf:info
              "CSDB Out-of-Order: Queue Length";
            type uint8 {
              tailf:info
                "<0-128>;;OoO queue length, default 16 packets, O means disable OoO";
              range "0..128";
            }
            default "16";
          }
        }
        leaf synwait-time {
          tailf:info
            "CSDB TCP protocol: 3-way handshake timeout";
          type uint16 {
            tailf:info
              "<0-300>;;syn timeout value (sec), default 30 sec";
            range "0..300";
          }
          default "30";
        }
      }
      container udp {
        tailf:info
          "CSDB UDP protocol";
        leaf idle-time {
          tailf:info
            "CSDB UDP Protocol: idle time";
          type uint16 {
            tailf:info
              "<1-1200>;;idle timeout value (sec), default 30 sec";
            range "1..1200";
          }
          default "30";
        }
      }
      container icmp {
        tailf:info
          "CSDB ICMP protocol";
        leaf idle-time {
          tailf:info
            "CSDB ICMP Protocol: idle time";
          type uint16 {
            tailf:info
              "<1-1200>;;idle timeout value (sec), default 10 sec";
            range "1..1200";
          }
          default "10";
        }
      }
      container session {
        tailf:info
          "CSDB Session Management";
        leaf max-session {
          tailf:info
            "CSDB Session: maximum session";
          type uint32 {
            tailf:info
              "<1-655350>;;session, default 65535";
            range "1..655350";
          }
          default "65535";
        }
      }
    }
    container ethernet {
      tailf:ncs-device-type "cli-ned";
      tailf:display-when "not(../../ncs:module) or ../../ncs:module[ncs:name='tailf-ned-cisco-ios']";
      tailf:info
        "Ethernet configuration";
      list evc {
        tailf:info
          "define an Ethernet virtual connection (EVC)";
        tailf:cli-mode-name "config-evc";
        tailf:cli-compact-syntax;
        tailf:cli-full-command;
        key "name";
        leaf name {
          type string {
            tailf:info
              "WORD;;EVC identifier of length <1-100>";
            length "1..100";
          }
        }
        container oam {
          tailf:info
            "OAM Protocol";
          container protocol {
            tailf:info
              "Protocol for EVC status reporting";
            container cfm {
              tailf:info
                "Protocol CFM";
              leaf domain {
                tailf:info
                  "Protocol CFM Domain";
                type string {
                  tailf:info
                    "WORD;;domain name";
                }
              }
            }
          }
        }
      }
      container cfm {
        tailf:info
          "Connectivity Fault Management";
        leaf ieee {
          tailf:info
            "CFM IEEE enable";
          tailf:cli-full-command;
          type empty;
        }
        leaf global {
          tailf:info
            "CFM global enable";
          tailf:cli-full-command;
          type empty;
        }
        container traceroute {
          tailf:info
            "CFM Traceroute";
          container cache {
            tailf:info
              "CFM Traceroute Cache";
            tailf:cli-display-separated;
            presence "true";
            leaf hold-time {
              tailf:info
                "Hold Time";
              type uint16 {
                tailf:info
                  "<1-65535>;;minutes (default 100)";
                range "1..65535";
              }
              default "100";
            }
          }
        }
        container mip {
          tailf:info
            "CFM MIP commands";
          list auto-create {
            tailf:info
              "CFM MIP auto creation";
            tailf:cli-suppress-mode;
            tailf:cli-delete-when-empty;
            tailf:cli-compact-syntax;
            tailf:cli-sequence-commands;
            key "evc";
            leaf evc {
              tailf:info
                "auto create for CFM over EVC";
              tailf:cli-expose-key-name;
              type string {
                tailf:info
                  "WORD;;EVC name";
              }
            }
            leaf level {
              tailf:info
                "Maintenance Level";
              tailf:cli-prefix-key;
              type uint8 {
                tailf:info
                  "<0-7>;;maintenance level number";
                range "0..7";
              }
            }
          }
        }
        list domain {
          tailf:info
            "Configure a domain";
          tailf:cli-mode-name "config-ecfm";
          tailf:cli-compact-syntax;
          tailf:cli-incomplete-command;
          key "name";
          leaf name {
            type string {
              tailf:info
                "WORD;;maintenance domain name";
            }
          }
          leaf level {
            tailf:info
              "Maintenance Level";
            tailf:cli-hide-in-submode;
            type uint8 {
              tailf:info
                "<0-7>;;maintenance level number";
            }
          }
          list service {
            tailf:info
              "Maintenance Association within Domain";
            tailf:cli-mode-name "config-ecfm-srv";
            tailf:cli-compact-syntax;
            tailf:cli-sequence-commands;
            tailf:cli-incomplete-command;
            key "csi-id";
            leaf csi-id {
              type string {
                tailf:info
                  "WORD;;service instance id - short MA name";
              }
            }
            leaf port {
              tailf:info
                "DOWN service direction with no vlan association";
              tailf:cli-hide-in-submode;
              tailf:cli-optional-in-sequence;
              tailf:cli-full-command;
              type empty;
            }
            leaf evc {
              tailf:info
                "Specify EVC";
              tailf:cli-hide-in-submode;
              type string {
                tailf:info
                  "WORD;;EVC name";
              }
            }
            leaf vlan {
              tailf:info
                "Specify vlan (range 1-4094)";
              tailf:cli-hide-in-submode;
              type uint16 {
                tailf:info
                  "<1-4094>;;between 1 and 4094";
                range "1..4094";
              }
            }
            leaf direction {
              tailf:info
                "service direction";
              tailf:cli-hide-in-submode;
              tailf:cli-full-command;
              type enumeration {
                enum "down" {
                  tailf:info
                    "direction towards the LAN";
                }
              }
            }
            container continuity-check {
              tailf:cli-break-sequence-commands;
              tailf:info
                "Enable Continuity Check for Maintenance Association";
              tailf:cli-display-separated;
              presence "true";
              leaf interval {
                tailf:info
                  "Interval Continuity Check messages transmitted";
                tailf:cli-full-command;
                type string {
                  tailf:info
                    "WORD;;interval string";
                }
              }
            }
            leaf sender-id {
              tailf:info
                "Include Sender ID TLV";
              tailf:cli-full-command;
              type enumeration {
                enum "chassis" {
                  tailf:info
                    "Send Chassis ID";
                }
                enum "none" {
                  tailf:info
                    "Info not included in Sender Id";
                }
              }
            }
            container ais {
              tailf:info
                "AIS Maintenance Condition";
              leaf period {
                tailf:info
                  "AIS Transmission period";
                type enumeration {
                  enum "1" {
                    tailf:info
                      "Seconds";
                  }
                  enum "60" {
                    tailf:info
                      "Seconds";
                  }
                }
                default "60";
              }
              leaf level {
                tailf:info
                  "Maintenance Level to send AIS";
                type uint8 {
                  tailf:info
                    "<0-7>;;Maintenance Level";
                  range "0..7";
                }
              }
            }
            container efd {
              tailf:info
                "Ethernet Fault Detection";
              container notify {
                tailf:info
                  "EFD Notification Registration";
                leaf g8032 {
                  tailf:info
                    "Notify G.8032 Controller of EFD events";
                  type empty;
                }
              }
            }
          }
        }
      }
      container ring {
        tailf:info
          "Ring";
        container g8032 {
          tailf:info
            "Specify the g.8032 ethernet ring";
          list profile {
            tailf:info
              "g.8032 ring profile configuration";
            tailf:cli-mode-name "config-erp-profile";
            key "profile-name";
            leaf profile-name {
              type string {
                tailf:info
                  "WORD;;ERP profile name string";
              }
            }
            container timer {
              tailf:info
                "g.8032 timer";
              leaf wtr {
                tailf:info
                  "Wait-to-Restore time";
                type uint8 {
                  tailf:info
                    "<1-12>;;minutes";
                  range "1..12";
                }
              }
              leaf guard {
                tailf:info
                  "Guard timer";
                type uint16 {
                  tailf:info
                    "<10-2000>;;milliseconds";
                  range "10..2000";
                }
              }
            }
          }
          list g8032-list {
            tailf:cli-drop-node-name;
            tailf:cli-mode-name "config-erp-ring";
            key "ring-name";
            leaf ring-name {
              tailf:cli-disallow-value "profile";
              type string {
                tailf:info
                  "WORD;;Name of the ethernet ring";
              }
            }
            container exclusion-list {
              tailf:info
                "Specifiy exclusion list not protected by ERP";
              leaf-list vlan-ids {
                tailf:info
                  "Assign list of VLANs to the exclusion list";
                tailf:cli-replace-all;
                tailf:cli-range-list-syntax;
                type uint16 {
                  tailf:info
                    "<1-4094>;;VLAN id";
                  range "1..4094";
                }
              }
            }
            container port0 {
              tailf:info
                "Port0 of the local node connected to G.8032 ring";
              tailf:cli-compact-syntax;
              tailf:cli-sequence-commands;
              tailf:cli-add-mode;
              tailf:cli-mode-name "config-erp-ring-port";
              tailf:cli-incomplete-command;
              container interface {
                tailf:info
                  "Assign port interface";
                tailf:cli-flatten-container;
                tailf:cli-compact-syntax;
                tailf:cli-hide-in-submode;
                uses interface-name-grouping;
              }
              container monitor {
                tailf:info
                  "Assign the Ethernet Service Instance to monitor g.8032 ring port";
                container service {
                  tailf:info
                    "Specify an Ethernet Service Instance";
                  leaf instance {
                    tailf:info
                      "Specify an Ethernet Service Instance";
                    type uint16 {
                      tailf:info
                        "Ethernet Service Instance ID";
                      range "1..8000";
                    }
                  }
                }
              }
            }
            choice port1-choice {
              container port1 {
                tailf:info
                  "Port1 of the local node connected to G.8032 ring";
                tailf:cli-compact-syntax;
                tailf:cli-sequence-commands;
                tailf:cli-add-mode;
                tailf:cli-mode-name "config-erp-ring-port";
                tailf:cli-incomplete-command;
                container interface {
                  tailf:info
                    "Assign port interface";
                  tailf:cli-flatten-container;
                  tailf:cli-compact-syntax;
                  tailf:cli-hide-in-submode;
                  uses interface-name-grouping;
                }
                container monitor {
                  tailf:info
                    "Assign the Ethernet Service Instance to monitor g.8032 ring port";
                  container service {
                    tailf:info
                      "Specify an Ethernet Service Instance";
                    leaf instance {
                      tailf:info
                        "Specify an Ethernet Service Instance";
                      type uint16 {
                        tailf:info
                          "Ethernet Service Instance ID";
                        range "1..8000";
                      }
                    }
                  }
                }
              }
              container port1-none {
                tailf:cli-drop-node-name;
                tailf:cli-full-command;
                container port1 {
                  leaf none {
                    tailf:info
                      "Assign port1 as none to enable g.8032 open-ring";
                    type empty;
                  }
                }
              }
            }
            list instance {
              tailf:info
                "Configure the g.8032 ethernet ring instance";
              tailf:cli-mode-name "config-erp-inst";
              tailf:cli-full-command;
              key "instance-id";
              leaf instance-id {
                type uint8 {
                  tailf:info
                    "<1-2>;;Instance number";
                  range "1..2";
                }
              }
              leaf profile {
                tailf:info
                  "Specify associated g.8032 ethernet ring profile";
                type string {
                  tailf:info
                    "WORD;;Ethernet ring profile name";
                }
              }
              container rpl {
                tailf:info
                  "Specify RPL owner, neighbor or next-neighbor";
                tailf:cli-compact-syntax;
                tailf:cli-sequence-commands;
                leaf port {
                  tailf:cli-drop-node-name;
                  tailf:cli-incomplete-command;
                  type enumeration {
                    enum "port0" {
                      tailf:info
                        "Assign port0 as RPL owner, neighbor or next-neighbor";
                    }
                    enum "port1" {
                      tailf:info
                        "Assign port1 as RPL owner, neighbor or next-neighbor";
                    }
                  }
                }
                leaf type {
                  tailf:cli-drop-node-name;
                  type enumeration {
                    enum "neighbor" {
                      tailf:info
                        "RPL neighbor";
                    }
                    enum "next-neighbor" {
                      tailf:info
                        "RPL next neighbor";
                    }
                    enum "owner" {
                      tailf:info
                        "RPL owner";
                    }
                  }
                }
              }
              container inclusion-list {
                tailf:info
                  "Specify inclusion list protected by ERP";
                leaf-list vlan-ids {
                  tailf:info
                    "Associates a set of VLAN IDs with the current instance";
                  tailf:cli-range-list-syntax;
                  type uint16 {
                    tailf:info
                      "WORD;;List of VLAN IDs in the form a-b,c,d,e-f,g";
                    range "1..4094";
                  }
                }
              }
              container aps-channel {
                tailf:info
                  "Configure g.8032 instance aps-channel";
                tailf:cli-add-mode;
                tailf:cli-mode-name "config-erp-inst-aps";
                container port0 {
                  tailf:info
                    "Configure g.8032 aps-channel info associated to port0";
                  container service {
                    tailf:info
                      "Specify an Ethernet Service Instance";
                    leaf instance {
                      tailf:info
                        "Specify an Ethernet Service Instance";
                      type uint16 {
                        tailf:info
                          "<1-8000>;;Ethernet Service Instance ID";
                        range "1..8000";
                      }
                    }
                  }
                }
                container port1 {
                  tailf:info
                    "Configure g.8032 aps-channel info associated to port1";
                  choice port1-choice {
                    container service {
                      tailf:info
                        "Specify an Ethernet Service Instance";
                      leaf instance {
                        tailf:info
                          "Specify an Ethernet Service Instance";
                        type uint16 {
                          tailf:info
                            "<1-8000>;;Ethernet Service Instance ID";
                          range "1..8000";
                        }
                      }
                    }
                    leaf none {
                      tailf:info
                        "Specify port1 APS channel as none";
                      type empty;
                    }
                  }
                }
              }
            }
          }
        }
      }
      list tcn-propagation {
        tailf:info
          "Enable TCN propagation";
        tailf:cli-suppress-mode;
        tailf:cli-delete-when-empty;
        key "source to";
        leaf source {
          type enumeration {
            enum "g8032" {
              tailf:info
                "g.8032 ethernet ring";
            }
            enum "rep" {
              tailf:info
                "REP ethernet ring";
            }
          }
        }
        leaf to {
          tailf:info
            "propagate TCN to";
          tailf:cli-expose-key-name;
          type enumeration {
            enum "g8032" {
              tailf:info
                "g.8032 ethernet ring";
            }
            enum "rep" {
              tailf:info
                "REP ethernet ring";
            }
          }
        }
      }
    }
    container interface {
      tailf:ncs-device-type "cli-ned";
      tailf:display-when "not(../../ncs:module) or ../../ncs:module[ncs:name='tailf-ned-cisco-ios']";
      tailf:info
        "Configure interfaces";
      tailf:cli-diff-dependency "/ios:vrf/definition" {
        tailf:xpath-root 3;
      }
      tailf:cli-explicit-exit;
      list Null {
        tailf:cli-allow-join-with-key {
          tailf:cli-display-joined;
        }
        tailf:cli-mode-name "config-if";
        tailf:cli-suppress-key-abbreviation;
        tailf:cli-full-command;
        key "name";
        leaf name {
          type uint8 {
            tailf:info
              "<0-0>;;Null interface number";
            range "0";
          }
        }
        container ip {
          tailf:info
            "Interface Internet Protocol config commands";
          leaf unreachables {
            tailf:info
              "Enable sending ICMP Unreachable messages";
            tailf:cli-boolean-no;
            tailf:cli-full-command;
            type boolean;
            default "true";
          }
        }
        container ipv6 {
          tailf:info
            "IPv6 interface subcommands";
          leaf unreachables {
            tailf:info
              "Enable sending of ICMP Unreachable messages";
            tailf:cli-boolean-no;
            tailf:cli-full-command;
            type boolean;
            default "true";
          }
        }
      }
      list Loopback {
        tailf:info
          "Loopback interface";
        tailf:cli-allow-join-with-key {
          tailf:cli-display-joined;
        }
        tailf:cli-mode-name "config-if";
        tailf:cli-suppress-key-abbreviation;
        tailf:cli-full-command;
        key "name";
        leaf name {
          type string {
            tailf:info
              "<0-2147483647>;;Loopback interface number";
            pattern '([0-9\.])+';
          }
        }
        uses interface-common-pre-grouping;
        uses interface-common-grouping;
      }
      list Embedded-Service-Engine {
        tailf:info
          "cisco embedded service engine module";
        tailf:cli-allow-join-with-key {
          tailf:cli-display-joined;
        }
        tailf:cli-mode-name "config-if";
        tailf:cli-suppress-key-abbreviation;
        key "name";
        leaf name {
          type string {
            pattern '[0-9]+.*';
            tailf:info
              "<0-2>/<0-0>;;Embedded-Service-Engine interface number";
          }
        }
        uses interface-common-pre-grouping;
        uses interface-common-grouping;
      }
      list Tunnel {
        tailf:info
          "Tunnel interface";
        tailf:cli-allow-join-with-key {
          tailf:cli-display-joined;
        }
        tailf:cli-mode-name "config-if";
        tailf:cli-suppress-key-abbreviation;
        key "name";
        leaf name {
          type uint32 {
            tailf:info
              "<0-2147483647>;;Tunnel interface number";
          }
        }
        uses interface-common-pre-grouping;
        uses interface-common-grouping;
        container qos {
          tailf:info
            "Quality of Service related commands";
          leaf pre-classify {
            tailf:info
              "Enable QOS classification before packets are tunnel encapsulated";
            type empty;
          }
        }
        uses interface-tunnel-grouping;
      }
      list Port-channel {
        tailf:info
          "Ethernet Channel of interfaces";
        tailf:cli-allow-join-with-key {
          tailf:cli-display-joined;
        }
        tailf:cli-mode-name "config-if";
        tailf:cli-suppress-key-abbreviation;
        tailf:callpoint interface-port-channel-hook {
          tailf:set-hook node;
        }
        key "name";
        leaf name {
          type uint32 {
            tailf:info
              "<1-512>;;Port-channel interface number";
            range "1..512";
          }
        }
        uses interface-common-pre-grouping;
        uses interface-ethernet-pre-grouping;
        uses interface-switch-grouping;
        uses interface-ethernet-grouping;
        uses interface-common-grouping {
          refine "l2protocol-tunnel" {
            tailf:cli-diff-dependency "../switchport" {
              tailf:xpath-root 3;
            }
          }
        }
        container lacp {
          tailf:info
            "LACP Port Channel interface subcommands";
          leaf fast-switchover {
            tailf:info
              "Enable LACP fast switchover on this port channel";
            type empty;
          }
          leaf max-bundle {
            tailf:info
              "LACP maximum number of ports to bundle in this port channel";
            type uint8 {
              tailf:info
                "<1-8>;;Max number of ports to bundle in this Port Channel";
              range "1..8";
            }
          }
        }
        container mlacp {
          tailf:info
            "mLACP Port Channel interface subcommands";
          container interchassis {
            tailf:info
              "mLACP Interchassis commands";
            leaf group {
              tailf:info
                "Interchassis Group";
              type uint32 {
                tailf:info
                  "<1-4294967295>;;Group ID";
              }
            }
          }
        }
      }
      container Port-channel-subinterface {
        tailf:cli-drop-node-name;
        list Port-channel {
          tailf:info
            "Ethernet Channel of interfaces";
          tailf:cli-allow-join-with-key {
            tailf:cli-display-joined;
          }
          tailf:cli-mode-name "config-subif";
          tailf:cli-suppress-key-abbreviation;
          key "name";
          leaf name {
            type string {
              pattern '[0-9]+\.[0-9]+';
            }
          }
          uses interface-common-pre-grouping;
          uses interface-ethernet-pre-grouping;
          uses interface-switch-grouping;
          uses interface-ethernet-grouping;
          uses interface-common-grouping {
            refine "l2protocol-tunnel" {
              tailf:cli-diff-dependency "../switchport" {
                tailf:xpath-root 3;
              }
            }
          }
        }
      }
      list Multilink {
        tailf:info
          "Multilink-group interface";
        tailf:cli-allow-join-with-key {
          tailf:cli-display-joined;
        }
        tailf:cli-mode-name "config-if";
        tailf:cli-suppress-key-abbreviation;
        key "name";
        leaf name {
          type uint16 {
            tailf:info
              "<1-65535>;;Multilink interface number";
            range "1..65535";
          }
        }
        uses interface-common-pre-grouping;
        uses interface-common-grouping;
        uses interface-pointtopoint-grouping;
      }
      list MFR {
        tailf:info
          "Multilink Frame Relay bundle interface";
        tailf:cli-allow-join-with-key {
          tailf:cli-display-joined;
        }
        tailf:cli-mode-name "config-if";
        tailf:cli-suppress-key-abbreviation;
        key "name";
        leaf name {
          type uint32 {
            tailf:info
              "<0-2147483647>;;MFR interface number";
          }
        }
        uses interface-common-pre-grouping;
        uses interface-common-grouping;
      }
      container MFR-subinterface {
        tailf:cli-drop-node-name;
        list MFR {
          tailf:info
            "Multilink Frame Relay bundle interface";
          tailf:cli-allow-join-with-key {
            tailf:cli-display-joined;
          }
          tailf:cli-mode-name "config-subif";
          tailf:cli-suppress-key-abbreviation;
          tailf:cli-incomplete-command;
          key "name";
          leaf name {
            type string {
              pattern '[0-9]+\.[0-9]+';
            }
          }
          leaf type {
            tailf:cli-drop-node-name;
            tailf:cli-hide-in-submode;
            type enumeration {
              enum "multipoint" {
                tailf:info
                  "Treat as a multipoint link";
              }
              enum "point-to-point" {
                tailf:info
                  "Treat as a point-to-point link";
              }
            }
          }
          uses interface-common-pre-grouping;
          uses interface-common-grouping;
        }
      }
      list BRI {
        tailf:info
          "ISDN Basic Rate Interface";
        tailf:cli-allow-join-with-key {
          tailf:cli-display-joined;
        }
        tailf:cli-mode-name "config-if";
        tailf:cli-suppress-key-abbreviation;
        key "name";
        leaf name {
          type uint16 {
            tailf:info
              "<0-0>;;BRI interface number";
            range "0";
          }
        }
        uses interface-common-pre-grouping;
        uses interface-common-grouping;
      }
      list Ethernet {
        tailf:info
          "Ethernet";
        tailf:cli-allow-join-with-key {
          tailf:cli-display-joined;
        }
        tailf:cli-mode-name "config-if";
        tailf:cli-suppress-key-abbreviation;
        key "name";
        leaf name {
          type string {
            tailf:info
              "<slot>/<port>;;Ethernet interface number";
            pattern '[0-9]+.*';
          }
        }
        uses interface-common-pre-grouping;
        uses interface-ethernet-pre-grouping;
        uses interface-switch-grouping;
        uses interface-ethernet-grouping;
        uses interface-common-grouping {
          refine "l2protocol-tunnel" {
            tailf:cli-diff-dependency "../switchport" {
              tailf:xpath-root 3;
            }
          }
        }
        uses interface-zone-member-grouping;
      }
      list FastEthernet {
        tailf:info
          "FastEthernet IEEE 802.3";
        tailf:cli-allow-join-with-key {
          tailf:cli-display-joined;
        }
        tailf:cli-mode-name "config-if";
        tailf:cli-suppress-key-abbreviation;
        key "name";
        leaf name {
          type string {
            pattern '[0-9]+.*';
            tailf:info
              "<0-66>/<0-128>;;FastEthernet interface number";
          }
        }
        uses interface-common-pre-grouping;
        uses interface-ethernet-pre-grouping;
        uses interface-switch-grouping;
        uses interface-ethernet-grouping;
        uses interface-common-grouping {
          refine "l2protocol-tunnel" {
            tailf:cli-diff-dependency "../switchport" {
              tailf:xpath-root 3;
            }
          }
        }
        uses interface-zone-member-grouping;
      }
      list GigabitEthernet {
        tailf:info
          "GigabitEthernet IEEE 802.3z";
        tailf:cli-allow-join-with-key {
          tailf:cli-display-joined;
        }
        tailf:cli-mode-name "config-if";
        tailf:cli-suppress-key-abbreviation;
        key "name";
        leaf name {
          type string {
            pattern '[0-9]+.*';
            tailf:info
              "<0-66>/<0-128>;;GigabitEthernet interface number";
          }
        }
        uses interface-common-pre-grouping;
        uses interface-ethernet-pre-grouping;
        uses interface-switch-grouping;
        uses interface-ethernet-grouping;
        uses interface-common-grouping {
          refine "l2protocol-tunnel" {
            tailf:cli-diff-dependency "../switchport" {
              tailf:xpath-root 3;
            }
          }
        }
        uses interface-zone-member-grouping;
      }
      list TenGigabitEthernet {
        tailf:info
          "Ten Gigabit Ethernet";
        tailf:cli-allow-join-with-key {
          tailf:cli-display-joined;
        }
        tailf:cli-mode-name "config-if";
        tailf:cli-suppress-key-abbreviation;
        key "name";
        leaf name {
          type string {
            pattern '[0-9]+.*';
            tailf:info
              "<0-66>/<0-128>;;TenGigabitEthernet interface number";
          }
        }
        uses interface-common-pre-grouping;
        uses interface-ethernet-pre-grouping;
        uses interface-switch-grouping;
        uses interface-ethernet-grouping;
        uses interface-common-grouping {
          refine "l2protocol-tunnel" {
            tailf:cli-diff-dependency "../switchport" {
              tailf:xpath-root 3;
            }
          }
        }
        uses interface-zone-member-grouping;
      }
      list BDI {
        tailf:info
          "Bridge-Domain interface";
        tailf:cli-allow-join-with-key {
          tailf:cli-display-joined;
        }
        tailf:cli-mode-name "config-if";
        tailf:cli-suppress-key-abbreviation;
        key "name";
        leaf name {
          type uint16 {
            tailf:info
              "<1-4095>;;BDI interface number";
            range "1..4095";
          }
        }
        uses interface-common-pre-grouping;
        uses interface-switch-grouping;
        uses interface-common-grouping;
      }
      list Cable {
        tailf:info
          "CMTS interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container downstream {
          tailf:info
            "Associate a Cable/Modular-Cable/Integrated-Cable interface with this CGD host";
          tailf:cli-compact-syntax;
          tailf:cli-sequence-commands;
          leaf Modular-Cable {
            tailf:info
              "Modular cable";
            tailf:cli-incomplete-command;
            type string {
              tailf:info
                "<slot>/<card>/<port>;;Enter slot/subslot/bay";
            }
          }
          leaf rf-channel {
            tailf:info
              "RF channel";
            type string {
              tailf:info
                "<grouplist>;;List of port numbers and number ranges";
            }
          }
        }
        container cable {
          container tftp-enforce {
            tailf:info
              "Only allow modems to register if they attempt tftp first";
            tailf:cli-delete-when-empty;
            presence "true";
            leaf mark-only {
              tailf:info
                "Allow registration but mark violating modems with # symbol";
              type empty;
            }
          }
          leaf ip-init {
            tailf:info
              "IP Initialization Parameters";
            type enumeration {
              enum "apm" {
                tailf:info
                  "Alternate Provisioning mode";
              }
              enum "dual-stack" {
                tailf:info
                  "Dual-stack Provisioning mode";
              }
              enum "ipv4" {
                tailf:info
                  "IPv4 Provisioning mode";
              }
              enum "ipv6" {
                tailf:info
                  "IPv6 Provisioning mode";
              }
            }
            default "ipv4";
          }
          container mtc-mode {
            tailf:info
              "Enable/Disable Multiple Transmit Channel Mode";
            presence "true";
          }
          list rcc-template {
            tailf:info
              "Bind RCC template to interface";
            tailf:cli-suppress-mode;
            tailf:cli-delete-when-empty;
            key "index";
            leaf index {
              type uint8 {
                tailf:info
                  "<1-255>;;cable rcc-template id";
                range "1..255";
              }
            }
          }
          container rcp-control {
            tailf:info
              "Receive Channel Profile control";
            leaf verbose {
              tailf:info
                "Enable verbose reporting";
              type empty;
            }
          }
          container shared-secret {
            tailf:info
              "Shared Secret String";
            tailf:cli-compact-syntax;
            tailf:cli-sequence-commands {
              tailf:cli-reset-siblings;
            }
            uses password-07-grouping;
          }
          container dynamic-secret {
            tailf:info
              "Enable dynamic secret for CM config files";
            tailf:cli-compact-syntax;
            tailf:cli-sequence-commands {
              tailf:cli-reset-siblings;
            }
            choice dynamic-secret-choice {
              case reject {
                leaf reject {
                  tailf:info
                    "Reject registration request from modems violating dynamic secret";
                  type empty;
                }
              }
              case mark {
                leaf mark {
                  tailf:info
                    "Mark modems violating dynamic secret";
                  type empty;
                }
              }
              case lock {
                leaf lock {
                  tailf:info
                    "Lock modems violating dynamic secret";
                  type empty;
                }
                leaf lock-qos {
                  tailf:cli-drop-node-name;
                  tailf:cli-optional-in-sequence;
                  type uint16 {
                    tailf:info
                      "<1-1023>;;Profile used to lock";
                    range "1..1023";
                  }
                }
              }
            }
            leaf nocrypt {
              tailf:info
                "Do not encrypt modem config file name";
              type empty;
            }
          }
          container enable-trap {
            tailf:info
              "Enable an SNMP cable trap";
            leaf cmonoff-notification {
              tailf:info
                "Cable Modem Online/Offline notification";
              type empty;
            }
            leaf cmonoff-interval {
              tailf:info
                "Interval in Seconds";
              type uint32 {
                tailf:info
                  "<0-86400>;;Interval in secs";
                range "0..86400";
              }
            }
          }
          leaf packet-cache {
            tailf:cli-boolean-no;
            tailf:cli-full-command;
            type boolean;
            default "true";
          }
          leaf default-phy-burst {
            tailf:info
              "Max phy burst if max long data grant is 0";
            type uint16 {
              tailf:info
                "<0-4096>;;Maximal number of bytes allowed in a burst";
              range "0..4096";
            }
          }
          container insertion-interval {
            tailf:info
              "Period between initial ranging opportunities - msec";
            choice interval-choice {
              leaf fixed-intrvl {
                tailf:cli-drop-node-name;
                type uint16 {
                  tailf:info
                    "<100-2000>;;Fixed period between initial ranging slots - msec";
                }
              }
              container automatic {
                tailf:info
                  "Use automatic adjustment algorithm for initial ranging period";
                tailf:cli-compact-syntax;
                tailf:cli-sequence-commands {
                  tailf:cli-reset-siblings;
                }
                leaf min-intrvl {
                  tailf:cli-drop-node-name;
                  type uint8 {
                    tailf:info
                      "<20-120>;;Lower bound on period between initial ranging slots - msecs";
                    range "20..120";
                  }
                  default "60";
                }
                leaf max-intrvl {
                  tailf:cli-drop-node-name;
                  type uint16 {
                    tailf:info
                      "<240-1800>;;Upper bound on period between initial ranging slots - msecs";
                    range "240..1800";
                  }
                  default "480";
                }
              }
            }
          }
          container map-advance {
            tailf:info
              "Set algorithm for the look-ahead time in MAPs";
            choice map-advance-choice {
              leaf static {
                type uint16 {
                  tailf:info
                    "<100-20000>;;max map advance - usecs";
                  range "100..20000";
                }
              }
              container dynamic {
                tailf:info
                  "Automatically tune the value to the current propagation delay";
                tailf:cli-compact-syntax;
                tailf:cli-sequence-commands;
                leaf safety {
                  tailf:cli-drop-node-name;
                  tailf:cli-incomplete-command;
                  type uint16 {
                    tailf:info
                      "<300-1500>;;Safety factor - usecs";
                    range "300..1500";
                  }
                }
                leaf max-delay {
                  tailf:cli-drop-node-name;
                  type uint16 {
                    tailf:info
                      "<100-20000>;;max map advance - usecs";
                    range "100..20000";
                  }
                }
              }
            }
          }
          leaf sync-interval {
            tailf:info
              "Interval between CMTS transmission of successive SYNC";
            type uint16 {
              tailf:info
                "<1-200>;;sync interval - msec";
              range "1..200";
            }
          }
          leaf bundle {
            tailf:info
              "Bundle number for bundling of cable interfaces";
            type uint8 {
              tailf:info
                "<1-255>;;Bundle number";
              range "1..255";
            }
          }
          container downstream {
            tailf:info
              "Downstream parameter configuration";
            container dsg {
              tailf:info
                "Downstream DSG settings";
              leaf timer {
                tailf:info
                  "DSG Timer Setting";
                type uint16 {
                  tailf:info
                    "<1-65535>;;DSG timer index.";
                }
              }
              list tg {
                tailf:info
                  "DSG Tunnel group";
                tailf:cli-suppress-mode;
                tailf:cli-delete-when-empty;
                key "tgid";
                leaf tgid {
                  type uint16 {
                    tailf:info
                      "<1-65535>;;DSG Tunnel Group ID";
                    range "1..65535";
                  }
                }
                list channel {
                  tailf:info
                    "DSG Channel";
                  tailf:cli-suppress-mode;
                  tailf:cli-delete-when-empty;
                  key "channel-id";
                  leaf channel-id {
                    type uint16 {
                      tailf:info
                        "<1-65535>;;DSG Channel ID";
                      range "1..65535";
                    }
                  }
                }
              }
            }
          }
          container upstream {
            tailf:info
              "Upstream port configuration";
            leaf balance-scheduling {
              tailf:info
                "upstream channel balance scheduling on one mac-domain";
              type empty;
            }
            leaf max-ports {
              tailf:info
                "Maximum number of upstream ports for this interface";
              type uint8 {
                tailf:info
                  "<0-8>;;Number of upstreams";
                range "0..8";
              }
            }
            list bonding-group {
              tailf:info
                "Configure upstream bonding group";
              tailf:cli-mode-name "config-upstream-bonding";
              key "id";
              leaf id {
                type uint16 {
                  tailf:info
                    "<1-65535>;;bonding group id";
                  range "1..65535";
                }
              }
              list upstream {
                tailf:info
                  "Add an upstream to this bonding group.";
                tailf:cli-suppress-mode;
                tailf:cli-delete-when-empty;
                key "number";
                leaf number {
                  type uint8 {
                    tailf:info
                      "<0-4>;;upstream to add";
                  }
                }
              }
              leaf attributes {
                tailf:info
                  "Configure attributes for this bonding group.";
                type string {
                  tailf:info
                    "<0-FFFFFFFF>;;UBG Attribute Value in hex";
                }
              }
            }
            container resiliency {
              tailf:info
                "upstream resiliency configuration";
              leaf on-failure {
                tailf:info
                  "ranging retries exceeded error handling";
                type enumeration {
                  enum "disable-channel" {
                    tailf:info
                      "disable channel";
                  }
                  enum "extended-ranging" {
                    tailf:info
                      "continue to range";
                  }
                  enum "reset-modem" {
                    tailf:info
                      "take modem offline";
                  }
                }
                default "extended-ranging";
              }
            }
            list cable-upstream-list {
              tailf:cli-drop-node-name;
              tailf:cli-suppress-mode;
              tailf:cli-delete-when-empty;
              key "port";
              leaf port {
                type uint8 {
                  tailf:info
                    "<0-4>;;Port number";
                }
              }
              leaf connector {
                tailf:info
                  "Physical upstream connector";
                type uint8 {
                  tailf:info
                    "<0-19>;;Physical port number";
                  range "0..19";
                }
              }
              leaf frequency {
                tailf:info
                  "Frequency";
                type uint32 {
                  tailf:info
                    "<5000000-85000000>;;Upstream Frequency in Hz";
                  range "5000000..85000000";
                }
              }
              container channel-width {
                tailf:info
                  "Channel width in HZ";
                tailf:cli-compact-syntax;
                tailf:cli-sequence-commands {
                  tailf:cli-reset-siblings;
                }
                leaf first-choice-width {
                  tailf:cli-drop-node-name;
                  type uint32 {
                    tailf:info
                      "Channel width Hz";
                  }
                }
                leaf last-choice-width {
                  tailf:cli-drop-node-name;
                  type uint32 {
                    tailf:info
                      "Channel width Hz";
                  }
                }
              }
              leaf description {
                tailf:info
                  "Upstream name/description";
                tailf:cli-multi-value;
                tailf:cli-full-command;
                type string {
                  tailf:info
                    "LINE;;Up to 80 characters describing this US port";
                }
              }
              leaf docsis-mode {
                tailf:info
                  "Upstream channel DOCSIS mode";
                type enumeration {
                  enum "atdma" {
                    tailf:info
                      "DOCSIS 2.0 ATDMA-only channel";
                  }
                  enum "scdma" {
                    tailf:info
                      "DOCSIS 2.0 SCDMA-only channel";
                  }
                  enum "tdma" {
                    tailf:info
                      "DOCSIS 1.x-only channel";
                  }
                  enum "tdma-atdma" {
                    tailf:info
                      "DOCSIS 1.x and DOCSIS 2.0 mixed channel";
                  }
                }
              }
              leaf minislot-size {
                tailf:info
                  "Minislot size";
                type uint8 {
                  tailf:info
                    "Minislot size in time ticks";
                  range "2|4|8|16|32|64|128";
                }
              }
              container power-adjust {
                tailf:info
                  "Power adjustment";
                leaf continue {
                  tailf:info
                    "Minimum power adjustment which set CONTINUE ranging status";
                  type uint8 {
                    tailf:info
                      "<2-15>;;Power level in dB";
                    range "2..15";
                  }
                }
              }
              container range-backoff {
                tailf:info
                  "Change Range Backoff Value";
                tailf:cli-compact-syntax;
                tailf:cli-sequence-commands;
                choice range-backoff-choice {
                  case automatic {
                    leaf automatic {
                      tailf:info
                        "Automatic Change Range Backoff Value";
                      type empty;
                    }
                  }
                  case numeric {
                    leaf start {
                      tailf:cli-drop-node-name;
                      tailf:cli-incomplete-command;
                      type uint8 {
                        tailf:info
                          "<0-15>;;rangebackoff-start";
                      }
                    }
                    leaf end {
                      tailf:cli-drop-node-name;
                      type uint8 {
                        tailf:info
                          "<0-15>;;rangebackoff-end";
                      }
                    }
                  }
                }
              }
              container modulation-profile {
                tailf:info
                  "Modulation Profile Number";
                tailf:cli-compact-syntax;
                tailf:cli-sequence-commands {
                  tailf:cli-reset-siblings;
                }
                leaf primary-profile-number {
                  tailf:cli-drop-node-name;
                  type uint8 {
                    tailf:info
                      "VALUE;;modulation number";
                  }
                }
                leaf secondary-profile-number {
                  tailf:cli-drop-node-name;
                  type uint8 {
                    tailf:info
                      "VALUE;;secondary modulation number";
                  }
                }
                leaf tertiary-profile-number {
                  tailf:cli-drop-node-name;
                  type uint8 {
                    tailf:info
                      "VALUE;;tertiary modulation number";
                  }
                }
              }
              leaf rate-limit {
                tailf:info
                  "Enable DOCSIS rate limiting on current upstream";
                tailf:cli-show-no;
                type empty;
              }
              leaf equalization-coefficient {
                tailf:info
                  "Enable equalization coefficient";
                type empty;
              }
              container rate-adapt {
                tailf:info
                  "Configure upstream rate-adapt";
                presence "true";
              }
              leaf attribute-mask {
                tailf:info
                  "Upstream Channel Provisioned Attribute Mask";
                type string {
                  tailf:info
                    "<0-FFFFFFFF>;;Attribute mask in hex";
                }
              }
              leaf chan-class-id {
                tailf:info
                  "Channel Class ID";
                type string {
                  tailf:info
                    "<0-FFFFFFFF>;;Class ID Extension";
                }
              }
              leaf shutdown {
                tailf:info
                  "Shutdown upstream port";
                tailf:cli-show-no;
                type empty;
              }
            }
          }
          container sid-cluster-group {
            tailf:info
              "SID Cluster Group parameters for Upstream Channel Bonding";
            leaf dynamic {
              tailf:info
                "Dynamic algorithm";
              type empty;
            }
            leaf num-of-cluster {
              tailf:info
                "Number of SID Cluster Group";
              type uint8 {
                tailf:info
                  "<1-8>;;1, 2, 3, 4, 5, 6, 7, 8";
                range "1..8";
              }
            }
            leaf req-multiplier {
              tailf:info
                "Request Multiplier";
              type uint8 {
                tailf:info
                  "<1-16>;;1, 2, 4, 8, 16";
                range "1|2|4|8|16";
              }
            }
          }
          container sid-cluster-switching {
            tailf:info
              "SID Cluster Switching parameters for Upstream Channel Bonding";
            leaf max-request {
              tailf:info
                "Max request";
              type uint8 {
                tailf:info
                  "<0-255>;;0 to 255";
              }
            }
            leaf max-time {
              tailf:info
                "Max time";
              type uint16 {
                tailf:info
                  "<0-65535>;;0 to 65535";
              }
            }
          }
          container divert-rate-limit {
            tailf:info
              "Set divert-rate-limit parameters";
            tailf:cli-compact-syntax;
            tailf:cli-sequence-commands {
              tailf:cli-reset-siblings;
            }
            leaf rate {
              tailf:info
                "rate in packets/sec";
              tailf:cli-incomplete-command;
              type uint16 {
                tailf:info
                  "<1-65535>;;rate in packets/second";
              }
            }
            leaf limit {
              tailf:info
                "limit in packets";
              type uint16 {
                tailf:info
                  "<4-4194>;;limit in packets";
              }
            }
          }
          container privacy {
            tailf:info
              "Cable Privacy";
            leaf mandatory {
              tailf:info
                "force privacy be mandatory";
              type empty;
            }
            leaf bpi-plus-policy {
              tailf:info
                "Privacy requires BPI+";
              type enumeration {
                enum "capable-enforcement" {
                  tailf:info
                    "BPI+ required for all capable modems with BPI+ enabled (policy 1)";
                }
                enum "d11-enabled-enforcement" {
                  tailf:info
                    "BPI+ required for all D1.1 and later modems with BPI+ enabled (policy 2)";
                }
                enum "d11-enforcement" {
                  tailf:info
                    "BPI+ required for all D1.1 and later modems (policy 3)";
                }
                enum "total-enforcement" {
                  tailf:info
                    "BPI+ required for all modems (policy 4)";
                }
              }
            }
          }
        }
      }
      list Modular-Cable {
        tailf:info
          "Modular Cable interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "MC Cable interface subcommands";
          leaf bundle {
            tailf:info
              "Bundle number for bundling of MC cable interfaces";
            type uint8 {
              tailf:info
                "<1-255>;;Bundle number";
              range "1..255";
            }
          }
          container rf-bandwidth-percent {
            tailf:cli-compact-syntax;
            tailf:cli-sequence-commands {
              tailf:cli-reset-siblings;
            }
            leaf percent-value {
              tailf:cli-drop-node-name;
              type uint8 {
                tailf:info
                  "<1-96>;;% bandwidth";
                range "1..96";
              }
            }
            container remaining {
              tailf:info
                "ratio of the remaining bandwidth";
              tailf:cli-flatten-container;
              tailf:cli-compact-syntax;
              leaf ratio {
                tailf:info
                  "ratio for sharing excess bandwidth";
                type uint8 {
                  tailf:info
                    "<1-100>;;Ratio";
                }
              }
            }
          }
        }
      }
      list Wideband-Cable {
        tailf:info
          "Wideband CMTS interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "Cable interface subcommands";
          leaf bundle {
            tailf:info
              "Bundle number for bundling of cable interfaces";
            tailf:cli-remove-before-change;
            type uint8 {
              tailf:info
                "<1-255>;;Bundle number";
              range "1..255";
            }
          }
          container rf-channel {
            tailf:info
              "RF channel associated with this Wideband interface";
            list rf-channel-list {
              tailf:cli-drop-node-name;
              tailf:cli-suppress-mode;
              tailf:cli-delete-when-empty;
              tailf:cli-compact-syntax;
              tailf:cli-sequence-commands {
                tailf:cli-reset-siblings;
              }
              key "rf-port";
              leaf rf-port {
                type uint8 {
                  tailf:info
                    "<0-23>;;RF channel number";
                  range "0..23";
                }
              }
              leaf bandwidth-percent {
                tailf:info
                  "% bandwidth of RF channel reserved for this Wideband interface";
                type uint8 {
                  tailf:info
                    "<1-100>;;% bandwidth";
                  range "1..100";
                }
              }
              container remaining {
                tailf:info
                  "ratio of the remaining bandwidth";
                tailf:cli-flatten-container;
                tailf:cli-compact-syntax;
                leaf ratio {
                  tailf:info
                    "ratio for sharing excess bandwidth";
                  type uint8 {
                    tailf:info
                      "<1-100>;;Ratio";
                  }
                }
              }
            }
          }
        }
      }
      list Bundle {
        tailf:info
          "Virtual Bundle";
        tailf:cli-allow-join-with-key {
          tailf:cli-display-joined;
        }
        tailf:cli-mode-name "config-if";
        tailf:cli-suppress-key-abbreviation;
        key "name";
        leaf name {
          type uint8 {
            tailf:info
              "<1-255>;;Bundle interface number";
            range "1..255";
          }
        }
        uses interface-common-pre-grouping;
        uses interface-common-grouping;
        container cable {
          tailf:info
            "Cable interface subcommands";
          leaf nd {
            tailf:info
              "Enable IPv6 ND gleaning";
            tailf:cli-boolean-no;
            tailf:cli-full-command;
            type boolean;
            default "true";
          }
          container arp {
            tailf:info
              "Enable arp request";
            container filter {
              tailf:info
                "Filter arp packets";
              container request-send {
                tailf:info
                  "send x arp requests every y seconds or none";
                tailf:cli-show-no;
                tailf:cli-compact-syntax;
                tailf:cli-sequence-commands;
                tailf:cli-delete-when-empty;
                tailf:cli-incomplete-command;
                presence "true";
                leaf number {
                  tailf:cli-drop-node-name;
                  tailf:cli-incomplete-command;
                  type uint8 {
                    tailf:info
                      "<0-20>;;number of arp request packets";
                  }
                }
                leaf window-size {
                  tailf:cli-drop-node-name;
                  type uint8 {
                    tailf:info
                      "<1-5>;;size of time window in seconds";
                  }
                }
              }
              container reply-accept {
                tailf:info
                  "accept x arp replies every y seconds or none";
                tailf:cli-show-no;
                tailf:cli-compact-syntax;
                tailf:cli-sequence-commands;
                tailf:cli-delete-when-empty;
                tailf:cli-incomplete-command;
                presence "true";
                leaf number {
                  tailf:cli-drop-node-name;
                  tailf:cli-incomplete-command;
                  type uint8 {
                    tailf:info
                      "<0-20>;;number of arp reply packets";
                  }
                }
                leaf window-size {
                  tailf:cli-drop-node-name;
                  type uint8 {
                    tailf:info
                      "<1-5>;;size of time window in seconds";
                  }
                }
              }
            }
          }
          container conf {
            tailf:cli-drop-node-name;
            leaf arp {
              tailf:cli-boolean-no;
              tailf:cli-full-command;
              type boolean;
              default "true";
            }
          }
          container ipv6 {
            tailf:info
              "IPv6 related configuration";
            container source-verify {
              tailf:info
                "Enable verification of source of IPv6 packets";
              container dhcp {
                tailf:info
                  "Verify address with the DHCPv6 server";
                presence "true";
                leaf server {
                  tailf:info
                    "Specify the lease query server where the DHCPv6 lease queries should be sent";
                  type inet:ipv6-address {
                    tailf:info
                      "X:X:X:X::X;;IPv6 Address of the lease query server";
                  }
                }
              }
              container leasequery-filter {
                tailf:info
                  "Filter x IPv6 lease query requests every y seconds or none";
                container upstream {
                  tailf:info
                    "IPv6 Lease query for upstream pkts";
                  tailf:cli-compact-syntax;
                  tailf:cli-sequence-commands;
                  leaf threshold {
                    tailf:cli-drop-node-name;
                    tailf:cli-incomplete-command;
                    type uint8 {
                      tailf:info
                        "<0-20>;;Number of IPv6 lease queries per sid";
                      range "0..20";
                    }
                  }
                  leaf interval {
                    tailf:cli-drop-node-name;
                    type uint8 {
                      tailf:info
                        "<1-5>;;size of time window in seconds for IPv6";
                      range "1..5";
                    }
                  }
                }
              }
              leaf leasetimer {
                tailf:info
                  "Specify the IPv6 lease timer value";
                type uint8 {
                  tailf:info
                    "<1-240>;;IPv6 Time in minutes";
                  range "1..240";
                }
              }
            }
          }
          container source-verify {
            tailf:info
              "Enable verification of source of packets";
            container dhcp {
              tailf:info
                "Verify address with the DHCPv4 server";
              presence "true";
              leaf server {
                tailf:info
                  "Specify the lease query server where the DHCPv4 lease queries should be sent";
                type inet:ipv4-address {
                  tailf:info
                    "A.B.C.D;;IPv4 Address of the lease query server";
                }
              }
            }
            container leasequery-filter {
              tailf:info
                "Filter x IPv4 lease query requests every y seconds or none";
              container upstream {
                tailf:info
                  "Lease query for upstream pkts";
                tailf:cli-compact-syntax;
                tailf:cli-sequence-commands;
                leaf threshold {
                  tailf:cli-drop-node-name;
                  tailf:cli-incomplete-command;
                  type uint8 {
                    tailf:info
                      "<0-20>;;Number of IPv4 lease queries per sid";
                    range "0..20";
                  }
                }
                leaf interval {
                  tailf:cli-drop-node-name;
                  type uint8 {
                    tailf:info
                      "<1-5>;;size of time window in seconds for IPv4";
                    range "1..5";
                  }
                }
              }
            }
            leaf leasetimer {
              tailf:info
                "Specify the IPv4 lease timer value";
              type uint8 {
                tailf:info
                  "<1-240>;;IPv4 Time in minutes";
                range "1..240";
              }
            }
          }
          container dhcp-parse {
            tailf:info
              "DHCP parse option";
            leaf option-43 {
              tailf:info
                "DHCP parse option 43";
              type empty;
            }
            leaf option-60 {
              tailf:info
                "DHCP parse option 60";
              type empty;
            }
          }
          container dhcp-giaddr {
            tailf:info
              "Control of giaddr in relayed DHCP requests";
            choice dhcp-giaddr-choice {
              container policy {
                tailf:info
                  "Use primary address for CMs, secondary addresses for hosts";
                presence "true";
              }
              leaf primary {
                tailf:info
                  "Use primary address for all devices";
                type empty;
              }
            }
          }
          list helper-address {
            tailf:info
              "Specify a destination address for UDP broadcasts";
            tailf:cli-suppress-mode;
            tailf:cli-delete-when-empty;
            key "IP-address";
            leaf IP-address {
              type inet:ipv4-address {
                tailf:info
                  "A.B.C.D;;IP destination address";
              }
            }
          }
        }
      }
      list Cellular {
        tailf:info
          "Cellular WAN interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        uses interface-pointtopoint-grouping;
      }
      list Vlan {
        tailf:info
          "Catalyst Vlans";
        tailf:cli-allow-join-with-key {
          tailf:cli-display-joined;
        }
        key "name";
        leaf name {
          type uint16 {
            tailf:info
              "<1-4094>;;Vlan interface number";
            range "1..4094";
          }
        }
        uses interface-common-pre-grouping;
        uses interface-ethernet-pre-grouping;
        uses interface-switch-grouping;
        uses interface-ethernet-grouping;
        uses interface-common-grouping;
        uses interface-zone-member-grouping;
      }
      list Async {
        tailf:info
          "Async interface";
        tailf:cli-allow-join-with-key {
          tailf:cli-display-joined;
        }
        key "name";
        leaf name {
          type uint16 {
            tailf:info
              "<1-9>;;Async interface number";
          }
        }
        uses interface-common-pre-grouping;
        uses interface-common-grouping;
      }
      list Group-Async {
        tailf:info
          "Async Group interface";
        tailf:cli-allow-join-with-key {
          tailf:cli-display-joined;
        }
        key "name";
        leaf name {
          type uint16 {
            tailf:info
              "<0-64>;;Group-Async interface number";
            range "0..64";
          }
        }
        leaf physical-layer {
          tailf:info
            "Configure sync or async physical layer on serial interface";
          type enumeration {
            enum "async" {
              tailf:info
                "Configure asynchronous physical layer on serial interface";
            }
            enum "sync" {
              tailf:info
                "Configure synchronous physical layer on serial interface";
            }
          }
        }
        uses interface-common-pre-grouping;
        uses interface-common-grouping;
      }
      list Serial {
        tailf:info
          "Serial interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        uses interface-pointtopoint-grouping;
      }
      container Serial-subinterface {
        tailf:cli-drop-node-name;
        list Serial {
          tailf:info
            "Serial interface";
          tailf:cli-allow-join-with-key {
            tailf:cli-display-joined;
          }
          tailf:cli-mode-name "config-subif";
          tailf:cli-suppress-key-abbreviation;
          key "name";
          leaf name {
            type string {
              pattern '[0-9]+.*\..*';
            }
          }
          leaf type {
            tailf:cli-drop-node-name;
            tailf:cli-hide-in-submode;
            type enumeration {
              enum "multipoint" {
                tailf:info
                  "Treat as a multipoint link";
              }
              enum "point-to-point" {
                tailf:info
                  "Treat as a point-to-point link";
              }
            }
          }
          uses interface-common-pre-grouping;
          uses interface-common-grouping;
          uses interface-pointtopoint-grouping;
        }
      }
      list Virtual-Template {
        tailf:info
          "Virtual Template interface";
        tailf:cli-allow-join-with-key {
          tailf:cli-display-joined;
        }
        tailf:cli-mode-name "config-if";
        tailf:cli-suppress-key-abbreviation;
        tailf:cli-explicit-exit;
        key "name";
        leaf name {
          type uint16 {
            tailf:info
              "<1-4095>;;Virtual-Template interface number";
            range "1..4095";
          }
        }
        leaf type {
          tailf:info
            "type of the virtual-template";
          tailf:cli-hide-in-submode;
          type enumeration {
            enum "ethernet" {
              tailf:info
                "Set VT type as ethernet";
            }
            enum "serial" {
              tailf:info
                "Set VT type as serial";
            }
            enum "tunnel" {
              tailf:info
                "Set VT type as tunnel";
            }
          }
        }
        uses interface-common-pre-grouping;
        uses interface-ethernet-pre-grouping;
        uses interface-switch-grouping;
        uses interface-ethernet-grouping;
        uses interface-common-grouping;
        uses interface-zone-member-grouping;
        uses interface-pointtopoint-grouping;
        uses interface-tunnel-grouping;
      }
      list pseudowire {
        tailf:info
          "Pseudowire Interface";
        tailf:cli-allow-join-with-key {
          tailf:cli-display-joined;
        }
        tailf:cli-mode-name "config-if";
        tailf:cli-suppress-key-abbreviation;
        key "name";
        leaf name {
          type uint32 {
            tailf:info
              "<1-231072>;;pseudowire interface number";
            range "1..231072";
          }
        }
        leaf description {
          tailf:info
            "Interface specific description";
          tailf:cli-multi-value;
          tailf:cli-full-command;
          type string {
            length "0..200";
          }
        }
        leaf encapsulation {
          tailf:info
            "Data encapsulation method";
          type enumeration {
            enum "l2tpv3" {
              tailf:info
                "Use L2TPv3 encapsulation";
            }
            enum "mpls" {
              tailf:info
                "Use MPLS encapsulation";
            }
          }
        }
        container neighbor {
          tailf:info
            "Neighbor options";
          tailf:cli-compact-syntax;
          tailf:cli-sequence-commands;
          leaf address {
            tailf:cli-drop-node-name;
            tailf:cli-incomplete-command;
            type inet:ipv4-address {
              tailf:info
                "A.B.C.D;;IP address of the peer PE";
            }
          }
          leaf vcid {
            tailf:cli-drop-node-name;
            type uint32 {
              tailf:info
                "<1-4294967295>;;Peer VC ID value";
              range "1..4294967295";
            }
          }
        }
        container label {
          tailf:info
            "MPLS local and remote pseudowire static labels";
          tailf:cli-compact-syntax;
          tailf:cli-sequence-commands;
          leaf local-pseudowire-label {
            tailf:cli-drop-node-name;
            tailf:cli-incomplete-command;
            type uint32 {
              tailf:info
                "<0-4294967295>;;Local pseudowire label";
            }
          }
          leaf remote-pseudowire-label {
            tailf:cli-drop-node-name;
            type uint32 {
              tailf:info
                "<16-1048575>;;Remote pseudowire label";
              range "16..1048575";
            }
          }
        }
        container signaling {
          tailf:info
            "Signaling options";
          leaf protocol {
            tailf:info
              "Signaling protocol to use";
            type enumeration {
              enum "ldp" {
                tailf:info
                  "Use LDP signaling";
              }
              enum "none" {
                tailf:info
                  "No signaling, use manually configured pseudowires";
              }
            }
          }
        }
        leaf control-word {
          tailf:info
            "Control-word options";
          type enumeration {
            enum "exclude" {
              tailf:info
                "Exclude control-word in pseudowire packets";
            }
            enum "include" {
              tailf:info
                "Include control-word in pseudowire packets";
            }
          }
        }
        leaf shutdown {
          tailf:info
            "Shutdown the selected interface";
          tailf:cli-full-command;
          tailf:cli-show-no;
          type empty;
        }
        container service-policy {
          tailf:info
            "Configure Service Policy";
          uses service-policy-grouping;
        }
      }
      list LISP {
        tailf:info
          "Locator/ID Separation Protocol Virtual Interface";
        tailf:cli-allow-join-with-key {
          tailf:cli-display-joined;
        }
        tailf:cli-mode-name "config-if";
        tailf:cli-suppress-key-abbreviation;
        key "name";
        leaf name {
          type uint16 {
            tailf:info
              "<0-1999>;;LISP interface number";
            range "0..1999";
          }
        }
        uses interface-common-pre-grouping;
        uses interface-common-grouping;
      }
      container LISP-subinterface {
        tailf:cli-drop-node-name;
        list LISP {
          tailf:cli-allow-join-with-key {
            tailf:cli-display-joined;
          }
          tailf:cli-mode-name "config-subif";
          tailf:cli-suppress-key-abbreviation;
          key "name";
          leaf name {
            type string {
              pattern '[0-9]+\.[0-9]+';
            }
          }
          uses interface-common-pre-grouping;
          uses interface-common-grouping;
        }
      }
    }
    container access-list {
      tailf:ncs-device-type "cli-ned";
      tailf:display-when "not(../../ncs:module) or ../../ncs:module[ncs:name='tailf-ned-cisco-ios']";
      tailf:info
        "Add an access list entry";
      tailf:cli-compact-syntax;
      tailf:cli-incomplete-command;
      tailf:cli-incomplete-no;
      list access-list-standard-range {
        tailf:cli-drop-node-name;
        tailf:cli-suppress-mode;
        tailf:cli-delete-when-empty;
        tailf:cli-compact-syntax;
        tailf:cli-incomplete-command;
        key "listnumber";
        leaf listnumber {
          tailf:cli-incomplete-command;
          tailf:cli-incomplete-no;
          tailf:cli-suppress-range;
          type uint16 {
            tailf:info
              "<1-99>;;IP standard access list";
            range "1..99";
          }
        }
        list std-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-multi-word-key;
            type string {
              tailf:info
                "deny;;Specify packets to reject
                 permit;;Specify packets to forwards
                 remark;;Access list entry comment";
              pattern '(permit.*)|(deny.*)|(remark.*)';
            }
          }
        }
      }
      list access-list-extended-range {
        tailf:cli-drop-node-name;
        tailf:cli-suppress-mode;
        tailf:cli-delete-when-empty;
        tailf:cli-compact-syntax;
        tailf:cli-incomplete-command;
        key "listnumber";
        leaf listnumber {
          tailf:cli-incomplete-command;
          tailf:cli-incomplete-no;
          tailf:cli-suppress-range;
          type uint16 {
            tailf:info
              "<100-199>;;IP extended access list";
            range "100..199";
          }
        }
        list ext-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-multi-word-key;
            type string {
              tailf:info
                "deny;;Specify packets to rejectdynamic;;Specify DYNAMIC list of PERMITs or DENYspermit;;Specify packets to forwardsremark;;Access list entry comment";
              pattern '(permit.*)|(deny.*)|(remark.*)';
            }
          }
        }
      }
      list access-list-standard-expanded {
        tailf:cli-drop-node-name;
        tailf:cli-suppress-mode;
        tailf:cli-delete-when-empty;
        tailf:cli-compact-syntax;
        tailf:cli-incomplete-command;
        key "listnumber";
        leaf listnumber {
          tailf:cli-incomplete-command;
          tailf:cli-incomplete-no;
          tailf:cli-suppress-range;
          type uint16 {
            tailf:info
              "<1300-1999>;;IP standard access list (expanded range)";
            range "1300..1999";
          }
        }
        list ext-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-multi-word-key;
            type string {
              tailf:info
                "deny;;Specify packets to rejectdynamic;;Specify DYNAMIC list of PERMITs or DENYspermit;;Specify packets to forwardsremark;;Access list entry comment";
              pattern '(permit.*)|(deny.*)|(remark.*)';
            }
          }
        }
      }
      list access-list-extended-expanded {
        tailf:cli-drop-node-name;
        tailf:cli-suppress-mode;
        tailf:cli-delete-when-empty;
        tailf:cli-compact-syntax;
        tailf:cli-incomplete-command;
        key "listnumber";
        leaf listnumber {
          tailf:cli-incomplete-command;
          tailf:cli-incomplete-no;
          tailf:cli-suppress-range;
          type uint16 {
            tailf:info
              "<2000-2699>;;IP extended access list (expanded range)";
            range "2000..2699";
          }
        }
        list ext-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-multi-word-key;
            type string {
              tailf:info
                "deny;;Specify packets to rejectdynamic;;Specify DYNAMIC list of PERMITs or DENYspermit;;Specify packets to forwardsremark;;Access list entry comment";
              pattern '(permit.*)|(deny.*)|(remark.*)|(dynamic.*)';
            }
          }
        }
      }
    }
    list virtual-service {
      tailf:ncs-device-type "cli-ned";
      tailf:display-when "not(../ncs:module) or ../ncs:module[ncs:name='tailf-ned-cisco-ios']";
      tailf:info
        "Configure virtual service";
      tailf:cli-mode-name "config-virt-serv";
      key "name";
      leaf name {
        type string {
          tailf:info
            "WORD;;Virtual service name (up to 63 characters)";
        }
      }
      leaf description {
        tailf:info
          "Virtual service description";
        tailf:cli-multi-value;
        type string {
          tailf:info
            "LINE;;Description of this virtual service (up to 191 characters)";
          length "0..191";
        }
      }
    }
    list route-map {
      tailf:ncs-device-type "cli-ned";
      tailf:display-when "not(../ncs:module) or ../ncs:module[ncs:name='tailf-ned-cisco-ios']";
      tailf:info
        "Route map tag";
      tailf:cli-mode-name "config-route-map";
      tailf:cli-compact-syntax;
      tailf:cli-full-command;
      key "name sequence";
      leaf name {
        type string {
          tailf:info
            "WORD;;Route map tag";
        }
      }
      leaf sequence {
        tailf:cli-drop-node-name;
        type uint16 {
          tailf:info
            "<0-65535>;;Sequence to insert to/delete from existing route-map entry";
          range "0..65535";
        }
      }
      leaf operation {
        tailf:cli-drop-node-name;
        tailf:cli-prefix-key {
          tailf:cli-before-key 2;
        }
        type enumeration {
          enum "deny" {
            tailf:code-name "op_deny";
            tailf:info
              "Route map denies set operations";
          }
          enum "permit" {
            tailf:code-name "op_internet";
            tailf:info
              "Route map permits set operations";
          }
        }
      }
      leaf description {
        tailf:info
          "Route-map comment";
        tailf:cli-multi-value;
        type string {
          tailf:info
            "LINE;;Comment up to 100 characters";
          length "0..100";
        }
      }
      container match {
        tailf:info
          "Match values from routing table";
        container as-path {
          tailf:info
            "Match BGP AS path list";
          leaf-list path-list-number {
            tailf:cli-drop-node-name;
            tailf:cli-flat-list-syntax;
            type uint16 {
              tailf:info
                "<1-500>;;AS path access-list";
            }
          }
        }
        container ip {
          tailf:info
            "IP specific information";
          container address {
            tailf:info
              "Match address of route or match packet";
            choice address-choice {
              leaf access-list {
                tailf:cli-drop-node-name;
                type exp-ip-acl-type;
              }
              leaf prefix-list {
                tailf:info
                  "Match entries of prefix-lists";
                type string;
                tailf:non-strict-leafref {
                  path "/ncs:devices/ncs:device/ncs:config/ios:ip/prefix-list/prefixes/name" {
                    tailf:xpath-root 3;
                  }
                }
              }
            }
          }
        }
        container ipv6 {
          tailf:info
            "IPv6 specific information";
          container address {
            tailf:info
              "Match address of route";
            choice address-choice {
              leaf access-list {
                tailf:cli-drop-node-name;
                type string {
                  tailf:info
                    "WORD;;IPv6 access-list name";
                  pattern '[a-zA-Z].*';
                }
              }
              leaf prefix-list {
                tailf:info
                  "IPv6 prefix-list";
                type string;
                tailf:non-strict-leafref {
                  path "/ncs:devices/ncs:device/ncs:config/ios:ipv6/prefix-list/prefixes/name" {
                    tailf:xpath-root 3;
                  }
                }
              }
            }
          }
        }
        container community {
          tailf:info
            "Match BGP community list";
          leaf-list name {
            tailf:info
              "Named Access List";
            tailf:cli-drop-node-name;
            tailf:cli-flat-list-syntax;
            type string {
              tailf:info
                "<1-99>       Community-list number (standard)
                 <100-500>       Community-list number (expanded)
                 WORD            Community-list name
                 exact-match     Do exact matching of communities
                ";
            }
          }
        }
      }
      container set {
        tailf:info
          "Set values in destination routing protocol";
        container as-path {
          tailf:info
            "Prepend string for a BGP AS-path attribute";
          container prepend {
            tailf:info
              "Prepend to the as-path";
            container as-container {
              tailf:cli-drop-node-name;
              leaf as-number {
                tailf:info
                  "<1-65535>;;AS number";
                tailf:cli-drop-node-name;
                tailf:cli-multi-value;
                type string {
                  tailf:info
                    "<1-65535>;;AS number";
                }
              }
            }
            container last-as-cont {
              tailf:cli-drop-node-name;
              leaf last-as {
                type uint16 {
                  tailf:info
                    "<1..10>;;number of last-AS prepends";
                  range "1..10";
                }
              }
            }
          }
          container tag {
            tailf:info
              "Set the tag as an AS-path attribute";
            tailf:cli-full-command;
            presence "tag";
          }
        }
        container community {
          tailf:info
            "BGP community attribute";
          tailf:cli-compact-syntax;
          tailf:cli-sequence-commands {
            tailf:cli-reset-siblings;
          }
          leaf-list community-number {
            tailf:cli-drop-node-name;
            tailf:cli-flat-list-syntax;
            ordered-by user;
            type union {
              type uint32 {
                tailf:info
                  "<1-4294967295>;;community number";
                range "1..4294967295";
              }
              type string {
                tailf:info
                  "aa:nn;;community number in aa:nn format";
                pattern '[0-9]+:[0-9]+';
              }
              type enumeration {
                enum "additive" {
                  tailf:info
                    "Add to the existing community";
                }
                enum "internet" {
                  tailf:info
                    "Internet (well-known community)";
                }
                enum "local-AS" {
                  tailf:info
                    "Do not send outside local AS (well-known community)";
                }
                enum "no-advertise" {
                  tailf:info
                    "Do not advertise to any peer (well-known community)";
                }
                enum "no-export" {
                  tailf:info
                    "Do not export to next AS (well-known community)";
                }
                enum "none" {
                  tailf:info
                    "No community attribute";
                }
              }
            }
          }
        }
        container comm-list {
          tailf:info
            "set BGP community list (for deletion)";
          tailf:cli-compact-syntax;
          tailf:cli-sequence-commands {
            tailf:cli-reset-siblings;
          }
          leaf name {
            tailf:cli-drop-node-name;
            type union {
              type uint16 {
                tailf:info
                  "<1-99>;;Community-list number (standard)";
                range "1..99";
              }
              type uint16 {
                tailf:info
                  "<100-500>;;Community-list number (expanded)";
                range "100..500";
              }
              type string {
                tailf:info
                  "WORD;;Community-list name";
              }
            }
          }
          leaf delete {
            tailf:info
              "Delete matching communities";
            tailf:cli-full-command;
            type empty;
          }
        }
        container extcommunity {
          tailf:info
            "BGP extended community attribute";
          leaf-list rt {
            tailf:info
              "Route Target extended community";
            tailf:cli-flat-list-syntax;
            type asn-ip-type {
              tailf:info
                "ASN:nn or IP-address:nn;;VPN extended community";
            }
          }
        }
        container ip {
          tailf:info
            "IP specific information";
          container next-hop {
            tailf:info
              "Next hop address";
            choice next-hop-choice {
              leaf-list address {
                tailf:cli-drop-node-name;
                tailf:cli-flat-list-syntax;
                type inet:ipv4-address {
                  tailf:info
                    "A.B.C.D;;IP address of next hop";
                }
              }
              container dynamic {
                tailf:info
                  "application dynamically sets next hop";
                leaf dhcp {
                  tailf:info
                    "DHCP learned next hop";
                  type empty;
                }
              }
              container encapsulate {
                tailf:info
                  "Encapsulation profile for VPN nexthop";
                leaf l3vpn {
                  tailf:info
                    "L3VPN";
                  type string {
                    tailf:info
                      "WORD;;Encapsulation profile name";
                  }
                }
              }
              leaf peer-address {
                tailf:info
                  "Use peer address (for BGP only)";
                type empty;
              }
            }
          }
          container df {
            tailf:info
              "Set DF bit";
            tailf:cli-delete-when-empty;
            presence "true";
            leaf bit {
              tailf:cli-drop-node-name;
              type uint8 {
                tailf:info
                  "<0-1>;;DF bit";
                range "0..1";
              }
            }
          }
        }
        container ipv6 {
          tailf:info
            "IPv6 specific information";
          container next-hop {
            tailf:info
              "IPv6 Next hop";
            choice next-hop-choice {
              leaf-list address {
                tailf:cli-drop-node-name;
                tailf:cli-flat-list-syntax;
                type inet:ipv6-address {
                  tailf:info
                    "X:X:X:X::X;;Next hop address";
                }
              }
              leaf peer-address {
                tailf:info
                  "Use peer address (for BGP only)";
                tailf:cli-full-command;
                type empty;
              }
            }
          }
        }
        container local-preference {
          tailf:info
            "BGP local preference path attribute";
          tailf:cli-delete-when-empty;
          presence "true";
          leaf value {
            tailf:cli-drop-node-name;
            type uint32 {
              tailf:info
                "<0-4294967295>;;Preference value";
            }
          }
        }
        leaf metric {
          tailf:info
            "Metric value for destination routing protocol";
          type string {
            tailf:info
              "+/-<metric>;;Add or subtract metric
               <0-4294967295>;;Metric value or Bandwidth in Kbits per second";
            pattern '[+-]?[0-9].*';
          }
        }
        leaf metric-type {
          tailf:info
            "Type of metric for destination routing protocol";
          type enumeration {
            enum "external" {
              tailf:info
                "IS-IS external metric";
            }
            enum "internal" {
              tailf:info
                "IS-IS internal metric or Use IGP metric as the MED for BGP";
            }
            enum "type-1" {
              tailf:info
                "OSPF external type 1 metric";
            }
            enum "type-2" {
              tailf:info
                "OSPF external type 2 metric";
            }
          }
        }
        leaf weight {
          tailf:info
            "BGP weight for routing table";
          type uint32 {
            tailf:info
              "<0-65535>;;Weight value";
            range "0..65535";
          }
        }
        container origin {
          tailf:info
            "BGP origin code";
          choice origin-choice {
            leaf origin-value {
              tailf:cli-drop-node-name;
              type enumeration {
                enum "igp" {
                  tailf:info
                    "local IGP";
                }
                enum "incomplete" {
                  tailf:info
                    "unknown heritage";
                }
              }
            }
            leaf egp {
              tailf:info
                "remote EGP";
              type uint32 {
                tailf:info
                  "<0-65535>;;remote AS";
                range "0..65535";
              }
            }
          }
        }
        leaf vrf {
          tailf:info
            "Define VRF name";
          tailf:cli-diff-dependency "/ios:ip/vrf" {
            tailf:xpath-root 3;
          }
          tailf:cli-diff-dependency "/ios:vrf/definition" {
            tailf:xpath-root 3;
          }
          type string {
            tailf:info
              "WORD;;VPN Routing/Forwarding instance name";
          }
        }
        leaf tag {
          tailf:info
            "Tag value for destination routing protocol";
          type uint32 {
            tailf:info
              "<0-4294967295>;;Tag value";
          }
        }
      }
      leaf continue {
        tailf:info
          "Continue on a different entry within the route-map";
        type uint16 {
          tailf:info
            "<0-65535>;;Route-map entry sequence number";
        }
      }
    }
    container dialer {
      tailf:ncs-device-type "cli-ned";
      tailf:display-when "not(../../ncs:module) or ../../ncs:module[ncs:name='tailf-ned-cisco-ios']";
      tailf:info
        "Dialer commands";
      list watch-list {
        tailf:info
          "Dialer watch list";
        tailf:cli-suppress-mode;
        tailf:cli-delete-when-empty;
        key "id";
        leaf id {
          type uint16 {
            tailf:info
              "<1-255>;;Dialer watch group number";
            range "1..255";
          }
        }
        container ip {
          tailf:info
            "IP";
          tailf:cli-compact-syntax;
          tailf:cli-sequence-commands {
            tailf:cli-reset-all-siblings;
          }
          leaf address {
            tailf:cli-drop-node-name;
            type inet:ipv4-address {
              tailf:info
                "A.B.C.D;;Protocol specific address";
            }
          }
          leaf mask {
            tailf:cli-drop-node-name;
            tailf:cli-no-value-on-delete;
            type inet:ipv4-address {
              tailf:info
                "A.B.C.D;;IP subnet mask";
            }
          }
        }
        container delay {
          tailf:info
            "Dialer watch delay";
          container route-check {
            tailf:info
              "Interval for checking watched route";
            leaf initial {
              tailf:info
                "Delay for initial check of watched route after boot";
              type uint32 {
                tailf:info
                  "<1-2147483>;;Delay time in seconds";
              }
            }
          }
          leaf connect {
            tailf:info
              "Interval before dialing the secondary route";
            type uint32 {
              tailf:info
                "<1-2147483>;;Delay time in seconds";
              range "1..2147483";
            }
          }
          leaf disconnect {
            tailf:info
              "Interval before disconnecting the secondary route";
            type uint32 {
              tailf:info
                "<1-2147483>;;Delay time in seconds";
              range "1..2147483";
            }
          }
        }
      }
    }
    list dialer-list {
      tailf:ncs-device-type "cli-ned";
      tailf:display-when "not(../ncs:module) or ../ncs:module[ncs:name='tailf-ned-cisco-ios']";
      tailf:info
        "Create a dialer list entry";
      tailf:cli-suppress-mode;
      tailf:cli-delete-when-empty;
      tailf:cli-compact-syntax;
      key "id";
      leaf id {
        type uint16 {
          tailf:info
            "<1-128>;;Dialer group number";
        }
      }
      container protocol {
        tailf:info
          "Permit or Deny based on protocols";
        leaf ip {
          tailf:info
            "IP";
          type enumeration {
            enum "deny" {
              tailf:info
                "Deny specified protocol";
            }
            enum "list" {
              tailf:info
                "Add access list to dialer list";
            }
            enum "permit" {
              tailf:info
                "Permit specified protocol";
            }
          }
        }
      }
    }
    container authentication {
      tailf:ncs-device-type "cli-ned";
      tailf:display-when "not(../../ncs:module) or ../../ncs:module[ncs:name='tailf-ned-cisco-ios']";
      container mac-move {
        leaf permit {
          type empty;
        }
      }
    }
    container banner {
      tailf:ncs-device-type "cli-ned";
      tailf:display-when "not(../../ncs:module) or ../../ncs:module[ncs:name='tailf-ned-cisco-ios']";
      tailf:info
        "Define a login banner";
      leaf exec {
        tailf:info
          "Set EXEC process creation banner. ";
        type string {
          tailf:info
            "LINE;;Quoted string. Use \\r\\n for newline. delimeter ^ is added automatically.";
        }
      }
      leaf login {
        tailf:info
          "Set login banner.";
        type string {
          tailf:info
            "LINE;;Quoted string. Use \\r\\n for newline. delimeter ^ is added automatically.";
        }
      }
      leaf prompt-timeout {
        tailf:info
          "Set Message for login authentication timeout.";
        type string {
          tailf:info
            "LINE;;Quoted string. Use \\r\\n for newline. delimeter ^ is added automatically.";
        }
      }
      leaf motd {
        tailf:info
          "Set Message of the Day banner.";
        type string {
          tailf:info
            "LINE;;Quoted string. Use \\r\\n for newline. delimeter ^ is added automatically.";
        }
      }
    }
    list pseudowire-class {
      tailf:ncs-device-type "cli-ned";
      tailf:display-when "not(../ncs:module) or ../ncs:module[ncs:name='tailf-ned-cisco-ios']";
      tailf:info
        "Pseudowire-class configuration";
      tailf:cli-mode-name "config-pw-class";
      tailf:cli-full-command;
      key "name";
      leaf name {
        type string {
          tailf:info
            "WORD;;Pseudowire-class name";
        }
      }
      leaf encapsulation {
        tailf:info
          "Data encapsulation method";
        type enumeration {
          enum "l2tpv2" {
            tailf:info
              "Use L2TPv2 encapsulation";
          }
          enum "l2tpv3" {
            tailf:info
              "Use L2TPv3 encapsulation";
          }
          enum "mpls" {
            tailf:info
              "Use MPLS encapsulation";
          }
        }
      }
      leaf control-word {
        tailf:info
          "Include control-word in pseudowire packets";
        type empty;
      }
      container status {
        tailf:info
          "Pseudowire status capabilities";
        container peer {
          tailf:info
            "peer status configuration";
          container topology {
            tailf:info
              "change status behaviour based on peer topology";
            leaf dual-homed {
              tailf:info
                "Our peer(s) are participating in a redundant solution with some form of redundancy protocol running between the peer routers";
              type empty;
            }
          }
        }
      }
    }
    container control-plane {
      tailf:ncs-device-type "cli-ned";
      tailf:display-when "not(../../ncs:module) or ../../ncs:module[ncs:name='tailf-ned-cisco-ios']";
      tailf:info
        "Configure control plane services";
      tailf:cli-add-mode;
      tailf:cli-mode-name "config-cp";
      presence "true";
      container service-policy {
        tailf:info
          "Configure QOS Service Policy";
        uses service-policy-grouping;
      }
    }
    container cops {
      tailf:ncs-device-type "cli-ned";
      tailf:display-when "not(../../ncs:module) or ../../ncs:module[ncs:name='tailf-ned-cisco-ios']";
      tailf:info
        "Common Open Policy Service (COPS)";
      container listener {
        tailf:info
          "Incoming connections from policy decision points (PDPs)";
        leaf access-list {
          tailf:info
            "Rules for PDPs connecting to local COPS listeners";
          type exp-ip-acl-type;
        }
      }
      container ip {
        tailf:info
          "IP parameters for COPS connections";
        leaf dscp {
          tailf:info
            "Differentiated Services Code Point marking for COPS messages";
          type dscp-type;
        }
      }
    }
    list connect {
      tailf:ncs-device-type "cli-ned";
      tailf:display-when "not(../ncs:module) or ../ncs:module[ncs:name='tailf-ned-cisco-ios']";
      tailf:info
        "cross-connect two interfaces";
      tailf:cli-mode-name "config-connection";
      tailf:cli-compact-syntax;
      tailf:cli-sequence-commands;
      key "interface1 interface2";
      leaf name {
        tailf:cli-drop-node-name;
        tailf:cli-prefix-key;
        type string {
          tailf:info
            "WORD;;Name for this connection";
        }
      }
      leaf interface1 {
        type string {
          tailf:info
            "WORD;;First interface name";
        }
      }
      leaf number1 {
        tailf:cli-drop-node-name;
        tailf:cli-prefix-key {
          tailf:cli-before-key 2;
        }
        tailf:cli-optional-in-sequence;
        type uint16 {
          tailf:info
            "<1-8184>;;Service Instance Identifier";
          range "1..8184";
        }
      }
      leaf interface2 {
        type string {
          tailf:info
            "WORD;;Second interface name";
        }
      }
      leaf number2 {
        tailf:cli-drop-node-name;
        tailf:cli-hide-in-submode;
        type uint16 {
          tailf:info
            "<1-8184>;;Service Instance Identifier";
          range "1..8184";
        }
      }
      container backup {
        tailf:cli-break-sequence-commands;
        tailf:info
          "Xconnect backup configuration commands";
        container peer {
          tailf:info
            "Backup pseudowire";
          tailf:cli-compact-syntax;
          tailf:cli-sequence-commands {
            tailf:cli-reset-siblings;
          }
          leaf peer-router-ip-addr {
            tailf:cli-drop-node-name;
            tailf:cli-incomplete-command;
            type inet:ipv4-address {
              tailf:info
                "A.B.C.D;;IP address of peer";
            }
          }
          leaf vcid {
            tailf:cli-drop-node-name;
            type uint32 {
              tailf:info
                "<1-4294967295>;;Peer VC ID value";
              range "1..4294967295";
            }
          }
          leaf pw-class {
            tailf:cli-optional-in-sequence;
            type string {
              tailf:info
                "Optional Pseudowire-class to use for backup pseudowire";
            }
          }
        }
      }
    }
    list voice-port {
      tailf:ncs-device-type "cli-ned";
      tailf:display-when "not(../ncs:module) or ../ncs:module[ncs:name='tailf-ned-cisco-ios']";
      tailf:info
        "Configure a specific voice-port";
      tailf:cli-mode-name "config-voiceport";
      key "name";
      leaf name {
        type string {
          tailf:info
            "<0-0>;;Voice interface slot #";
        }
      }
      container timeouts {
        tailf:info
          "Configure voice timeout parameters";
        leaf interdigit {
          tailf:info
            "Interdigit Timeout duration in seconds";
          type uint8 {
            tailf:info
              "<0-120>;;seconds";
            range "0..120";
          }
        }
      }
      container busyout {
        tailf:info
          "Configure busyout trigger event & procedure";
        leaf action {
          tailf:cli-full-command;
          type string;
        }
        container monitor {
          tailf:info
            "The event of this interface triggers busyout";
          container action {
            tailf:info
              "busyout action when monitoring triggered";
            choice action-choice {
              leaf graceful {
                tailf:info
                  "graceful busyout when monitoring triggered";
                type empty;
              }
              leaf shutdown {
                tailf:info
                  "shutdown D channel when monitoring triggered";
                type empty;
              }
              container alarm {
                tailf:info
                  "Use alarm generation";
                leaf blue {
                  tailf:info
                    "Use blue alarm";
                  type empty;
                }
              }
            }
          }
          list state {
            tailf:cli-drop-node-name;
            tailf:cli-suppress-mode;
            tailf:cli-delete-when-empty;
            tailf:cli-compact-syntax;
            key "name";
            leaf name {
              type string {
                tailf:info
                  "WORD;;Interface name";
              }
            }
            leaf in-service {
              tailf:info
                "Inverted logic trigger by interface back up or in service";
              type empty;
            }
          }
        }
      }
    }
    container dial-peer {
      tailf:ncs-device-type "cli-ned";
      tailf:display-when "not(../../ncs:module) or ../../ncs:module[ncs:name='tailf-ned-cisco-ios']";
      tailf:info
        "Dial Map (Peer) configuration commands";
      list voice {
        tailf:info
          "Voice type";
        tailf:cli-mode-name "config-dial-peer";
        tailf:cli-incomplete-command;
        tailf:cli-sequence-commands;
        key "id";
        leaf id {
          type uint32 {
            tailf:info
              "<1-2147483647>;;Voice dial-peer tag";
            range "1..2147483647";
          }
        }
        leaf peer {
          tailf:cli-drop-node-name;
          tailf:cli-hide-in-submode;
          type enumeration {
            enum "mmoip" {
              tailf:info
                "Multi Media Over IP";
            }
            enum "pots" {
              tailf:info
                "Telephony";
            }
            enum "voatm" {
              tailf:info
                "Voice over ATM";
            }
            enum "vofr" {
              tailf:info
                "Voice over Frame Relay";
            }
            enum "voip" {
              tailf:info
                "Voice over IP";
            }
          }
        }
        leaf answer-address {
          tailf:cli-break-sequence-commands;
          tailf:info
            "The Call Destination Number";
          tailf:cli-full-command;
          type string {
            tailf:info
              "WORD;;A string of digits including wild cards";
          }
        }
        leaf trunkgroup {
          tailf:info
            "trunk groups associated with this peer";
          type string {
            tailf:info
              "WORD;;trunkgroup id";
          }
          tailf:non-strict-leafref {
            path "/ncs:devices/ncs:device/ncs:config/ios:trunk/group/name" {
              tailf:xpath-root 3;
            }
          }
        }
        leaf description {
          tailf:info
            "Dialpeer specific description";
          tailf:cli-multi-value;
          type string {
            tailf:info
              "LINE;;Up to 64 characters describing this dialpeer";
            length "1..64";
          }
        }
        container translation-profile {
          tailf:info
            "Translation profile";
          leaf incoming {
            tailf:info
              "Translation Profile for incoming call leg";
            tailf:cli-full-command;
            type string {
              tailf:info
                "WORD;;Profile name";
            }
          }
          leaf outgoing {
            tailf:info
              "Translation Profile for outgoing call leg";
            tailf:cli-full-command;
            type string {
              tailf:info
                "WORD;;Profile name";
            }
          }
        }
        leaf huntstop {
          tailf:info
            "Stop hunting on Dial-Peers";
          tailf:cli-full-command;
          type empty;
        }
        leaf max-conn {
          tailf:info
            "Sets the maximum connections per peer, negation sets to unlimited";
          tailf:cli-full-command;
          type uint32 {
            tailf:info
              "<1-2147483647>;;Maximum connections, negation sets to unlimited";
          }
        }
        leaf destination-pattern {
          tailf:info
            "A full E.164 telephone number prefix";
          tailf:cli-full-command;
          type string {
            tailf:info
              "WORD;;A sequence of digits - representing the prefix or full telephone number";
          }
        }
        container modem {
          tailf:info
            "Modem commands through this peer";
          container passthrough {
            tailf:info
              "Pass modem traffic via clear channel";
            choice passthrough-choice {
              leaf system {
                tailf:info
                  "Use global configuration";
                tailf:cli-boolean-no;
                tailf:cli-full-command;
                type boolean;
                default "true";
              }
              container nse {
                tailf:info
                  "Use Named Signaling Events (NSE)";
                tailf:cli-compact-syntax;
                leaf payload-type {
                  tailf:info
                    "Configure NSE payload type";
                  type uint32 {
                    tailf:info
                      "<98-117>;;Payload type value";
                  }
                }
                leaf codec {
                  tailf:info
                    "Codec selections for upspeed";
                  type enumeration {
                    enum "g711ulaw" {
                      tailf:info
                        "G.711 u Law 64000 bp";
                    }
                    enum "g711alaw" {
                      tailf:info
                        "G.711 A Law 64000 bps";
                    }
                  }
                }
                leaf redundancy {
                  tailf:info
                    "Use Packet Redundancy (RFC2198) for modem traffic";
                  type empty;
                }
              }
            }
          }
        }
        container session {
          tailf:info
            "The session [ target | protocol | transport ] for this peer";
          leaf protocol {
            tailf:info
              "The session protocol to be used in getting to this peer";
            type enumeration {
              enum "aal2-trunk";
              enum "cisco" {
                tailf:info
                  "Cisco Session Protocol";
              }
              enum "sipv2" {
                tailf:info
                  "IETF Session Initiation Protocol";
              }
              enum "smtp";
              enum "multicast" {
                tailf:info
                  "Multicast Session Protocol(voice conferencing)";
              }
            }
          }
          leaf target {
            tailf:info
              "The session target for this peer";
            tailf:cli-multi-value;
            tailf:cli-full-command;
            type string {
              tailf:info
                "WORD;;A string specifying the session target";
            }
          }
        }
        container dtmf-relay {
          tailf:info
            "Transport DTMF digits across IP link. Enter DTMF Relay options in order of preference.";
          tailf:cli-compact-syntax;
          tailf:cli-reset-container;
          leaf cisco-rtp {
            tailf:info
              "Cisco Proprietary RTP";
            type empty;
          }
          leaf h245-alphanumeric {
            tailf:info
              "DTMF Relay via H245 Alphanumeric IE";
            type empty;
          }
          leaf h245-signal {
            tailf:info
              "DTMF Relay via H245 Signal IE";
            type empty;
          }
          leaf rtp-nte {
            tailf:info
              "RTP Named Telephone Event RFC 2833";
            type empty;
          }
        }
        container incoming {
          tailf:info
            "Incoming called number";
          leaf called-number {
            tailf:info
              "An incoming called number pattern";
            type string {
              tailf:info
                "WORD;;A sequence of digits representing a phone number prefix";
            }
          }
        }
        leaf direct-inward-dial {
          type empty;
        }
        leaf forward-digits {
          type union {
            type uint8;
            type enumeration {
              enum "all";
              enum "extra";
            }
          }
        }
        container codec {
          tailf:info
            "The codec rate to be attempted in getting to this peer";
          tailf:cli-compact-syntax;
          tailf:cli-sequence-commands {
            tailf:cli-reset-siblings;
          }
          leaf name {
            tailf:cli-drop-node-name;
            type string {
              tailf:info
                "WORD;;Codec name";
            }
          }
          leaf bytes {
            tailf:info
              "Specify number of voice data bytes per frame";
            tailf:cli-break-sequence-commands;
            type uint32;
          }
          leaf mode {
            tailf:info
              "Specify the value of the mode";
            type uint32 {
              tailf:info
                "20 = 15.2 kbps, 30 = 13.33 kbps";
            }
          }
        }
        container fax {
          tailf:info
            "Configure fax";
          container protocol {
            tailf:info
              "The fax protocol to be attempted in getting to this peer";
            choice protocol-option {
              leaf none {
                tailf:info
                  "No FAX protocol";
                type empty;
              }
              leaf cisco {
                tailf:info
                  "Use Cisco proprietary protocol";
                type empty;
              }
              leaf pass-through {
                tailf:info
                  "Use an audio codec for fax transport";
                type enumeration {
                  enum "g711ulaw" {
                    tailf:info
                      "G.711 u Law 64000 bps (for T1)";
                  }
                  enum "g711alaw" {
                    tailf:info
                      "G.711 A Law 64000 bps (for E1)";
                  }
                }
              }
            }
          }
        }
        container ip {
          tailf:info
            "Set ip packet options";
          container qos {
            tailf:info
              "Set ip QoS Parameters";
            list dscp {
              tailf:info
                "Specify ip DSCP";
              tailf:cli-compact-syntax;
              tailf:cli-suppress-mode;
              tailf:cli-delete-when-empty;
              tailf:cli-incomplete-command;
              key "name";
              leaf name {
                type string {
                  tailf:info
                    "WORD;;voice set";
                }
              }
              choice dscp-choice {
                leaf media {
                  tailf:info
                    "Apply DSCP to media payload packets";
                  type empty;
                }
                leaf signaling {
                  tailf:info
                    "Apply DSCP to signaling packets";
                  type empty;
                }
                leaf video {
                  tailf:info
                    "Apply DSCP to video packets";
                  type enumeration {
                    enum "rsvp-none" {
                      tailf:info
                        "Use this DSCP value if RSVP is not configured";
                    }
                    enum "rsvp-pass" {
                      tailf:info
                        "Use this DSCP value if RSVP reservation is successful";
                    }
                    enum "rsvp-fail" {
                      tailf:info
                        "Use this DSCP value if RSVP reservation fails";
                    }
                  }
                }
              }
            }
          }
        }
        leaf vad {
          tailf:info
            "Use VoiceActivityDetection as necessary option";
          tailf:cli-full-command;
          tailf:cli-boolean-no;
          type boolean;
          default "true";
        }
      }
      container outbound {
        tailf:info
          "Define the outbound options";
        container status-check {
          tailf:info
            "Enable or disable status checking";
          leaf pots {
            tailf:info
              "Telephony";
            tailf:cli-boolean-no;
            tailf:cli-full-command;
            type boolean;
            default "true";
          }
        }
      }
      container cor {
        container custom {
          tailf:cli-add-mode;
          presence "true";
          list name {
            tailf:cli-suppress-mode;
            tailf:cli-delete-when-empty;
            key "name";
            leaf name {
              type string;
            }
          }
        }
      }
    }
    leaf config-register {
      tailf:ncs-device-type "cli-ned";
      tailf:display-when "not(../../ncs:module) or ../../ncs:module[ncs:name='tailf-ned-cisco-ios']";
      tailf:info
        "Define the configuration register";
      type string {
        tailf:info
          "<0x0-0xFFFF>;;Config register number";
        pattern '[0-9xXa-fA-F].*';
      }
    }
    container network-clock-participate {
      tailf:ncs-device-type "cli-ned";
      tailf:display-when "not(../../ncs:module) or ../../ncs:module[ncs:name='tailf-ned-cisco-ios']";
      tailf:info
        "Participate in Network Clocking";
      container wic {
        tailf:info
          "WIC Module";
        list wic-enabled {
          tailf:cli-drop-node-name;
          tailf:cli-suppress-mode;
          tailf:cli-delete-when-empty;
          key "slot";
          leaf slot {
            type uint8 {
              tailf:info
                "<0-3>;;Slot Number (physical)";
              range "0..3";
            }
          }
        }
        list wic-disabled {
          tailf:cli-suppress-mode;
          tailf:cli-delete-when-empty;
          key "slot";
          leaf slot {
            type uint8 {
              tailf:info
                "<0-3>;;Slot Number (physical)";
              range "0..3";
            }
          }
        }
      }
    }
    container mgcp {
      tailf:ncs-device-type "cli-ned";
      tailf:display-when "not(../../ncs:module) or ../../ncs:module[ncs:name='tailf-ned-cisco-ios']";
      tailf:info
        "Enable Media Gateway Control Protocol";
      container fax {
        tailf:info
          "Configure MGCP Fax Parameters";
        container t38 {
          tailf:info
            "Configure MGCP Fax T.38 Parameters";
          leaf ecm {
            tailf:info
              "Enable Error Correction Mode (ECM)";
            tailf:cli-full-command;
            type empty;
          }
        }
      }
      container behavior {
        tailf:info
          "Set MGCP message behavior";
        container g729-variants {
          leaf static-pt {
            type empty;
          }
        }
      }
      list profile {
        tailf:info
          "MGCP profile configuration mode";
        tailf:cli-mode-name "config-mgcp-profile";
        tailf:cli-delete-when-empty;
        key "name";
        leaf name {
          type union {
            type enumeration {
              enum "default" {
                tailf:info
                  "Configure MGCP default profile";
              }
            }
            type string {
              tailf:info
                "Enter the name(is limited to 32 characters) of the profile";
              length "0..32";
            }
          }
        }
      }
    }
    container gatekeeper {
      tailf:ncs-device-type "cli-ned";
      tailf:display-when "not(../../ncs:module) or ../../ncs:module[ncs:name='tailf-ned-cisco-ios']";
      tailf:info
        "Enter gatekeeper configuration mode";
      tailf:cli-add-mode;
      tailf:cli-mode-name "config-gk";
      leaf shutdown {
        tailf:info
          "Shutdown Gatekeeper";
        type empty;
      }
    }
    container line {
      tailf:ncs-device-type "cli-ned";
      tailf:display-when "not(../../ncs:module) or ../../ncs:module[ncs:name='tailf-ned-cisco-ios']";
      tailf:info
        "Configure a terminal line";
      list console {
        tailf:info
          "Primary terminal line";
        tailf:cli-full-command;
        tailf:cli-mode-name "config-line";
        key "first";
        max-elements 1;
        leaf first {
          type enumeration {
            enum "0" {
              tailf:info
                "<0-0>;;First Line number";
            }
          }
        }
        uses line-grouping;
      }
      list aux {
        tailf:info
          "Auxiliary line";
        tailf:cli-full-command;
        tailf:cli-mode-name "config-line";
        key "first";
        max-elements 1;
        leaf first {
          type enumeration {
            enum "0" {
              tailf:info
                "<0-0>;;First Line number";
            }
          }
        }
        uses line-grouping;
      }
      container vty-single {
        tailf:cli-drop-node-name;
        list vty {
          tailf:info
            "Virtual terminal";
          tailf:cli-full-command;
          tailf:cli-mode-name "config-line";
          key "first";
          leaf first {
            type uint16 {
              tailf:info
                "<0-1869>;;First Line number";
              range "0..1869";
            }
          }
          uses line-grouping;
        }
      }
      list vty {
        tailf:info
          "Virtual terminal";
        tailf:cli-full-command;
        tailf:cli-mode-name "config-line";
        key "first last";
        leaf first {
          type uint16 {
            tailf:info
              "<0-1869>;;First Line number";
            range "0..1869";
          }
        }
        leaf last {
          type uint16 {
            tailf:info
              "<1-1869>;;Last Line number";
            range "1..1869";
          }
        }
        uses line-grouping;
      }
      list number-single {
        tailf:cli-drop-node-name;
        tailf:cli-full-command;
        tailf:cli-mode-name "config-line";
        key "first";
        leaf first {
          tailf:cli-suppress-range;
          tailf:cli-disallow-value "con|console|aux|vty";
          type string {
            tailf:info
              "Line number";
          }
        }
        uses line-grouping;
      }
      list number {
        tailf:cli-drop-node-name;
        tailf:cli-full-command;
        tailf:cli-mode-name "config-line";
        key "first last";
        leaf first {
          tailf:cli-suppress-range;
          type uint16 {
            tailf:info
              "<0-X>;;First Line number";
          }
        }
        leaf last {
          tailf:cli-suppress-range;
          type uint16 {
            tailf:info
              "<1-Y>;;Last Line number";
          }
        }
        uses line-grouping;
      }
    }
    container pnp {
      tailf:ncs-device-type "cli-ned";
      tailf:display-when "not(../../ncs:module) or ../../ncs:module[ncs:name='tailf-ned-cisco-ios']";
      tailf:info
        "Configure PNP";
      list profile {
        tailf:info
          "PNP profile";
        tailf:cli-mode-name "config-pnp-init";
        key "name";
        leaf name {
          type string {
            tailf:info
              "WORD;;PNP Profile name";
          }
        }
        container transport {
          tailf:info
            "The transport to use";
          tailf:cli-compact-syntax;
          tailf:cli-sequence-commands {
            tailf:cli-reset-siblings;
          }
          leaf protocol {
            tailf:cli-drop-node-name;
            type enumeration {
              enum "http" {
                tailf:info
                  "Use http (plaintext) transport";
              }
              enum "https" {
                tailf:info
                  "Use https (encrypted) transport";
              }
              enum "xmpp" {
                tailf:info
                  "Use XMPP transport";
              }
            }
          }
          leaf over {
            tailf:cli-drop-node-name;
            when "../protocol = 'xmpp'" {
              tailf:xpath-root 3;
              tailf:dependency "../protocol";
            }
            type enumeration {
              enum "socket" {
                tailf:info
                  "xmpp over plain socket (no encryption)";
              }
              enum "starttls" {
                tailf:info
                  "xmpp starttls";
              }
              enum "tls" {
                tailf:info
                  "xmpp over tls (encrypted)";
              }
            }
          }
          choice address-choice {
            leaf host {
              tailf:info
                "hostname of server";
              type inet:host {
                tailf:info
                  "WORD;;Hostname of the server";
              }
            }
            leaf ipv4 {
              tailf:info
                "ipv4 address";
              type inet:ipv4-address {
                tailf:info
                  "WORD;;IP address of the server";
              }
            }
            leaf ipv6 {
              tailf:info
                "IPv6 address";
              type inet:ipv6-address {
                tailf:info
                  "X:X:X:X::X;;IPv6 address of server";
              }
            }
          }
          leaf port {
            tailf:info
              "port number";
            type uint16 {
              tailf:info
                "<1-65535>;;Port number to use";
            }
          }
          container source {
            tailf:info
              "Bind port to interface";
            tailf:cli-flatten-container;
            tailf:cli-compact-syntax;
            uses interface-name-grouping;
          }
        }
        container reconnect {
          tailf:info
            "Pause to wait before reconnecting";
          leaf seconds {
            tailf:cli-drop-node-name;
            type uint32 {
              tailf:info
                "<1-2000000>;;Pause in seconds";
              range "1..2000000";
            }
          }
        }
      }
      leaf startup-vlan {
        tailf:info
          "PNP startup-vlan";
        tailf:cli-full-command;
        type uint16 {
          tailf:info
            "PNP vlan id;default vlan is 1";
          range "2..4094";
        }
      }
      leaf tag {
        tailf:info
          "PNP tag";
        tailf:cli-full-command;
        type string {
          tailf:info
            "WORD;;PNP tag name";
        }
      }
    }
    container onep {
      tailf:ncs-device-type "cli-ned";
      tailf:display-when "not(../../ncs:module) or ../../ncs:module[ncs:name='tailf-ned-cisco-ios']";
      tailf:info
        "ONEP functionality";
      tailf:cli-add-mode;
      leaf start {
        tailf:cli-boolean-no;
        tailf:cli-full-command;
        type boolean;
      }
      container transport {
        tailf:info
          "Transport type";
        container tipc {
          tailf:info
            "tipc transport";
          presence "true";
        }
      }
    }
    container logging {
      tailf:ncs-device-type "cli-ned";
      tailf:display-when "not(../../ncs:module) or ../../ncs:module[ncs:name='tailf-ned-cisco-ios']";
      tailf:info
        "Modify message logging facilities";
      list discriminator {
        tailf:info
          "Create or modify a message discriminator";
        tailf:cli-suppress-mode;
        tailf:cli-delete-when-empty;
        tailf:cli-compact-syntax;
        key "discr-name";
        leaf discr-name {
          type string {
            tailf:info
              "WORD;;discriminator name; string; max. 8 characters";
          }
        }
        container mnemonics {
          tailf:info
            "Mnemonics pattern for messsage filtering";
          tailf:cli-flatten-container;
          tailf:cli-compact-syntax;
          choice mnemonics-choice {
            leaf drops {
              tailf:info
                "To drop messages including the specified regexp string";
              type string {
                tailf:info
                  "WORD;;Specify a regular expression string for message filtering";
              }
            }
            leaf includes {
              tailf:info
                "To deliver messages including the specified regexp string";
              type string {
                tailf:info
                  "WORD;;Specify a regular expression string for message filtering";
              }
            }
          }
        }
        container msg-body {
          tailf:info
            "Msg-body pattern for messsage filtering";
          tailf:cli-flatten-container;
          tailf:cli-compact-syntax;
          choice mnemonics-choice {
            leaf drops {
              tailf:info
                "To drop messages including the specified regexp string";
              type string {
                tailf:info
                  "WORD;;Specify a regular expression string for message filtering";
              }
            }
            leaf includes {
              tailf:info
                "To deliver messages including the specified regexp string";
              type string {
                tailf:info
                  "WORD;;Specify a regular expression string for message filtering";
              }
            }
          }
        }
      }
      container cmts {
        tailf:info
          "CMTS config commands";
        container ipc-cable {
          tailf:info
            "Cable IPC config commands";
          leaf log-level {
            tailf:info
              "cable ipc log level config commands";
            type logging-level-type;
          }
        }
        container sea {
          tailf:info
            "SEA config commands";
          leaf syslog-level {
            tailf:info
              "Specify syslog loggging level";
            type logging-level-type;
          }
        }
      }
      leaf alarm {
        tailf:info
          "Configure syslog for alarms";
        tailf:cli-full-command;
        type union {
          type uint8 {
            tailf:info
              "<1-4>;;Alarm Logging severity level";
            range "1..4";
          }
          type enumeration {
            enum "critical" {
              tailf:info
                "Service affecting Condition       (severity=1)";
            }
            enum "informational" {
              tailf:info
                "Informational messages            (severity=4)";
            }
            enum "major" {
              tailf:info
                "Immediate action needed           (severity=2)";
            }
            enum "minor" {
              tailf:info
                "Minor warning conditions          (severity=3)";
            }
          }
        }
      }
      container buffered {
        tailf:info
          "Set buffered logging parameters";
        tailf:cli-compact-syntax;
        tailf:cli-sequence-commands {
          tailf:cli-reset-siblings;
        }
        leaf xxml {
          tailf:alt-name "xml";
          tailf:info
            "Enable logging in XML to XML logging buffer";
          tailf:cli-optional-in-sequence;
          type empty;
        }
        leaf discriminator {
          tailf:info
            "Establish MD-Console association";
          tailf:cli-optional-in-sequence;
          type string {
            tailf:info
              "WORD;;discriminator name; string; max. 8 characters";
          }
        }
        leaf buffer-size {
          tailf:cli-drop-node-name;
          type uint32 {
            tailf:info
              "<4096-2147483647>;;Logging buffer size";
            range "4096..2147483647";
          }
        }
        leaf severity-level {
          tailf:cli-drop-node-name;
          type logging-level-type;
          default "debugging";
        }
      }
      container console {
        tailf:info
          "Set console logging parameters";
        tailf:cli-compact-syntax;
        tailf:cli-sequence-commands {
          tailf:cli-reset-siblings;
        }
        leaf xxml {
          tailf:alt-name "xml";
          tailf:info
            "Enable logging in XML to XML logging buffer";
          tailf:cli-optional-in-sequence;
          type empty;
        }
        leaf discriminator {
          tailf:info
            "Establish MD-Console association";
          tailf:cli-optional-in-sequence;
          type string {
            tailf:info
              "WORD;;discriminator name; string; max. 8 characters";
          }
        }
        leaf severity-level {
          tailf:cli-drop-node-name;
          type logging-level-type;
          default "debugging";
        }
      }
      container event {
        tailf:info
          "Global interface events";
        container link-status {
          tailf:info
            "Globally enable/disable link UPDOWN message";
          leaf boot {
            tailf:info
              "Supress/Allow link UPDOWN messages during boot";
            type empty;
          }
          leaf global {
            type empty;
          }
          leaf default {
            tailf:info
              "Link UPDOWN messages for all interfaces";
            type empty;
          }
        }
      }
      container esm {
        tailf:info
          "Set ESM filter restrictions";
        leaf config {
          tailf:info
            "Permit/Deny configuration changes from ESM filters";
          tailf:cli-full-command;
          type empty;
        }
      }
      leaf facility {
        tailf:info
          "Facility parameter for syslog messages";
        type enumeration {
          enum "auth" {
            tailf:info
              "Authorization system";
          }
          enum "cron" {
            tailf:info
              "Cron/at facility";
          }
          enum "daemon" {
            tailf:info
              "System daemons";
          }
          enum "kern" {
            tailf:info
              "Kernel";
          }
          enum "local0" {
            tailf:info
              "Local use";
          }
          enum "local1" {
            tailf:info
              "Local use";
          }
          enum "local2" {
            tailf:info
              "Local use";
          }
          enum "local3" {
            tailf:info
              "Local use";
          }
          enum "local4" {
            tailf:info
              "Local use";
          }
          enum "local5" {
            tailf:info
              "Local use";
          }
          enum "local6" {
            tailf:info
              "Local use";
          }
          enum "local7" {
            tailf:info
              "Local use";
          }
          enum "lpr" {
            tailf:info
              "Line printer system";
          }
          enum "mail" {
            tailf:info
              "Mail system";
          }
          enum "news" {
            tailf:info
              "USENET news";
          }
          enum "sys10" {
            tailf:info
              "System use";
          }
          enum "sys11" {
            tailf:info
              "System use";
          }
          enum "sys12" {
            tailf:info
              "System use";
          }
          enum "sys13" {
            tailf:info
              "System use";
          }
          enum "sys14" {
            tailf:info
              "System use";
          }
          enum "sys9" {
            tailf:info
              "System use";
          }
          enum "syslog" {
            tailf:info
              "Syslog itself";
          }
          enum "user" {
            tailf:info
              "User process";
          }
          enum "uucp" {
            tailf:info
              "Unix-to-Unix copy system";
          }
        }
      }
      container history {
        tailf:info
          "Configure syslog history table";
        leaf size {
          tailf:info
            "Set history table size";
          type uint16 {
            tailf:info
              "<0-500>;History size";
          }
        }
        leaf severity-level {
          tailf:cli-drop-node-name;
          type union {
            type uint8 {
              tailf:info
                "<0-7>;;Logging severity level";
              range "0..7";
            }
            type enumeration {
              enum "alerts" {
                tailf:info
                  "Immediate action needed           (severity=1)";
              }
              enum "critical" {
                tailf:info
                  "Critical conditions               (severity=2)";
              }
              enum "debugging" {
                tailf:info
                  "Debugging messages                (severity=7)";
              }
              enum "emergencies" {
                tailf:info
                  "System is unusable                (severity=0)";
              }
              enum "errors" {
                tailf:info
                  "Error conditions                  (severity=3)";
              }
              enum "informational" {
                tailf:info
                  "Informational messages            (severity=6)";
              }
              enum "notifications" {
                tailf:info
                  "Normal but significant conditions (severity=5)";
              }
              enum "warnings" {
                tailf:info
                  "Warning conditions                (severity=4)";
              }
            }
          }
        }
      }
      list hostname {
        tailf:info
          "Hostname or A.B.C.D;;IP address of the logging host";
        tailf:cli-drop-node-name;
        tailf:cli-suppress-mode;
        tailf:cli-delete-when-empty;
        key "host";
        leaf host {
          tailf:cli-disallow-value "esm|alarm|buffered|facility|history|rate-limit|source-interface|host|console";
          tailf:cli-full-command;
          type inet:host {
            tailf:info
              "Hostname or A.B.C.D";
          }
        }
      }
      list host {
        tailf:info
          "Set syslog server IP address and parameters";
        tailf:cli-suppress-mode;
        tailf:cli-delete-when-empty;
        tailf:cli-compact-syntax;
        key "host";
        leaf host {
          tailf:cli-disallow-value "esm|alarm|buffered|facility|history|rate-limit|source-interface|host";
          tailf:cli-full-command;
          type inet:host {
            tailf:info
              "Hostname or A.B.C.D";
          }
        }
        leaf vrf {
          tailf:info
            "Set VRF option";
          tailf:cli-diff-dependency "/ios:ip/vrf" {
            tailf:xpath-root 3;
          }
          tailf:cli-diff-dependency "/ios:vrf/definition" {
            tailf:xpath-root 3;
          }
          type string {
            tailf:info
              "WORD;;VPN Routing/Forwarding instance name";
          }
        }
        leaf discriminator {
          tailf:info
            "Specify a message discriminator identifier for this logging session";
          type string {
            tailf:info
              "WORD;;Message discriminator identifier for this logging session (8 chars. max)";
          }
        }
      }
      container rate-limit {
        tailf:info
          "Set messages per second limit";
        tailf:cli-sequence-commands;
        tailf:cli-compact-syntax;
        tailf:cli-reset-container;
        leaf console {
          tailf:info
            "Rate limit only console messages";
          tailf:cli-optional-in-sequence;
          tailf:cli-incomplete-command;
          type empty;
        }
        leaf all {
          tailf:info
            "Rate limit all messages, including debug messages";
          tailf:cli-optional-in-sequence;
          tailf:cli-incomplete-command;
          type empty;
        }
        leaf rate {
          tailf:cli-drop-node-name;
          type uint16 {
            tailf:info
              "<1-10000>;;Messages per second";
          }
        }
      }
      container source-interface {
        tailf:info
          "Specify interface for source address in logging transactions";
        tailf:cli-compact-syntax;
        uses interface-name-grouping;
        leaf vrf {
          tailf:info
            "Specify the vrf of source interface for logging transactions";
          type string {
            tailf:info
              "WORD;;VPN Routing/Forwarding instance name";
          }
        }
      }
      leaf trap {
        tailf:info
          "Set syslog server logging level";
        tailf:cli-full-command;
        type logging-level-type;
      }
    }
    container cpd {
      tailf:ncs-device-type "cli-ned";
      tailf:display-when "not(../../ncs:module) or ../../ncs:module[ncs:name='tailf-ned-cisco-ios']";
      tailf:info
        "Global Control Point Discovery Configuration";
      tailf:cli-display-separated;
      presence "true";
      leaf cr-id {
        tailf:info
          "Control Relationship Identifier";
        type uint16 {
          tailf:info
            "<1-65535>;;Control Relationship Identifier Value";
          range "1..65535";
        }
      }
    }
    container nls {
      tailf:ncs-device-type "cli-ned";
      tailf:display-when "not(../../ncs:module) or ../../ncs:module[ncs:name='tailf-ned-cisco-ios']";
      tailf:info
        "Global Network Layer Signaling Configuration";
      tailf:cli-display-separated;
      presence "true";
      leaf resp-timeout {
        tailf:info
          "NLS Response Timeout";
        type uint8 {
          tailf:info
            "<1-60>;;NLS Response Timeout Value";
          range "1..60";
        }
      }
    }
    list flow-sampler-map {
      tailf:ncs-device-type "cli-ned";
      tailf:display-when "not(../ncs:module) or ../ncs:module[ncs:name='tailf-ned-cisco-ios']";
      tailf:info
        "Flow sampler configuration";
      tailf:cli-mode-name "config-sampler";
      key "name";
      leaf name {
        type string {
          tailf:info
            "WORD;;Name of the flow sampler";
        }
      }
      container mode {
        tailf:info
          "Mode of packet sampling for netflow processing";
        container random {
          tailf:info
            "Random mode of sampling";
          leaf one-out-of {
            tailf:info
              "Select one packet out of";
            type uint16 {
              tailf:info
                "<1-65535>;number of sequential packets to select one packet from";
              range "1..65535";
            }
          }
        }
      }
    }
    container frame-relay {
      tailf:ncs-device-type "cli-ned";
      tailf:display-when "not(../../ncs:module) or ../../ncs:module[ncs:name='tailf-ned-cisco-ios']";
      tailf:info
        "global frame relay configuration commands";
      leaf switching {
        tailf:info
          "enable frame relay pvc switching";
        type empty;
      }
    }
    container scheduler {
      tailf:ncs-device-type "cli-ned";
      tailf:display-when "not(../../ncs:module) or ../../ncs:module[ncs:name='tailf-ned-cisco-ios']";
      tailf:info
        "Scheduler parameters";
      container allocate {
        tailf:info
          "Guarantee CPU time for processes";
        tailf:cli-compact-syntax;
        tailf:cli-sequence-commands;
        leaf interrupt-time {
          tailf:cli-drop-node-name;
          tailf:cli-incomplete-command;
          type uint16 {
            tailf:info
              "<400-60000>;;Microseconds handling network interrupts";
            range "400..60000";
          }
        }
        leaf process-time {
          tailf:cli-drop-node-name;
          type uint16 {
            tailf:info
              "<100-4000>;;Microseconds running processes";
            range "100..4000";
          }
        }
      }
      leaf isr-watchdog {
        tailf:info
          "Detect ISR Hang";
        type empty;
      }
    }
    container process {
      tailf:ncs-device-type "cli-ned";
      tailf:display-when "not(../../ncs:module) or ../../ncs:module[ncs:name='tailf-ned-cisco-ios']";
      tailf:info
        "Configure process";
      container cpu {
        tailf:info
          "Configure cpu parameters";
        container threshold {
          tailf:info
            "cpu threshold parameters";
          container type {
            tailf:info
              "cpu threshold type";
            tailf:cli-compact-syntax;
            container total {
              tailf:info
                "total cpu utilization";
              tailf:cli-compact-syntax;
              tailf:cli-sequence-commands {
                tailf:cli-reset-siblings;
              }
              uses process-cpu-threshold-grouping;
            }
            container interrupt {
              tailf:info
                "interrupt level utilization";
              tailf:cli-compact-syntax;
              tailf:cli-sequence-commands {
                tailf:cli-reset-siblings;
              }
              uses process-cpu-threshold-grouping;
            }
            container process {
              tailf:info
                "process level utilization";
              tailf:cli-compact-syntax;
              tailf:cli-sequence-commands {
                tailf:cli-reset-siblings;
              }
              uses process-cpu-threshold-grouping;
            }
          }
        }
      }
    }
    container ntp {
      tailf:ncs-device-type "cli-ned";
      tailf:display-when "not(../../ncs:module) or ../../ncs:module[ncs:name='tailf-ned-cisco-ios']";
      tailf:info
        "Configure NTP";
      tailf:cli-diff-dependency "/ios:ip/vrf" {
        tailf:xpath-root 3;
      }
      tailf:cli-diff-dependency "/ios:vrf/definition" {
        tailf:xpath-root 3;
      }
      leaf max-associations {
        tailf:info
          "Set maximum number of associations";
        tailf:cli-full-command;
        type uint32 {
          tailf:info
            "<0-4294967295>;;Number of associations";
        }
      }
      leaf passive {
        tailf:info
          "NTP passive mode";
        tailf:cli-full-command;
        type empty;
      }
      leaf logging {
        tailf:info
          "Enable NTP message logging";
        tailf:cli-full-command;
        type empty;
      }
      container panic {
        tailf:info
          "Reject time updates > panic threshold (default 1000Sec)";
        leaf update {
          tailf:info
            "Reject time updates > panic threshold (default 1000Sec)";
          type empty;
        }
      }
      list authentication-key {
        tailf:info
          "Authentication key for trusted time sources";
        tailf:cli-suppress-mode;
        tailf:cli-delete-when-empty;
        tailf:cli-sequence-commands;
        tailf:cli-compact-syntax;
        tailf:cli-incomplete-command;
        key "number";
        leaf number {
          type uint32 {
            tailf:info
              "<1-4294967295>;;Key number";
            range "1..4294967295";
          }
        }
        leaf md5 {
          tailf:info
            "MD5 authentication";
          type string {
            tailf:info
              "WORD;;Authentication key";
          }
        }
        leaf encryption-type {
          tailf:cli-drop-node-name;
          type uint32 {
            tailf:info
              "<0-4294967295>;;Authentication key encryption type";
          }
        }
      }
      leaf authenticate {
        tailf:info
          "Authenticate time sources";
        tailf:cli-full-command;
        type empty;
      }
      list trusted-key {
        tailf:info
          "Key numbers for trusted time sources";
        tailf:cli-suppress-mode;
        tailf:cli-delete-when-empty;
        tailf:cli-sequence-commands;
        tailf:cli-compact-syntax;
        key "key-number";
        leaf key-number {
          type uint16 {
            tailf:info
              "<1-65535>;;Key number";
            range "1..65535";
          }
        }
        leaf hyphen {
          tailf:info
            "hyphen";
          tailf:alt-name "-";
          tailf:cli-incomplete-command;
          type empty;
        }
        leaf end-key-number {
          tailf:cli-drop-node-name;
          type uint16 {
            tailf:info
              "<1-65535>;;End Key range";
            range "1..65535";
          }
        }
      }
      leaf orphan {
        tailf:info
          "Threshold Stratum for orphan mode";
        tailf:cli-full-command;
        type uint8 {
          tailf:info
            "<1-16>;;Orphan stratum";
          range "1..16";
        }
      }
      leaf mindistance {
        tailf:info
          "Minimum distance to consider for clockhop";
        tailf:cli-full-command;
        type uint16 {
          tailf:info
            "<1-500>;;Minimum distance to consider for clockhop";
          range "1..500";
        }
      }
      leaf maxdistance {
        tailf:info
          "Maximum Distance for synchronization";
        tailf:cli-full-command;
        type uint8 {
          tailf:info
            "<1-16>;;Maximum distance for synchronization";
          range "1..16";
        }
      }
      leaf broadcastdelay {
        tailf:info
          "Estimated round-trip delay";
        tailf:cli-full-command;
        type uint32 {
          tailf:info
            "<1-999999>;;Round-trip delay in microseconds";
          range "1..999999";
        }
      }
      container source {
        tailf:info
          "Configure interface for source address";
        uses interface-name-grouping;
      }
      container access-group {
        tailf:info
          "Control NTP access";
        container peer {
          tailf:info
            "Provide full access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container query-only {
          tailf:info
            "Allow only control queries";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container serve {
          tailf:info
            "Provide server and query access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container serve-only {
          tailf:info
            "Provide only server access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
      }
      container master {
        tailf:info
          "Act as NTP master clock";
        tailf:cli-delete-when-empty;
        presence "true";
        leaf stratum {
          tailf:cli-drop-node-name;
          type uint8 {
            tailf:info
              "<1-15>;;Stratum number";
            range "1..15";
          }
        }
      }
      container peer {
        tailf:info
          "Configure NTP peer";
        uses ntp-peer-grouping;
        container ip {
          tailf:info
            "Use IP for DNS resolution";
          tailf:cli-compact-syntax;
          uses ntp-peer-grouping;
        }
        container ipv6 {
          tailf:info
            "Use IPv6 for DNS resolution";
          tailf:cli-compact-syntax;
          uses ntp-peer-grouping;
        }
        list vrf {
          tailf:info
            "VPN Routing/Forwarding Information";
          tailf:cli-suppress-mode;
          tailf:cli-delete-when-empty;
          tailf:cli-compact-syntax;
          tailf:cli-incomplete-command;
          key "name";
          leaf name {
            type string {
              tailf:info
                "WORD;;VPN Routing/Forwarding instance name";
            }
          }
          uses ntp-peer-grouping;
        }
      }
      container server {
        tailf:info
          "Configure NTP server";
        uses ntp-peer-grouping;
        container ip {
          tailf:info
            "Use IP for DNS resolution";
          tailf:cli-compact-syntax;
          uses ntp-peer-grouping;
        }
        container ipv6 {
          tailf:info
            "Use IPv6 for DNS resolution";
          tailf:cli-compact-syntax;
          uses ntp-peer-grouping;
        }
        list vrf {
          tailf:info
            "VPN Routing/Forwarding Information";
          tailf:cli-suppress-mode;
          tailf:cli-delete-when-empty;
          tailf:cli-compact-syntax;
          tailf:cli-reset-container;
          tailf:cli-incomplete-command;
          key "name";
          leaf name {
            type string {
              tailf:info
                "WORD;;VPN Routing/Forwarding instance name";
            }
          }
          uses ntp-peer-grouping;
        }
      }
      container allow {
        tailf:info
          "Allow processing of packets";
        container mode {
          tailf:info
            "Allow processing of particular mode packets";
          leaf private {
            tailf:info
              "Allow processing private mode packets";
            type empty;
          }
        }
      }
      leaf update-calendar {
        tailf:info
          "Periodically update calendar with NTP time";
        type empty;
      }
    }
    container sntp {
      tailf:ncs-device-type "cli-ned";
      tailf:display-when "not(../../ncs:module) or ../../ncs:module[ncs:name='tailf-ned-cisco-ios']";
      tailf:info
        "Configure SNTP";
      tailf:cli-incomplete-no;
      leaf logging {
        tailf:info
          "Enable SNTP message logging";
        tailf:cli-full-command;
        type empty;
      }
      list authentication-key {
        tailf:info
          "Authentication key for trusted time sources";
        tailf:cli-suppress-mode;
        tailf:cli-delete-when-empty;
        tailf:cli-sequence-commands;
        tailf:cli-compact-syntax;
        tailf:cli-incomplete-command;
        key "number";
        leaf number {
          type uint32 {
            tailf:info
              "<1-4294967295>;;Key number";
            range "1..4294967295";
          }
        }
        leaf md5 {
          tailf:info
            "MD5 authentication";
          type string {
            tailf:info
              "WORD;;Authentication key";
          }
        }
        leaf encryption-type {
          tailf:cli-drop-node-name;
          type uint32 {
            tailf:info
              "<0-4294967295>;;Authentication key encryption type";
          }
        }
      }
      leaf authenticate {
        tailf:info
          "Authenticate time sources";
        tailf:cli-full-command;
        type empty;
      }
      list trusted-key {
        tailf:info
          "Key numbers for trusted time sources";
        tailf:cli-suppress-mode;
        tailf:cli-delete-when-empty;
        tailf:cli-sequence-commands;
        tailf:cli-compact-syntax;
        key "key-number";
        leaf key-number {
          type uint16 {
            tailf:info
              "<1-65535>;;Key number";
            range "1..65535";
          }
        }
        leaf hyphen {
          tailf:info
            "hyphen";
          tailf:alt-name "-";
          tailf:cli-incomplete-command;
          type empty;
        }
        leaf end-key-number {
          tailf:cli-drop-node-name;
          type uint16 {
            tailf:info
              "<1-65535>;;End Key range";
            range "1..65535";
          }
        }
      }
      container server {
        tailf:info
          "Configure SNTP server";
        uses sntp-server-grouping;
        container ip {
          tailf:info
            "Use IP for DNS resolution";
          tailf:cli-compact-syntax;
          uses sntp-server-grouping;
        }
        container ipv6 {
          tailf:info
            "Use IPv6 for DNS resolution";
          tailf:cli-compact-syntax;
          uses sntp-server-grouping;
        }
        list vrf {
          tailf:info
            "VPN Routing/Forwarding Information";
          tailf:cli-suppress-mode;
          tailf:cli-delete-when-empty;
          tailf:cli-compact-syntax;
          tailf:cli-reset-container;
          tailf:cli-incomplete-command;
          key "name";
          leaf name {
            type string {
              tailf:info
                "WORD;;VPN Routing/Forwarding instance name";
            }
          }
          uses sntp-server-grouping;
        }
      }
      container broadcast {
        tailf:info
          "Configure SNTP broadcast services";
        leaf client {
          tailf:info
            "Enable SNTP broadcast client mode";
          type empty;
        }
      }
      container multicast {
        tailf:info
          "Configure SNTP multicast services";
        container client {
          tailf:info
            "Enable SNTP multicast client mode";
          tailf:cli-delete-when-empty;
          tailf:cli-reset-container;
          presence "true";
          leaf address {
            tailf:cli-drop-node-name;
            type union {
              type inet:ipv4-address {
                tailf:info
                  "A.B.C.D;;Multicast client IP address";
              }
              type inet:ipv6-address {
                tailf:info
                  "X:X:X:X::X;;Multicast client IPv6 address";
              }
            }
          }
        }
      }
      container source-interface {
        tailf:info
          "Configure interface for source address";
        uses interface-name-grouping;
      }
    }
    container ptp {
      tailf:ncs-device-type "cli-ned";
      tailf:display-when "not(../../ncs:module) or ../../ncs:module[ncs:name='tailf-ned-cisco-ios']";
      tailf:info
        "Precision Time Protocol";
      container clock {
        tailf:info
          "Configure PTP clock";
        container ordinary {
          tailf:info
            "Configure PTP Ordinary clock";
          list domain {
            tailf:info
              "PTP domain";
            tailf:cli-mode-name "config-ptp-clk";
            key "id";
            max-elements 1;
            leaf id {
              type uint8 {
                tailf:info
                  "<0-127>;;Domain number";
                range "0..127";
              }
            }
            leaf hybrid {
              tailf:info
                "Hybrid Mode";
              tailf:cli-hide-in-submode;
              type empty;
            }
            list clock-port {
              tailf:info
                "Configure clock port";
              tailf:cli-mode-name "config-ptp-port";
              key "name mode";
              max-elements 1;
              leaf name {
                type string {
                  tailf:info
                    "WORD;;Port name";
                }
              }
              leaf mode {
                type enumeration {
                  enum "master" {
                    tailf:info
                      "Configure as Master";
                  }
                  enum "slave" {
                    tailf:info
                      "Configure as Slave";
                  }
                }
              }
              container transport {
                tailf:info
                  "Set port transport parameters";
                tailf:cli-compact-syntax;
                tailf:cli-sequence-commands {
                  tailf:cli-reset-siblings;
                }
                leaf proto {
                  tailf:cli-drop-node-name;
                  tailf:cli-incomplete-command;
                  type enumeration {
                    enum "ethernet" {
                      tailf:info
                        "Use Ethernet encapsulation";
                    }
                    enum "ipv4" {
                      tailf:info
                        "Use IPv4 encapsulation";
                    }
                  }
                }
                leaf unicast {
                  tailf:info
                    "Use unicast communication channel";
                  type empty;
                }
                leaf interface {
                  tailf:info
                    "Transport interface";
                  when "../proto = 'ipv4'" {
                    tailf:xpath-root 3;
                  }
                  type string {
                    tailf:info
                      "WORD;;Abbreviated interface name";
                  }
                }
                leaf negotiation {
                  tailf:info
                    "Enable unicast negotiation";
                  type empty;
                }
              }
              container clock {
                tailf:info
                  "Set clock parameters";
                leaf source {
                  tailf:info
                    "Local clock address";
                  type string {
                    tailf:info
                      "WORD;;MAC/IP address";
                  }
                }
              }
            }
          }
        }
      }
    }
    container mac-address-table {
      tailf:ncs-device-type "cli-ned";
      tailf:display-when "not(../../ncs:module) or ../../ncs:module[ncs:name='tailf-ned-cisco-ios']";
      tailf:info
        "Configure the MAC address table";
      container notification {
        tailf:info
          "Enable a Notification feature";
        leaf mac-move {
          tailf:info
            "Enable Mac Move Notification";
          type empty;
        }
      }
      container limit {
        list bdomain {
          tailf:cli-suppress-mode;
          tailf:cli-delete-when-empty;
          tailf:cli-compact-syntax;
          key "id";
          leaf id {
            type uint16;
          }
          leaf maximum {
            type uint16;
          }
          leaf action {
            type enumeration {
              enum "warning";
              enum "limit";
              enum "shutdown";
            }
          }
          leaf flood {
            type empty;
          }
        }
      }
    }
    container no {
      tailf:ncs-device-type "cli-ned";
      tailf:display-when "not(../../ncs:module) or ../../ncs:module[ncs:name='tailf-ned-cisco-ios']";
      container mac-address-table {
        tailf:info
          "Configure the MAC address table";
        container learning {
          tailf:info
            "Enable a MAC table learning feature";
          list vlan {
            tailf:info
              "Layer 2 table learning per VLAN";
            tailf:cli-suppress-mode;
            tailf:cli-delete-when-empty;
            key "id";
            leaf id {
              type uint16 {
                tailf:info
                  "<1-4094>;;VLAN ID";
                range "1..4094";
              }
            }
            leaf module {
              tailf:info
                "Layer 2 table learning per VLAN per module";
              type uint8 {
                tailf:info
                  "<1-9>;;Module";
                range "1..9";
              }
            }
          }
        }
      }
    }
    container privilege {
      tailf:ncs-device-type "cli-ned";
      tailf:display-when "not(../../ncs:module) or ../../ncs:module[ncs:name='tailf-ned-cisco-ios']";
      tailf:info
        "Command privilege parameters";
      container exec {
        tailf:info
          "Exec mode";
        list level {
          tailf:info
            "Set privilege level of command";
          tailf:cli-suppress-mode;
          tailf:cli-delete-when-empty;
          tailf:cli-compact-syntax;
          tailf:cli-incomplete-command;
          tailf:cli-no-key-completion;
          key "privilege";
          leaf privilege {
            tailf:cli-incomplete-command;
            tailf:cli-incomplete-no;
            tailf:cli-suppress-range;
            type uint8 {
              tailf:info
                "<0-15>;;Privilege level";
            }
          }
          list command-list {
            tailf:cli-suppress-mode;
            tailf:cli-delete-when-empty;
            tailf:cli-drop-node-name;
            tailf:cli-compact-syntax;
            tailf:cli-show-long-obu-diffs;
            tailf:cli-no-key-completion;
            tailf:cli-suppress-key-abbreviation;
            tailf:cli-no-match-completion;
            ordered-by user;
            key "command";
            leaf command {
              tailf:cli-drop-node-name;
              tailf:cli-multi-word-key;
              type string {
                tailf:info
                  "LINE;;Initial keywords of the command to modify";
              }
            }
          }
        }
      }
    }
    container spanning-tree {
      tailf:ncs-device-type "cli-ned";
      tailf:display-when "not(../../ncs:module) or ../../ncs:module[ncs:name='tailf-ned-cisco-ios']";
      tailf:info
        "Spanning Tree Subsystem";
      container etherchannel {
        tailf:info
          "Spanning tree etherchannel specific configuration";
        container guard {
          tailf:info
            "Configure guard features for etherchannel";
          leaf misconfig {
            tailf:info
              "Enable guard to protect against etherchannel misconfiguration";
            type empty;
          }
        }
      }
      container extend {
        tailf:info
          "Spanning Tree 802.1t extensions";
        leaf system-id {
          tailf:info
            "Extend system-id into priority portion of the bridge id (PVST & Rapid PVST only)";
          type empty;
        }
      }
      container loopguard {
        tailf:info
          "Spanning tree loopguard options";
        leaf default {
          tailf:info
            "Enable loopguard by default on all ports";
          type empty;
        }
      }
      container mst {
        tailf:info
          "Multiple spanning tree configuration";
        list instance-range {
          tailf:cli-suppress-mode;
          tailf:cli-delete-when-empty;
          tailf:cli-drop-node-name;
          tailf:cli-compact-syntax;
          tailf:cli-range-list-syntax;
          key "id";
          leaf id {
            type uint16;
          }
          leaf priority {
            tailf:info
              "Set the bridge priority for the spanning tree";
            type uint16 {
              tailf:info
                "<0-61440>;;bridge priority in increments of 4096";
              range "0..61440";
            }
          }
        }
        container configuration {
          tailf:info
            "Enter MST configuration submode";
          tailf:cli-add-mode;
          tailf:cli-mode-name "config-mst";
          leaf name {
            tailf:info
              "Set configuration name";
            type string {
              tailf:info
                "WORD;;Configuration name";
            }
          }
          list instance {
            tailf:info
              "Map vlans to an MST instance";
            tailf:cli-suppress-mode;
            tailf:cli-delete-when-empty;
            key "id";
            leaf id {
              type uint16 {
                tailf:info
                  "<0-4094>;;MST instance id";
                range "0..4094";
              }
            }
            leaf-list vlan {
              tailf:info
                "Range of vlans to add to the instance mapping";
              tailf:cli-range-list-syntax;
              type uint16 {
                tailf:info
                  "LINE;;vlan range ex: 1-65, 72, 300 -200";
              }
            }
          }
        }
      }
      container optimize {
        container bpdu {
          leaf transmission {
            tailf:cli-boolean-no;
            tailf:cli-show-no;
            type boolean;
          }
        }
      }
      container portfast {
        tailf:info
          "Spanning tree portfast options";
        tailf:cli-compact-syntax;
        tailf:cli-sequence-commands {
          tailf:cli-reset-siblings;
        }
        leaf bdpu {
          tailf:cli-drop-node-name;
          tailf:cli-optional-in-sequence;
          type enumeration {
            enum "bpdufilter" {
              tailf:info
                "Enable portfast bdpu filter on this switch";
            }
            enum "bpduguard" {
              tailf:info
                "Enable portfast bpdu guard on this switch";
            }
          }
        }
        leaf default {
          tailf:info
            "Enable portfast by default on all access ports";
          type empty;
        }
      }
      leaf mode {
        tailf:info
          "Spanning tree operating mode";
        tailf:cli-full-command;
        type enumeration {
          enum "mst" {
            tailf:info
              "Multiple spanning tree mode";
          }
          enum "pvst" {
            tailf:info
              "Per-Vlan spanning tree mode";
          }
          enum "rapid-pvst" {
            tailf:info
              "Per-Vlan rapid spanning tree mode";
          }
        }
      }
      container vlans-max-age {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf max-age {
            tailf:info
              "Set the max age interval for the spanning tree";
            type uint8 {
              tailf:info
                "<6-40>;;maximum number of seconds the information in a BPDU is valid";
              range "6..40";
            }
          }
        }
      }
      container vlans-forward-time {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf forward-time {
            tailf:info
              "Set the forward delay for the spanning tree";
            type uint8 {
              tailf:info
                "<4-30>;;number of seconds for the forward delay timer";
              range "4..30";
            }
          }
        }
      }
      container vlans-hello-time {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf hello-time {
            tailf:info
              "Set the hello interval for the spanning tree";
            type uint8 {
              tailf:info
                "<1-10>;;number of seconds between generation of config BPDUs";
              range "1..10";
            }
          }
        }
      }
      container vlans-priority {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf priority {
            tailf:info
              "Set the bridge priority for the spanning tree";
            type uint16 {
              tailf:info
                "<0-61440>;;bridge priority in increments of 4096";
              range "0..61440";
            }
          }
        }
      }
      container vlans-root {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          container root {
            tailf:info
              "Configure switch as root";
            container primary {
              tailf:info
                "Configure this switch as primary root for this spanning tree";
              tailf:cli-compact-syntax;
              tailf:cli-sequence-commands {
                tailf:cli-reset-siblings;
              }
              leaf diameter {
                tailf:info
                  "Network diameter of this spanning tree";
                type uint8 {
                  tailf:info
                    "<2-7>;;Maximum number of bridges between any two end nodes";
                  range "2..7";
                }
              }
              leaf hello-time {
                tailf:info
                  "Hello interval for this spanning tree";
                type uint8 {
                  tailf:info
                    "<1-10>;;Hello interval in seconds";
                  range "1..10";
                }
              }
            }
            container secondary {
              tailf:info
                "Configure switch as secondary root";
              tailf:cli-compact-syntax;
              tailf:cli-sequence-commands {
                tailf:cli-reset-siblings;
              }
              leaf diameter {
                tailf:info
                  "Network diameter of this spanning tree";
                type uint8 {
                  tailf:info
                    "<2-7>;;Maximum number of bridges between any two end nodes";
                  range "2..7";
                }
              }
              leaf hello-time {
                tailf:info
                  "Hello interval for this spanning tree";
                type uint8 {
                  tailf:info
                    "<1-10>;;Hello interval in seconds";
                  range "1..10";
                }
              }
            }
          }
        }
      }
    }
    container dot1x {
      tailf:ncs-device-type "cli-ned";
      tailf:display-when "not(../../ncs:module) or ../../ncs:module[ncs:name='tailf-ned-cisco-ios']";
      tailf:info
        "IEEE 802.1X Global Configuration Commands";
      container critical {
        tailf:info
          "Set 802.1x Critical Authentication parameters";
        leaf eapol {
          tailf:info
            "Send EAPOL-Success on successful Critical Authentication";
          type empty;
        }
        container recovery {
          tailf:info
            "Set 802.1x Critical Authentication Recovery parameters";
          leaf delay {
            tailf:info
              "Set 802.1x Critical Authentication Recovery Delay period";
            type uint16 {
              tailf:info
                "<1-10000>;;802.1x Critical Authentication Recovery delay in milliseconds";
              range "1..10000";
            }
          }
        }
      }
      leaf system-auth-control {
        tailf:info
          "Enable or Disable SysAuthControl";
        type empty;
      }
    }
    container power {
      tailf:ncs-device-type "cli-ned";
      tailf:display-when "not(../../ncs:module) or ../../ncs:module[ncs:name='tailf-ned-cisco-ios']";
      tailf:info
        "Power configure";
      leaf redundancy-mode {
        tailf:info
          "set power supply redundancy mode";
        type enumeration {
          enum "combined" {
            tailf:info
              "combine power supply outputs (no redundancy)";
          }
          enum "redundant" {
            tailf:info
              "either power supply can operate system (redundancy)";
          }
        }
      }
    }
    container parameter-map {
      tailf:ncs-device-type "cli-ned";
      tailf:display-when "not(../../ncs:module) or ../../ncs:module[ncs:name='tailf-ned-cisco-ios']";
      tailf:info
        "parameter map";
      container type {
        tailf:info
          "parameter map type";
        list inspect {
          tailf:info
            "inspect parameter-map";
          tailf:cli-mode-name "config-profile";
          key "name";
          leaf name {
            type string {
              tailf:info
                "WORD;;parameter-map name";
            }
          }
          leaf alert {
            tailf:info
              "Turn on/off alert";
            type enumeration {
              enum "off" {
                tailf:info
                  "Turn off alert";
              }
              enum "on" {
                tailf:info
                  "Turn on alert";
              }
            }
          }
          leaf audit-trail {
            tailf:info
              "Turn on/off audit trail";
            type enumeration {
              enum "off" {
                tailf:info
                  "Turn off audit trail";
              }
              enum "on" {
                tailf:info
                  "Turn on audit trail";
              }
            }
          }
          leaf dns-timeout {
            tailf:info
              "Specify timeout for DNS";
            type uint32 {
              tailf:info
                "<1-2147483>;;Timeout in seconds";
              range "1..2147483";
            }
          }
          container icmp {
            tailf:info
              "Config timeout values for icmp";
            leaf idle-time {
              tailf:info
                "Specify timeout for icmp";
              type uint32 {
                tailf:info
                  "<1-2147483>;;Timeout in seconds";
                range "1..2147483";
              }
            }
          }
          container max-incomplete {
            tailf:info
              "Specify maximum number of incomplete connections before clamping";
            leaf high {
              tailf:info
                "Specify high-watermark for clamping";
              type uint32 {
                tailf:info
                  "<1-2147483647>;;Number of connections";
                range "1..2147483647";
              }
            }
            leaf low {
              tailf:info
                "Specify low-watermark for clamping";
              type uint32 {
                tailf:info
                  "<1-2147483647>;;Number of connections";
                range "1..2147483647";
              }
            }
          }
          container one-minute {
            tailf:info
              "Specify one-minute-sample watermarks for clamping";
            leaf high {
              tailf:info
                "Specify high-watermark for clamping";
              type uint32 {
                tailf:info
                  "<1-2147483647>;;Number of connections";
                range "1..2147483647";
              }
            }
            leaf low {
              tailf:info
                "Specify low-watermark for clamping";
              type uint32 {
                tailf:info
                  "<1-2147483647>;;Number of connections";
                range "1..2147483647";
              }
            }
          }
          container sessions {
            tailf:info
              "Maximum number of inspect sessions";
            leaf maximum {
              tailf:info
                "Maximum sessions";
              type uint32 {
                tailf:info
                  "<1-2147483647>;;Number of sessions";
                range "1..2147483647";
              }
            }
          }
          container tcp {
            tailf:info
              "Config timeout values for tcp connections";
            leaf finwait-time {
              tailf:info
                "Specify timeout for TCP connections after a FIN";
              type uint32 {
                tailf:info
                  "<1-2147483>;;Timeout in seconds";
                range "1..2147483";
              }
            }
            leaf idle-time {
              tailf:info
                "Specify idle timeout for tcp connections";
              type uint32 {
                tailf:info
                  "<1-2147483>;;Timeout in seconds";
                range "1..2147483";
              }
            }
            container max-incomplete {
              tailf:info
                "Specify max half-open connection per host";
              leaf host {
                tailf:info
                  "Specify max half-open connection per host";
                type uint32 {
                  tailf:info
                    "<1-4294967295>;;half-open sessions";
                  range "1..4294967295";
                }
              }
            }
            leaf synwait-time {
              tailf:info
                "Specify timeout for TCP connections after a SYN and no";
              type uint32 {
                tailf:info
                  "<1-2147483>;;Timeout in seconds";
                range "1..2147483";
              }
            }
          }
          container udp {
            tailf:info
              "Config timeout values for udp flows";
            leaf idle-time {
              tailf:info
                "Specify idle timeout for udp";
              type uint32 {
                tailf:info
                  "<1-2147483>;;Timeout in seconds";
                range "1..2147483";
              }
            }
          }
        }
      }
    }
    container vpdn {
      tailf:ncs-device-type "cli-ned";
      tailf:display-when "not(../../ncs:module) or ../../ncs:module[ncs:name='tailf-ned-cisco-ios']";
      tailf:info
        "Virtual Private Dialup Network";
      leaf authen-before-forward {
        tailf:info
          "Authenticate a user locally before tunnelling";
        type empty;
      }
      leaf enable {
        tailf:info
          "Enable VPDN";
        type empty;
      }
      leaf-list search-order {
        ordered-by user;
        tailf:info
          "Configure the order to search different VPDN tunnel types";
        type enumeration {
          enum "dnis" {
            tailf:info
              "Tunnel based on DNIS";
          }
          enum "domain" {
            tailf:info
              "Tunnel based on domain";
          }
          enum "multihop-hostname" {
            tailf:info
              "Tunnel based on peer hostname from ingress tunnel";
          }
        }
      }
    }
    container bba-group {
      tailf:ncs-device-type "cli-ned";
      tailf:display-when "not(../../ncs:module) or ../../ncs:module[ncs:name='tailf-ned-cisco-ios']";
      tailf:info
        "Configure BBA Group";
      list pppoe {
        tailf:info
          "PPPoE type";
        key "id";
        leaf id {
          type union {
            type string {
              tailf:info
                "WORD;;BBA Group name";
            }
            type enumeration {
              enum "global" {
                tailf:info
                  "PPPoE global group";
              }
            }
          }
        }
        container vendor-tag {
          tailf:info
            "PPPoE Vendor Specific Tag";
          container circuit-id {
            tailf:info
              "Circuit-Id";
            leaf service {
              tailf:info
                "Enable processing";
              type empty;
            }
          }
          container dsl-sync-rate {
            tailf:info
              "DSL-Sync-Rate";
            leaf service {
              tailf:info
                "Enable processing";
              type empty;
            }
          }
          container remote-id {
            tailf:info
              "Remote-Id";
            leaf service {
              tailf:info
                "Enable processing";
              type empty;
            }
          }
          leaf strip {
            tailf:info
              "Strip all vendor tags";
            type empty;
          }
        }
        leaf virtual-template {
          tailf:info
            "BBA virtual template command";
          type uint16 {
            tailf:info
              "<1-4095>;;Virtual Template interface number";
            range "1..4095";
          }
        }
      }
    }
    container mac {
      tailf:ncs-device-type "cli-ned";
      tailf:display-when "not(../../ncs:module) or ../../ncs:module[ncs:name='tailf-ned-cisco-ios']";
      tailf:info
        "Global MAC configuration subcommands";
      container access-list {
        tailf:info
          "Named access-list";
        list extended {
          tailf:info
            "Extended Access List";
          key "id";
          leaf id {
            type string {
              tailf:info
                "WORD;;access-list name";
            }
          }
          container deny {
            tailf:info
              "Specify packets to reject";
            tailf:cli-compact-syntax;
            tailf:cli-sequence-commands;
            container source {
              tailf:cli-flatten-container;
              tailf:cli-compact-syntax;
              tailf:cli-drop-node-name;
              choice target-choice {
                leaf any {
                  tailf:info
                    "any source MAC address";
                  type empty;
                }
                leaf host {
                  tailf:info
                    "A single source host";
                  type string {
                    tailf:info
                      "H.H.H;;48-bit source MAC address";
                  }
                }
              }
            }
            container dest {
              tailf:cli-flatten-container;
              tailf:cli-compact-syntax;
              tailf:cli-drop-node-name;
              choice target-choice {
                leaf any {
                  tailf:info
                    "any destination MAC address";
                  type empty;
                }
                leaf host {
                  tailf:info
                    "A single destination host";
                  type string {
                    tailf:info
                      "H.H.H;;48-bit destination MAC address";
                  }
                }
              }
            }
          }
          container permit {
            tailf:info
              "Specify packets to forward";
            tailf:cli-compact-syntax;
            tailf:cli-sequence-commands;
            container source {
              tailf:cli-flatten-container;
              tailf:cli-compact-syntax;
              tailf:cli-drop-node-name;
              choice target-choice {
                leaf any {
                  tailf:info
                    "any source MAC address";
                  type empty;
                }
                leaf host {
                  tailf:info
                    "A single source host";
                  type string {
                    tailf:info
                      "H.H.H;;48-bit source MAC address";
                  }
                }
              }
            }
            container dest {
              tailf:cli-flatten-container;
              tailf:cli-compact-syntax;
              tailf:cli-drop-node-name;
              choice target-choice {
                leaf any {
                  tailf:info
                    "any destination MAC address";
                  type empty;
                }
                leaf host {
                  tailf:info
                    "A single destination host";
                  type string {
                    tailf:info
                      "H.H.H;;48-bit destination MAC address";
                  }
                }
              }
            }
          }
        }
      }
    }
    container tacacs-server {
      tailf:ncs-device-type "cli-ned";
      tailf:display-when "not(../../ncs:module) or ../../ncs:module[ncs:name='tailf-ned-cisco-ios']";
      tailf:info
        "Modify TACACS query parameters";
      list host {
        tailf:info
          "Specify a TACACS server";
        tailf:cli-suppress-mode;
        tailf:cli-delete-when-empty;
        tailf:cli-compact-syntax;
        tailf:cli-reset-container;
        key "name";
        leaf name {
          type host-type {
            tailf:info
              "Hostname or A.B.C.D;;IP address of TACACS server";
          }
        }
        leaf port {
          tailf:info
            "TCP port for TACACS+ server (default is 49)";
          type uint16 {
            tailf:info
              "<1-65535>;;Port number";
            range "1..65535";
          }
        }
        leaf timeout {
          tailf:info
            "Time to wait for this TACACS server to reply (overrides default)";
          type uint16 {
            tailf:info
              "<1-1000>;;Timeout value in seconds to wait for server to reply";
            range "1..1000";
          }
        }
        container key {
          tailf:info
            "per-server encryption key (overrides default)";
          tailf:cli-flatten-container;
          tailf:cli-compact-syntax;
          tailf:cli-sequence-commands {
            tailf:cli-reset-siblings;
          }
          tailf:cli-incomplete-command;
          leaf encryption {
            tailf:cli-drop-node-name;
            tailf:cli-optional-in-sequence;
            type enumeration {
              enum "0" {
                tailf:info
                  "Specifies an UNENCRYPTED key will follow";
              }
              enum "7" {
                tailf:info
                  "Specifies HIDDEN key will follow";
              }
            }
          }
          leaf key {
            tailf:cli-drop-node-name;
            tailf:cli-full-command;
            tailf:cli-multi-value;
            type string {
              tailf:info
                "LINE;;The UNENCRYPTED (cleartext) shared key";
            }
          }
        }
      }
      leaf timeout {
        tailf:info
          "Time to wait for a TACACS server to reply";
        type uint16 {
          tailf:info
            "<1-1000>;;Wait time (default 5 seconds)";
          range "1..1000";
        }
        default "5";
      }
      container directed-request {
        tailf:info
          "Allow user to specify tacacs server to use with `@server'";
        tailf:cli-compact-syntax;
        tailf:cli-sequence-commands;
        presence "true";
        leaf restricted {
          tailf:info
            "restrict queries to directed request servers only";
          tailf:cli-optional-in-sequence;
          type empty;
        }
        leaf no-truncate {
          tailf:info
            "Do not truncate the @hostname from username.";
          type empty;
        }
      }
      container key {
        tailf:info
          "Set TACACS+ encryption key.";
        tailf:cli-compact-syntax;
        tailf:cli-sequence-commands {
          tailf:cli-reset-siblings;
        }
        tailf:cli-incomplete-command;
        leaf encryption {
          tailf:cli-drop-node-name;
          tailf:cli-optional-in-sequence;
          type enumeration {
            enum "0" {
              tailf:info
                "Specifies an UNENCRYPTED key will follow";
            }
            enum "7" {
              tailf:info
                "Specifies HIDDEN key will follow";
            }
          }
        }
        leaf key {
          tailf:cli-drop-node-name;
          tailf:cli-full-command;
          tailf:cli-multi-value;
          type string {
            tailf:info
              "LINE;;The UNENCRYPTED (cleartext) shared key";
          }
        }
      }
    }
    container udld {
      tailf:ncs-device-type "cli-ned";
      tailf:display-when "not(../../ncs:module) or ../../ncs:module[ncs:name='tailf-ned-cisco-ios']";
      tailf:info
        "Configure global UDLD setting";
      leaf aggressive {
        tailf:info
          "Enable UDLD protocol in aggressive mode on fiber ports except where locally configured";
        type empty;
      }
      container message {
        tailf:info
          "Set UDLD message parameters";
        leaf time {
          tailf:info
            "Set UDLD message time period";
          type uint8 {
            tailf:info
              "<7-90>;;Time in seconds between sending of messages in steady state";
            range "7..90";
          }
        }
      }
    }
    container vtp {
      tailf:ncs-device-type "cli-ned";
      tailf:display-when "not(../../ncs:module) or ../../ncs:module[ncs:name='tailf-ned-cisco-ios']";
      tailf:info
        "Configure global VTP state";
      leaf file {
        tailf:info
          "Configure IFS filesystem file where VTP configuration is stored.";
        type string {
          tailf:info
            "WORD;;The ascii name of the IFS filesystem file where VTP configuration is stored.";
        }
      }
      leaf interface {
        tailf:info
          "Configure interface as the preferred source for the VTP IP updater address.";
        type string {
          tailf:info
            "WORD;;The name of the interface providing the VTP updater ID for this device.";
        }
      }
      leaf password {
        tailf:info
          "Set the password for the VTP administrative domain";
        type string {
          tailf:info
            "WORD;;The ascii password for the VTP administrative domain.";
        }
      }
      leaf pruning {
        tailf:info
          "Set the adminstrative domain to permit pruning";
        type empty;
      }
      leaf version {
        tailf:info
          "Set the adminstrative domain to VTP version";
        type uint8 {
          tailf:info
            "<1-3>;;Set the adminstrative domain VTP version number";
          range "1..3";
        }
      }
      leaf domain {
        tailf:info
          "Set the name of the VTP administrative domain.";
        type string;
      }
      leaf mode {
        tailf:info
          "Configure VTP device mode";
        type enumeration {
          enum "client" {
            tailf:info
              "Set the device to client mode.";
          }
          enum "off" {
            tailf:info
              "Set the device to off mode.";
          }
          enum "server" {
            tailf:info
              "Set the device to server mode.";
          }
          enum "transparent" {
            tailf:info
              "Set the device to transparent mode.";
          }
        }
      }
    }
    container rep {
      tailf:ncs-device-type "cli-ned";
      tailf:display-when "not(../../ncs:module) or ../../ncs:module[ncs:name='tailf-ned-cisco-ios']";
      tailf:info
        "Resilient Ethernet Protocol characteristics";
      container admin {
        tailf:info
          "administrative configuration";
        list vlan {
          tailf:info
            "VLAN";
          key "name";
          leaf name {
            type uint16 {
              tailf:info
                "<2-4094>;;between 2 and 4094";
              range "2..4094";
            }
          }
        }
      }
    }
    container xconnect {
      tailf:ncs-device-type "cli-ned";
      tailf:display-when "not(../../ncs:module) or ../../ncs:module[ncs:name='tailf-ned-cisco-ios']";
      tailf:info
        "Xconnect config commands";
      container logging {
        tailf:info
          "Configure logging flags";
        container pseudowire {
          tailf:info
            "pseudowire status transition logging";
          leaf status {
            tailf:info
              "pseudowire status up/down logging";
            tailf:cli-full-command;
            type empty;
          }
        }
        leaf redundancy {
          tailf:info
            "xconnect redundancy events";
          tailf:cli-full-command;
          type empty;
        }
      }
    }
    container fabric {
      tailf:ncs-device-type "cli-ned";
      tailf:display-when "not(../../ncs:module) or ../../ncs:module[ncs:name='tailf-ned-cisco-ios']";
      tailf:info
        "Catalyst 6000 crossbar fabric configuration commands";
      container switching-mode {
        tailf:info
          "Switching mode settings";
        container allow {
          tailf:info
            "Allow settings";
          choice allow-choice {
            leaf bus-mode {
              tailf:info
                "Allow switching in bus mode for modules";
              type empty;
            }
            container truncated {
              tailf:info
                "Truncated switching mode";
              presence "true";
              leaf threshold {
                tailf:info
                  "Number of SFM-capable modules for truncated switching mode. Switch applies the threshold only when the mode is disallowed. Switch ignores the threshold when the truncated mode is allowed";
                type uint8 {
                  tailf:info
                    "<1-9>;;Threshold for truncated switching mode.";
                  range "1..9";
                }
              }
            }
          }
        }
        container force {
          tailf:info
            "Force modules to different switching modes";
          leaf bus-mode {
            tailf:info
              "Switching mode of service modules will be forced to bus-mode by powercycling it.";
            type empty;
          }
        }
      }
    }
    container port-channel {
      tailf:ncs-device-type "cli-ned";
      tailf:display-when "not(../../ncs:module) or ../../ncs:module[ncs:name='tailf-ned-cisco-ios']";
      tailf:info
        "EtherChannel configuration";
      leaf load-balance {
        tailf:info
          "Load Balancing method";
        type enumeration {
          enum "dst-ip" {
            tailf:info
              "Dst IP Addr";
          }
          enum "dst-mac" {
            tailf:info
              "Dst Mac Addr";
          }
          enum "dst-mixed-ip-port" {
            tailf:info
              "Dst IP Addr and TCP/UDP Port";
          }
          enum "dst-port" {
            tailf:info
              "Dst TCP/UDP Port";
          }
          enum "mpls" {
            tailf:info
              "Load Balancing for MPLS packets";
          }
          enum "src-dst-ip" {
            tailf:info
              "Src XOR Dst IP Addr";
          }
          enum "src-dst-mac" {
            tailf:info
              "Src XOR Dst Mac Addr";
          }
          enum "src-dst-mixed-ip-port" {
            tailf:info
              "Src XOR Dst IP Addr and TCP/UDP Port";
          }
          enum "src-dst-port" {
            tailf:info
              "Src XOR Dst TCP/UDP Port";
          }
          enum "src-ip" {
            tailf:info
              "Src IP Addr";
          }
          enum "src-mac" {
            tailf:info
              "Src Mac Addr";
          }
          enum "src-mixed-ip-port" {
            tailf:info
              "Src IP Addr and TCP/UDP Port";
          }
          enum "src-port" {
            tailf:info
              "Src TCP/UDP Port";
          }
        }
      }
      leaf load-balance-hash-algo {
        tailf:info
          "Algorithm selection for FBLB";
        type string;
      }
    }
    container l2 {
      tailf:ncs-device-type "cli-ned";
      tailf:display-when "not(../../ncs:module) or ../../ncs:module[ncs:name='tailf-ned-cisco-ios']";
      tailf:info
        "Layer 2 configuration";
      list vfi {
        tailf:info
          "Configure a virtual forwarding instance";
        tailf:cli-mode-name "config-vfi";
        tailf:cli-compact-syntax;
        key "name";
        leaf name {
          type string {
            tailf:info
              "WORD;;VFI name";
          }
        }
        leaf point-to-point {
          tailf:info
            "Point-to-point configuration mode";
          tailf:cli-hide-in-submode;
          tailf:cli-full-command;
          type empty;
        }
        leaf manual {
          tailf:info
            "Multipoint manual configuration mode";
          tailf:cli-hide-in-submode;
          tailf:cli-full-command;
          type empty;
        }
        container vpn {
          tailf:info
            "VPN configuration";
          leaf id {
            tailf:info
              "VPN id";
            type uint32 {
              tailf:info
                "<1-4294967295>;;VPN id value";
              range "1..4294967295";
            }
          }
        }
        leaf bridge-domain {
          tailf:info
            "Bridge Domain";
          type uint16 {
            tailf:info
              "<1-8000>;;Bridge Domain ID value";
            range "1..8000";
          }
        }
        leaf mtu {
          tailf:cli-full-command;
          type uint16;
        }
        list neighbor {
          tailf:cli-suppress-mode;
          tailf:cli-delete-when-empty;
          tailf:cli-compact-syntax;
          tailf:cli-sequence-commands {
            tailf:cli-reset-all-siblings;
          }
          tailf:cli-incomplete-command;
          key "id";
          leaf id {
            type inet:ipv4-address {
              tailf:info
                "A.B.C.D;;VFI neighbor's router id";
            }
          }
          leaf vcid {
            tailf:cli-drop-node-name;
            tailf:cli-optional-in-sequence;
            tailf:cli-incomplete-command;
            type uint32 {
              tailf:info
                "<1-4294967295>;;Enter VC ID value";
              range "1..4294967295";
            }
          }
          leaf encapsulation {
            tailf:info
              "Connection encapsulation type";
            tailf:cli-optional-in-sequence;
            type enumeration {
              enum "mpls" {
                tailf:info
                  "Use MPLS encapsulation";
              }
              enum "l2tpv3" {
                tailf:info
                  "Use L2TPv3 encapsulation";
              }
            }
          }
          leaf pw-class {
            tailf:info
              "Pseudowire-class configuration";
            tailf:cli-optional-in-sequence;
            type string {
              tailf:info
                "WORD;;Pseudowire-class name";
            }
          }
          leaf no-split-horizon {
            tailf:info
              "Disable split-horizon forwarding";
            type empty;
          }
        }
      }
    }
    container l2protocol-tunnel {
      tailf:ncs-device-type "cli-ned";
      tailf:display-when "not(../../ncs:module) or ../../ncs:module[ncs:name='tailf-ned-cisco-ios']";
      tailf:info
        "Tunnel Layer2 protocols";
      leaf cos {
        tailf:info
          "Class of Service";
        type uint8 {
          tailf:info
            "<0-7>;;priority value";
          range "0..7";
        }
      }
      container global {
        tailf:info
          "Global settings";
        leaf drop-threshold {
          tailf:info
            "L2PT packets drop threshold";
          type uint16 {
            tailf:info
              "<100-20000>;;Packets per second";
            range "100..20000";
          }
        }
      }
    }
    container l2vpn {
      tailf:ncs-device-type "cli-ned";
      tailf:display-when "not(../../ncs:module) or ../../ncs:module[ncs:name='tailf-ned-cisco-ios']";
      tailf:info
        "Layer2 VPN commands";
      tailf:cli-add-mode;
      presence "true";
    }
    container l2vpn-vfi {
      tailf:ncs-device-type "cli-ned";
      tailf:display-when "not(../../ncs:module) or ../../ncs:module[ncs:name='tailf-ned-cisco-ios']";
      tailf:cli-drop-node-name;
      container l2vpn {
        container vfi {
          tailf:info
            "Configure a Virtual Forwarding Instance (VFI)";
          list context {
            tailf:info
              "Layer2 VPN Context";
            tailf:cli-mode-name "config-vfi";
            key "name";
            leaf name {
              type string {
                tailf:info
                  "WORD;;Virtual Forwarding Instance (VFI) name";
              }
            }
            container vpn {
              tailf:info
                "VPN configuration";
              leaf id {
                tailf:info
                  "VPN id";
                type uint32 {
                  tailf:info
                    "<1-4294967295>;;VPN id value";
                  range "1..4294967295";
                }
              }
            }
            container autodiscovery {
              tailf:info
                "Auto Discovery mode";
              container bgp {
                tailf:info
                  "Use BGP for neighbor discovery";
                container signaling {
                  tailf:info
                    "Signaling protocol to use";
                  container bgp {
                    tailf:info
                      "Use BGP signaling";
                    tailf:cli-add-mode;
                    tailf:cli-mode-name "config-vfi-autodiscovery";
                    container ve {
                      leaf id {
                        type uint32;
                      }
                    }
                    container route-target {
                      tailf:info
                        "Specify Route Target VPN Extended Communities";
                      uses vrf-route-target-grouping;
                    }
                  }
                }
              }
            }
            container member {
              tailf:info
                "Configure the cross connect member";
              list pseudowire {
                tailf:cli-suppress-mode;
                tailf:cli-delete-when-empty;
                tailf:cli-allow-join-with-key {
                  tailf:cli-display-joined;
                }
                key "name";
                leaf name {
                  type uint32 {
                    tailf:info
                      "<1-231072>;;Pseudowire interface number";
                    range "1..231072";
                  }
                  tailf:non-strict-leafref {
                    path "/ncs:devices/ncs:device/ncs:config/ios:interface/pseudowire/name" {
                      tailf:xpath-root 3;
                    }
                  }
                }
              }
            }
          }
        }
      }
    }
    container l2vpn-xconnect {
      tailf:ncs-device-type "cli-ned";
      tailf:display-when "not(../../ncs:module) or ../../ncs:module[ncs:name='tailf-ned-cisco-ios']";
      tailf:cli-drop-node-name;
      container l2vpn {
        tailf:info
          "Layer2 VPN commands";
        container xconnect {
          tailf:info
            "Configure a cross connect";
          list context {
            tailf:info
              "Layer2 VPN Context";
            tailf:cli-mode-name "config-xconnect";
            tailf:cli-compact-syntax;
            key "name";
            leaf name {
              type string {
                tailf:info
                  "WORD;;Configure the cross connect name";
              }
            }
            container member {
              tailf:info
                "Configure the cross connect member";
              list member-list {
                tailf:cli-drop-node-name;
                tailf:cli-suppress-mode;
                tailf:cli-delete-when-empty;
                tailf:cli-compact-syntax;
                tailf:cli-sequence-commands {
                  tailf:cli-reset-all-siblings;
                }
                key "name";
                leaf name {
                  type string {
                    tailf:info
                      "WORD;;Interface name";
                    pattern '(GigabitEthernet.*)|(Port-channel.*)|(TenGigabitEthernet.*)|(Vlan.*)|(Ethernet.*)|(FastEthernet.*)';
                  }
                }
                leaf service-instance {
                  tailf:info
                    "Ethernet Service Instance";
                  tailf:cli-optional-in-sequence;
                  type uint32 {
                    tailf:info
                      "<1-4000>;;Service Instance ID";
                  }
                }
                leaf group {
                  tailf:info
                    "Configure the cross connect member redundancy group";
                  type string {
                    tailf:info
                      "WORD;;Enter redundancy group name";
                  }
                }
                leaf priority {
                  tailf:info
                    "Configure the cross connect member priority";
                  type uint8 {
                    tailf:info
                      "<0-16>;;Enter priority number of the member (0: Highest, 16: Lowest)";
                    range "0..16";
                  }
                }
              }
              list pseudowire {
                tailf:info
                  "Pseudowire Interface";
                tailf:cli-suppress-mode;
                tailf:cli-delete-when-empty;
                tailf:cli-allow-join-with-key {
                  tailf:cli-display-joined;
                }
                key "name";
                leaf name {
                  type uint32 {
                    tailf:info
                      "<1-231072>;;Pseudowire interface number";
                    range "1..231072";
                  }
                }
              }
              list address-list {
                tailf:cli-drop-node-name;
                tailf:cli-suppress-mode;
                tailf:cli-delete-when-empty;
                tailf:cli-compact-syntax;
                tailf:cli-sequence-commands {
                  tailf:cli-reset-all-siblings;
                }
                tailf:cli-incomplete-command;
                key "name";
                leaf name {
                  type inet:ipv4-address {
                    tailf:info
                      "A.B.C.D;;IP address of the peer";
                  }
                }
                leaf vcid {
                  tailf:cli-drop-node-name;
                  tailf:cli-incomplete-command;
                  type uint32 {
                    tailf:info
                      "<1-4294967295>;;Enter VC ID value";
                    range "1..4294967295";
                  }
                }
                leaf encapsulation {
                  tailf:info
                    "Data encapsulation method";
                  type enumeration {
                    enum "mpls" {
                      tailf:info
                        "Use MPLS encapsulation";
                    }
                  }
                }
                leaf group {
                  tailf:info
                    "Configure the cross connect member redundancy group";
                  type string {
                    tailf:info
                      "WORD;;Enter redundancy group name";
                  }
                }
                leaf priority {
                  tailf:info
                    "Configure the cross connect member priority";
                  type uint8 {
                    tailf:info
                      "<0-16>;;Enter priority number of the member (0: Highest, 16: Lowest)";
                    range "0..16";
                  }
                }
              }
            }
            container redundancy {
              tailf:info
                "Xconnect redundancy information";
              leaf predictive {
                tailf:info
                  "Switch over to backup member without waiting for UP status";
                type enumeration {
                  enum "disabled" {
                    tailf:info
                      "Disable predictive switchover capability for this xconnect";
                  }
                  enum "enabled" {
                    tailf:info
                      "Enable predictive switchover capability for this xconnect";
                  }
                }
              }
              list delay {
                tailf:info
                  "Xconnect redundancy delay parameters";
                tailf:cli-suppress-mode;
                tailf:cli-delete-when-empty;
                tailf:cli-compact-syntax;
                tailf:cli-sequence-commands;
                key "group";
                leaf group {
                  tailf:info
                    "Redundancy group name";
                  tailf:cli-expose-key-name;
                  type string {
                    tailf:info
                      "Redundancy group name";
                  }
                }
                leaf enable-delay {
                  tailf:cli-drop-node-name;
                  tailf:cli-prefix-key;
                  type uint8 {
                    tailf:info
                      "<0-180>;;Enable delay";
                    range "0..180";
                  }
                }
                leaf disable-delay {
                  tailf:cli-drop-node-name;
                  tailf:cli-prefix-key;
                  type union {
                    type uint8 {
                      tailf:info
                        "<0-180>;;Disable delay";
                      range "0..180";
                    }
                    type enumeration {
                      enum "never" {
                        tailf:info
                          "Disallow disable";
                      }
                    }
                  }
                }
              }
            }
          }
        }
      }
    }
    container system {
      tailf:ncs-device-type "cli-ned";
      tailf:display-when "not(../../ncs:module) or ../../ncs:module[ncs:name='tailf-ned-cisco-ios']";
      tailf:info
        "Set the system configuration";
      container env {
        tailf:info
          "Set the system environment settings";
        container temperature {
          tailf:info
            "Set the system temperature settings";
          container threshold {
            tailf:info
              "Set the system temperature thresholds";
            leaf yellow {
              tailf:info
                "Set the yellow threshold";
              type uint8 {
                tailf:info
                  "<0-25>;;Delta value from Red threshold in Degree Celsius";
                range "0..25";
              }
            }
          }
        }
      }
      container mtu {
        tailf:info
          "Set the system Maximum Transmission Unit (MTU)";
        leaf size {
          tailf:cli-drop-node-name;
          type uint16 {
            tailf:info
              "<1500-1998>;;MTU size in bytes";
            range "1500..1998";
          }
        }
        leaf jumbo {
          tailf:info
            "Set Jumbo MTU value for GigabitEthernet or TenGigabitEthernet interfaces";
          type uint16 {
            tailf:info
              "<1500-9000>;;Jumbo MTU size in bytes";
            range "1500..9000";
          }
        }
        leaf routing {
          tailf:info
            "Set the Routing MTU for the system";
          type uint16 {
            tailf:info
              "<1500-1500>;;MTU size in bytes";
            range "1500";
          }
        }
      }
    }
    container diagnostic {
      tailf:ncs-device-type "cli-ned";
      tailf:display-when "not(../../ncs:module) or ../../ncs:module[ncs:name='tailf-ned-cisco-ios']";
      tailf:info
        "Configure diagnostic information";
      container bootup {
        tailf:info
          "Configure diagnostic for bootup";
        leaf level {
          tailf:info
            "Select diagnostic level";
          type enumeration {
            enum "complete" {
              tailf:info
                "Complete level";
            }
            enum "minimal" {
              tailf:info
                "Minimal level";
            }
          }
        }
      }
      container cns {
        tailf:info
          "Configure diagnostic cns information";
        leaf publish {
          tailf:info
            "Configure diagnostic cns publish";
          type string {
            tailf:info
              "WORD;;Diagnostic cns subject";
          }
        }
        leaf subscribe {
          tailf:info
            "Configure diagnostic cns subscribe";
          type string {
            tailf:info
              "WORD;;Diagnostic cns subject";
          }
        }
      }
    }
    container errdisable {
      tailf:ncs-device-type "cli-ned";
      tailf:display-when "not(../../ncs:module) or ../../ncs:module[ncs:name='tailf-ned-cisco-ios']";
      tailf:info
        "Error disable";
      container detect {
        tailf:info
          "Error disable detection";
        container cause {
          tailf:info
            "Enable error disable detection for application";
          leaf all {
            tailf:info
              "Enable error detection on all cases";
            tailf:cli-full-command;
            type empty;
          }
          leaf arp-inspection {
            tailf:info
              "Enable error detection for arp inspection";
            tailf:cli-full-command;
            type empty;
          }
          leaf bpduguard {
            tailf:info
              "Enable error detection on bpdu-guard";
            tailf:cli-full-command;
            type empty;
          }
          leaf dhcp-rate-limit {
            tailf:info
              "Enable error detection on dhcp-rate-limit";
            tailf:cli-full-command;
            type empty;
          }
          leaf dtp-flap {
            tailf:info
              "Enable error detection on dtp-flapping";
            tailf:cli-full-command;
            type empty;
          }
          leaf gbic-invalid {
            tailf:info
              "Enable error detection on gbic-invalid";
            tailf:cli-full-command;
            type empty;
          }
          leaf inline-power {
            tailf:info
              "Enable error detection for inline-power";
            tailf:cli-full-command;
            type empty;
          }
          leaf l2ptguard {
            tailf:info
              "Enable timer to recover from l2protocol-tunnel error disable state";
            tailf:cli-full-command;
            type empty;
          }
          leaf link-flap {
            tailf:info
              "Enable error detection on linkstate-flapping";
            tailf:cli-full-command;
            type empty;
          }
          leaf loopback {
            tailf:info
              "Enable error detection on loopback";
            tailf:cli-full-command;
            type empty;
          }
          leaf mlacp-minlink {
            tailf:cli-full-command;
            type empty;
          }
          leaf pagp-flap {
            tailf:info
              "Enable error detection on pagp-flapping";
            tailf:cli-full-command;
            type empty;
          }
          leaf pppoe-ia-rate-limit {
            tailf:info
              "Enable error detection on PPPoE IA rate-limit";
            tailf:cli-full-command;
            type empty;
          }
          leaf security-violation {
            tailf:info
              "Enable error detection on 802.1x-guard";
            tailf:cli-full-command;
            type empty;
          }
          leaf sfp-config-mismatch {
            tailf:info
              "Enable error detection on SFP config mismatch";
            tailf:cli-full-command;
            type empty;
          }
          leaf small-frame {
            tailf:info
              "Enable error detection on small_frame";
            tailf:cli-full-command;
            type empty;
          }
        }
      }
      container flap-setting {
        tailf:info
          "Error disable flap detection setting";
        container cause {
          tailf:info
            "Set error disable flap parameters for application";
          container dtp-flap {
            tailf:info
              "Set the variables related to detection of dtp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container link-flap {
            tailf:info
              "Set the variables related to detection of link flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container pagp-flap {
            tailf:info
              "Set the variables related to detection of pagp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
        }
      }
      container recovery {
        tailf:info
          "Error disable recovery";
        container cause {
          tailf:info
            "Enable error disable recovery for application";
          leaf all {
            tailf:info
              "Enable timer to recover from all error causes";
            type empty;
          }
          leaf arp-inspection {
            tailf:info
              "Enable timer to recover from arp inspection error disable state";
            type empty;
          }
          leaf bpduguard {
            tailf:info
              "Enable timer to recover from BPDU Guard error";
            type empty;
          }
          leaf channel-misconfig {
            tailf:info
              "(STP)  Enable timer to recover from channel misconfig error";
            type empty;
          }
          leaf dhcp-rate-limit {
            tailf:info
              "Enable timer to recover from dhcp-rate-limit error";
            type empty;
          }
          leaf dtp-flap {
            tailf:info
              "Enable timer to recover from dtp-flap error";
            type empty;
          }
          leaf gbic-invalid {
            tailf:info
              "Enable timer to recover from invalid GBIC error";
            type empty;
          }
          leaf inline-power {
            tailf:info
              "Enable timer to recover from inline-power error";
            type empty;
          }
          leaf l2ptguard {
            tailf:info
              "Enable timer to recover from l2protocol-tunnel error disable state";
            type empty;
          }
          leaf link-flap {
            tailf:info
              "Enable timer to recover from link-flap error";
            type empty;
          }
          leaf link-monitor-failure {
            type empty;
          }
          leaf loopback {
            tailf:info
              "Enable timer to recover from loopback error";
            type empty;
          }
          leaf mac-limit {
            tailf:info
              "Enable timer to recover from mac limit disable state";
            type empty;
          }
          leaf mlacp-minlink {
            tailf:cli-full-command;
            type empty;
          }
          container oam-remote-failure {
            tailf:cli-display-separated;
            presence "true";
            leaf critical-event {
              tailf:cli-full-command;
              type empty;
            }
            leaf dying-gasp {
              tailf:cli-full-command;
              type empty;
            }
            leaf link-fault {
              tailf:cli-full-command;
              type empty;
            }
          }
          leaf pagp-flap {
            tailf:info
              "Enable timer to recover from pagp-flap error";
            type empty;
          }
          leaf port-mode-failure {
            tailf:info
              "Enable timer to recover from port mode change failure";
            type empty;
          }
          leaf pppoe-ia-rate-limit {
            tailf:info
              "Enable timer to recover from PPPoE IA rate-limit error";
            type empty;
          }
          leaf psp {
            type empty;
          }
          leaf psecure-violation {
            tailf:info
              "Enable timer to recover from psecure violation error";
            type empty;
          }
          leaf security-violation {
            tailf:info
              "Enable timer to recover from 802.1x violation error";
            type empty;
          }
          leaf sfp-config-mismatch {
            tailf:info
              "Enable timer to recover from SFP config mismatch error";
            type empty;
          }
          leaf small-frame {
            tailf:info
              "Enable timer to recover from small frame error";
            type empty;
          }
          leaf storm-control {
            tailf:info
              "Enable timer to recover from storm-control error";
            type empty;
          }
          leaf udld {
            tailf:info
              "Enable timer to recover from udld error";
            type empty;
          }
          leaf unicast-flood {
            type empty;
          }
          leaf vmps {
            tailf:info
              "Enable timer to recover from vmps shutdown error";
            type empty;
          }
        }
        leaf interval {
          tailf:info
            "Error disable recovery timer value";
          type uint32 {
            tailf:info
              "<30-86400>;;timer-interval(sec)";
            range "30..86400";
          }
        }
      }
    }
    container monitor {
      tailf:ncs-device-type "cli-ned";
      tailf:display-when "not(../../ncs:module) or ../../ncs:module[ncs:name='tailf-ned-cisco-ios']";
      tailf:info
        "Monitoring different system events";
      list session {
        tailf:info
          "Configure a SPAN session";
        tailf:cli-suppress-mode;
        tailf:cli-delete-when-empty;
        tailf:cli-compact-syntax;
        tailf:cli-incomplete-command;
        key "id";
        leaf id {
          type uint8 {
            tailf:info
              "<1-66>;;SPAN session number";
            range "1..66";
          }
        }
        container destination {
          tailf:info
            "SPAN destination interface or VLAN";
          leaf interface {
            tailf:info
              "SPAN destination interface";
            type string;
          }
          leaf encapsulation {
            tailf:cli-hide-in-submode;
            tailf:info
              "Set encapsulation for destination interface";
            type enumeration {
              enum "dot1q" {
                tailf:info
                  "interface uses only dot1q encapsulation";
              }
              enum "isl" {
                tailf:info
                  "interface uses only isl encapsulation";
              }
              enum "replicate" {
                tailf:info
                  "interface replicates source encapsulation";
              }
            }
          }
          leaf ingress {
            tailf:info
              "Enable ingress traffic forwarding";
            tailf:cli-hide-in-submode;
            type empty;
          }
          leaf ingress-encap {
            tailf:cli-drop-node-name;
            tailf:cli-hide-in-submode;
            when '../ingress' {
              tailf:xpath-root 3;
              tailf:dependency "../ingress";
            }
            type enumeration {
              enum "dot1q" {
                tailf:info
                  "ingress forwarding using dot1q encapsulation";
              }
              enum "isl" {
                tailf:info
                  "ingress forwarding using isl encapsulation";
              }
              enum "untagged" {
                tailf:info
                  "ingress forwarding using untagged encapsulation";
              }
            }
          }
          leaf vlan {
            tailf:info
              "Set default VLAN for untagged ingress traffic";
            tailf:cli-hide-in-submode;
            when '../ingress' {
              tailf:xpath-root 3;
              tailf:dependency "../ingress";
            }
            type uint16 {
              tailf:info
                "<1-4094>;;Default VLAN for untagged ingress traffic";
              range "1..4094";
            }
          }
        }
        container source {
          tailf:info
            "SPAN source interface, VLAN ";
          container interface {
            tailf:info
              "SPAN source interface";
            uses interface-name-grouping;
          }
          container vlan {
            tailf:info
              "SPAN source VLAN";
            tailf:cli-flatten-container;
            tailf:cli-compact-syntax;
            tailf:cli-sequence-commands;
            leaf vlan {
              tailf:cli-drop-node-name;
              type uint16 {
                tailf:info
                  "<1-4094>;;SPAN source VLAN";
                range "1..4094";
              }
            }
            leaf direction {
              tailf:cli-drop-node-name;
              type enumeration {
                enum "both" {
                  tailf:info
                    "Monitor received and transmitted traffic";
                }
                enum "rx" {
                  tailf:info
                    "Monitor received traffic only";
                }
                enum "tx" {
                  tailf:info
                    "Monitor transmitted traffic only";
                }
              }
            }
          }
        }
      }
      container event-trace {
        tailf:info
          "Tracing of system events";
        list event-trace-list {
          tailf:cli-drop-node-name;
          tailf:cli-suppress-mode;
          tailf:cli-delete-when-empty;
          tailf:cli-compact-syntax;
          key "name";
          leaf name {
            tailf:cli-multi-word-key;
            type string {
              tailf:info
                "WORD;;event trace entry";
            }
          }
        }
      }
    }
    list tftp-server {
      tailf:ncs-device-type "cli-ned";
      tailf:display-when "not(../ncs:module) or ../ncs:module[ncs:name='tailf-ned-cisco-ios']";
      tailf:info
        "Provide TFTP service for netload requests";
      tailf:cli-suppress-mode;
      tailf:cli-delete-when-empty;
      tailf:cli-compact-syntax;
      key "name";
      leaf name {
        type string {
          tailf:info
            "Allow URL file TFTP load requests";
        }
      }
      leaf alias {
        tailf:info
          "file alias";
        type string {
          tailf:info
            "WORD;;file alias";
        }
      }
      leaf access-list {
        tailf:cli-drop-node-name;
        tailf:cli-disallow-value "alias";
        type std-ip-acl-type;
      }
    }
    container radius-server {
      tailf:ncs-device-type "cli-ned";
      tailf:display-when "not(../../ncs:module) or ../../ncs:module[ncs:name='tailf-ned-cisco-ios']";
      tailf:info
        "Modify RADIUS query parameters";
      list host {
        tailf:info
          "Specify a RADIUS server";
        tailf:cli-suppress-mode;
        tailf:cli-delete-when-empty;
        tailf:cli-compact-syntax;
        key "id";
        leaf id {
          type string {
            tailf:info
              "Hostname or A.B.C.D;;IP address of RADIUS server";
          }
        }
        leaf acct-port {
          tailf:info
            "UDP port for RADIUS accounting server (default is 1646)";
          type uint16 {
            tailf:info
              "<0-65535>;;Port number";
            range "0..65535";
          }
        }
        leaf auth-port {
          tailf:info
            "UDP port for RADIUS authentication server (default is 1645)";
          type uint16 {
            tailf:info
              "<0-65535>;;Port number";
            range "0..65535";
          }
        }
        leaf key {
          tailf:info
            "per-server encryption key (overrides default)";
          type string {
            tailf:info
              "LINE;;The UNENCRYPTED (cleartext) server key";
          }
        }
      }
      leaf retransmit {
        tailf:info
          "Specify the number of retries to active server";
        type uint8 {
          tailf:info
            "<0-100>;;Number of retries for a transaction (default is 3)";
          range "0..100";
        }
        default "3";
      }
      leaf timeout {
        tailf:info
          "Time to wait for a RADIUS server to reply";
        type uint16 {
          tailf:info
            "<1-1000>;;Wait time (default 5 seconds)";
          range "1..1000";
        }
        default "5";
      }
      container key {
        tailf:info
          "encryption key shared with the RADIUS servers";
        tailf:cli-compact-syntax;
        tailf:cli-sequence-commands {
          tailf:cli-reset-siblings;
        }
        uses password-07-grouping;
      }
    }
    container radius {
      tailf:ncs-device-type "cli-ned";
      tailf:display-when "not(../../ncs:module) or ../../ncs:module[ncs:name='tailf-ned-cisco-ios']";
      tailf:info
        "RADIUS server configuration command";
      list filter {
        tailf:info
          "Packet filter configuration";
        key "id";
        leaf id {
          type string {
            tailf:info
              "WORD;;Name of the filter (max 31 characters, longer will be rejected";
          }
        }
        leaf match {
          tailf:cli-drop-node-name;
          tailf:cli-prefix-key;
          type enumeration {
            enum "match-all" {
              tailf:info
                "Filter if all of the attributes matches";
            }
            enum "match-any" {
              tailf:info
                "Filter if any of the attributes matches";
            }
          }
        }
      }
      list server {
        tailf:info
          "Server configuration";
        key "id";
        leaf id {
          type string {
            tailf:info
              "WORD;;Name for the radius server configuration";
          }
        }
        container address {
          tailf:info
            "Specify the radius server address";
          container ipv4 {
            tailf:info
              "IPv4 Address";
            tailf:cli-compact-syntax;
            tailf:cli-sequence-commands {
              tailf:cli-reset-siblings;
            }
            leaf host {
              tailf:cli-drop-node-name;
              type string {
                tailf:info
                  "Hostname or A.B.C.D;;IPv4 Address of radius server";
              }
            }
            leaf auth-port {
              tailf:info
                "UDP port for RADIUS authentication server (default is 1645)";
              tailf:cli-optional-in-sequence;
              type uint16 {
                tailf:info
                  "<0-65535>;;Port number";
                range "0..65535";
              }
            }
            leaf acct-port {
              tailf:info
                "UDP port for RADIUS accounting server (default is 1646)";
              type uint16 {
                tailf:info
                  "<0-65535>;;Port number";
                range "0..65535";
              }
            }
          }
        }
        container backoff {
          tailf:info
            "Retry backoff pattern(Default is retransmits with constant delay)";
          container exponential {
            tailf:info
              "Exponential retransmit backoff";
            tailf:cli-compact-syntax;
            tailf:cli-sequence-commands {
              tailf:cli-reset-siblings;
            }
            presence "true";
            leaf max-delay {
              tailf:cli-optional-in-sequence;
              tailf:info
                "Max delay between retransmits(default is 3 min)";
              type uint8 {
                tailf:info
                  "<1-120>;;Max time (in minutes) to delay between retransmits";
                range "1..120";
              }
            }
            leaf backoff-retry {
              tailf:info
                "Exponential backoff retry number(default is 8)";
              type uint8 {
                tailf:info
                  "<1-50>;;Number of retransmits in the exponential backoff mode";
                range "1..50";
              }
            }
          }
        }
        container key {
          tailf:info
            "Per-server encryption key";
          tailf:cli-compact-syntax;
          tailf:cli-sequence-commands {
            tailf:cli-reset-siblings;
          }
          leaf encryption {
            tailf:cli-drop-node-name;
            tailf:cli-incomplete-command;
            tailf:cli-optional-in-sequence;
            type enumeration {
              enum "0" {
                tailf:info
                  "Specifies an UNENCRYPTED key will follow";
              }
              enum "5" {
                tailf:info
                  "Specifies a HIDDEN key will follow";
              }
            }
          }
          leaf key {
            tailf:cli-drop-node-name;
            tailf:cli-multi-value;
            type string {
              tailf:info
                "LINE;;The UNCRYPTED (cleartext) shared key";
            }
          }
        }
      }
    }
    container zone {
      tailf:ncs-device-type "cli-ned";
      tailf:display-when "not(../../ncs:module) or ../../ncs:module[ncs:name='tailf-ned-cisco-ios']";
      tailf:info
        "FW with zoning";
      list security {
        tailf:info
          "Security zone";
        tailf:cli-mode-name "config-sec-zone";
        tailf:cli-full-command;
        key "id";
        leaf id {
          type string {
            tailf:info
              "WORD;;Name of security zone";
          }
        }
        leaf description {
          tailf:info
            "Zone description";
          tailf:cli-multi-value;
          type string {
            tailf:info
              "LINE;;Description of zone (up to 200 characters)";
          }
        }
      }
    }
    container zone-pair {
      tailf:ncs-device-type "cli-ned";
      tailf:display-when "not(../../ncs:module) or ../../ncs:module[ncs:name='tailf-ned-cisco-ios']";
      tailf:info
        "Zone pair command";
      list security {
        tailf:info
          "Zone-pair name";
        tailf:cli-sequence-commands {
          tailf:cli-reset-siblings;
        }
        tailf:cli-mode-name "config-sec-zone-pair";
        key "id";
        leaf id {
          type string {
            tailf:info
              "WORD;;Name of zone-pair";
          }
        }
        leaf source {
          tailf:info
            "Source zone";
          tailf:cli-hide-in-submode;
          tailf:non-strict-leafref {
            path "/ncs:devices/ncs:device/ncs:config/ios:zone/security/id" {
              tailf:xpath-root 3;
            }
          }
          type string {
            tailf:info
              "WORD;;Name of source zone";
          }
        }
        leaf destination {
          tailf:info
            "Destination zone";
          tailf:cli-hide-in-submode;
          tailf:non-strict-leafref {
            path "/ncs:devices/ncs:device/ncs:config/ios:zone/security/id" {
              tailf:xpath-root 3;
            }
          }
          type string {
            tailf:info
              "WORD;;Name of destination zone";
          }
        }
        leaf description {
          tailf:info
            "Zone description";
          tailf:cli-break-sequence-commands;
          tailf:cli-multi-value;
          type string {
            tailf:info
              "LINE;;Description of zone (up to 200 characters)";
            length "1..200";
          }
        }
        container service-policy {
          tailf:info
            "Configure CBAC Service Policy";
          container type {
            tailf:info
              "Service Policy type";
            leaf inspect {
              tailf:info
                "Configure CBAC Service Policy type inspect";
              type string;
              tailf:non-strict-leafref {
                path "/ncs:devices/ncs:device/ncs:config/ios:policy-map/name" {
                  tailf:xpath-root 3;
                }
              }
            }
          }
        }
      }
    }
    list alarm-contact {
      tailf:ncs-device-type "cli-ned";
      tailf:display-when "not(../ncs:module) or ../ncs:module[ncs:name='tailf-ned-cisco-ios']";
      tailf:info
        "Configure the system alarm contact settings";
      tailf:cli-suppress-mode;
      tailf:cli-delete-when-empty;
      tailf:cli-incomplete-command;
      key "name";
      leaf name {
        type union {
          type uint8 {
            tailf:info
              "<1-4>;;Alarm contact number";
            range "1..4";
          }
          type enumeration {
            enum "all" {
              tailf:info
                "Configure all alarm contacts";
            }
          }
        }
      }
      leaf description {
        tailf:cli-multi-value;
        type string {
          length "1..80";
        }
      }
      leaf severity {
        tailf:info
          "Set the severity level reported";
        type enumeration {
          enum "critical" {
            tailf:info
              "Critical alarm severity";
          }
          enum "major" {
            tailf:info
              "Major alarm severity";
          }
          enum "minor" {
            tailf:info
              "Minor alarm severity";
          }
        }
      }
      leaf trigger {
        tailf:info
          "Set the alarm trigger";
        type enumeration {
          enum "closed" {
            tailf:info
              "Assert alarm when contact is closed";
          }
          enum "open" {
            tailf:info
              "Assert alarm when contact is open";
          }
        }
      }
    }
    container mpls {
      tailf:ncs-device-type "cli-ned";
      tailf:display-when "not(../../ncs:module) or ../../ncs:module[ncs:name='tailf-ned-cisco-ios']";
      tailf:info
        "Configure MPLS parameters";
      container atm {
        tailf:info
          "Configure ATM options";
        leaf disable-headend-vc {
          tailf:info
            "Dedicated lsc capability: In this mode headend Tag VCs are disabled.";
          type empty;
        }
      }
      leaf cos-map {
        tailf:info
          "Configure MPLS CoS ATM Multi-VC CoS Map";
        tailf:cli-full-command;
        type uint8 {
          range "1..255" {
            tailf:info
              "<1-255>;;cos-map number";
          }
        }
      }
      container conf {
        tailf:cli-drop-node-name;
        leaf ip {
          tailf:cli-boolean-no;
          tailf:cli-full-command;
          type boolean;
          default "true";
        }
      }
      container ip {
        tailf:info
          "Dynamic MPLS forwarding for IP";
        tailf:cli-incomplete-no;
        tailf:cli-incomplete-command;
        leaf default-route {
          tailf:info
            "Allow MPLS forwarding for ip default route";
          tailf:cli-full-command;
          type empty;
        }
        choice propagate-ttl-choice {
          container propagate-ttl-conf {
            tailf:cli-drop-node-name;
            leaf propagate-ttl {
              tailf:info
                "Propagate IP TTL into the label stack";
              tailf:cli-boolean-no;
              tailf:cli-full-command;
              type boolean;
              default "true";
            }
          }
          container propagate-ttl {
            tailf:cli-incomplete-command;
            tailf:cli-incomplete-no;
            leaf forwarded {
              tailf:info
                "Propagate IP TTL for forwarded traffic";
              tailf:cli-boolean-no;
              tailf:cli-full-command;
              type boolean;
              default "true";
            }
          }
        }
        container ttl-expiration {
          tailf:info
            "Control MPLS TTL expiration behavior";
          leaf pop {
            tailf:info
              "Popping labels on TTL expiration";
            type uint8 {
              tailf:info
                "<1-6>;;Popping all labels if original packet has less than N labels";
              range "1..6";
            }
          }
        }
      }
      container label {
        tailf:info
          "Label properties";
        container atm {
          tailf:info
            "Configure ATM options";
          leaf disable-headend-vc {
            tailf:info
              "Dedicated lsc capability: In this mode headend Tag VCs are disabled.";
            type empty;
          }
        }
        leaf protocol {
          tailf:info
            "Set platform default label distribution protocol";
          tailf:cli-full-command;
          type enumeration {
            enum "ldp" {
              tailf:code-name "label_ldp";
              tailf:info
                "Use LDP (default)";
            }
            enum "tdp:" {
              tailf:code-name "label_tdp";
              tailf:info
                "Use TDP";
            }
          }
        }
        container range {
          tailf:info
            "Label range";
          tailf:cli-compact-syntax;
          tailf:cli-sequence-commands;
          leaf min {
            tailf:cli-drop-node-name;
            tailf:cli-incomplete-command;
            type uint32 {
              tailf:info
                "<16-1048575>;;Minimum label value";
              range "16..1048575";
            }
          }
          leaf max {
            tailf:cli-drop-node-name;
            type uint32 {
              tailf:info
                "<16-1048575>;;Maximum label value";
              range "16..1048575";
            }
          }
        }
      }
      container ldp {
        tailf:info
          "Label Distribution Protocol";
        leaf advertise-labels {
          tailf:cli-boolean-no;
          tailf:cli-full-command;
          type boolean;
          default "true";
        }
        container advertise-labels-conf {
          tailf:cli-drop-node-name;
          container advertise-labels {
            tailf:cli-incomplete-command;
            tailf:cli-incomplete-no;
            tailf:info
              "Label advertisements";
            container for {
              tailf:info
                "Access-list specifying controls on destination prefixes";
              tailf:cli-sequence-commands;
              tailf:cli-compact-syntax;
              leaf from {
                tailf:cli-drop-node-name;
                type string {
                  tailf:info
                    "WORD;;IP access-list for destination prefixes; name or number (1-99)";
                }
              }
              leaf to {
                tailf:info
                  "Access-list specifying controls on LDP peers";
                type string {
                  tailf:info
                    "WORD;;IP access-list for LDP peers; name or number (1-99)";
                }
              }
            }
            container interface {
              tailf:info
                "Advertise /32 interface address";
              uses interface-name-grouping;
            }
            leaf oldstyle {
              tailf:info
                "Use old style (TDP) method for matching prefix acl";
              tailf:cli-full-command;
              type empty;
            }
          }
        }
        container atm {
          tailf:info
            "Configure ATM MPLS options";
          leaf control-mode {
            tailf:info
              "Select LSP setup control mode for MPLS VCs";
            tailf:cli-full-command;
            type enumeration {
              enum "independent" {
                tailf:info
                  "Independent Downstream on Demand Label VC setup";
              }
              enum "ordered" {
                tailf:info
                  "Ordered Dowstream on Demand Label VC setup";
              }
            }
          }
          leaf vc-merge {
            tailf:info
              "Select VC merge capability";
            tailf:cli-full-command;
            tailf:cli-boolean-no;
            type boolean;
            default "true";
          }
        }
        container backoff {
          tailf:info
            "Set LDP session backoff parameters";
          tailf:cli-sequence-commands;
          tailf:cli-compact-syntax;
          leaf initial {
            tailf:cli-drop-node-name;
            tailf:cli-incomplete-command;
            type uint32 {
              tailf:info
                "<5-2147483>;;Initial session backoff time (seconds)";
              range "5..2147483";
            }
          }
          leaf max {
            tailf:cli-drop-node-name;
            type uint32 {
              tailf:info
                "<5-2147483>;;Maximum session backoff time (seconds)";
              range "5..2147483";
            }
          }
        }
        container discovery {
          tailf:info
            "LDP discovery";
          container hello {
            tailf:info
              "LDP discovery Hello";
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
          container targeted-hello {
            tailf:info
              "LDP discovery Targeted Hello";
            container accept {
              tailf:info
                "Accept targeted hellos";
              presence "Accept targeted hellos";
              leaf from {
                tailf:info
                  "Access list to specify acceptable targeted hello sources";
                type string {
                  tailf:info
                    "WORD;;IP access-list for acceptable targeted hello sources";
                }
              }
            }
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
        }
        container explicit-null {
          tailf:info
            "Advertise Explicit Null label in place of Implicit Null";
          tailf:cli-delete-when-empty;
          presence "true";
          leaf for {
            tailf:info
              "Access-list specifying controls on destination prefixes";
            type string {
              tailf:info
                "WORD;;IP access-list for destination prefixes; name or number (1-99)";
            }
          }
          leaf to {
            tailf:info
              "Access-list specifying controls on LDP peers";
            type string {
              tailf:info
                "WORD;;IP access-list for LDP peers; name or number (1-99)";
            }
          }
        }
        leaf loop-detection {
          tailf:info
            "Enable LDP Loop Detection";
          tailf:cli-full-command;
          type empty;
        }
        container graceful-restart {
          tailf:info
            "Configure Graceful Restart timers";
          presence "Configure Graceful Restart timers";
          container timers {
            tailf:info
              "Configure Graceful Restart timers";
            leaf forwarding-holding {
              tailf:info
                "Forwarding State Holding time";
              tailf:cli-full-command;
              type uint16 {
                tailf:info
                  "<30-600>;;seconds";
                range "30..600";
              }
            }
            leaf max-recovery {
              tailf:info
                "Max-Recovery time";
              tailf:cli-full-command;
              type uint16 {
                tailf:info
                  "<15-600>;;seconds";
                range "15..600";
              }
            }
            leaf neighbor-liveness {
              tailf:info
                "Neighbor-Liveness time";
              tailf:cli-full-command;
              type uint16 {
                tailf:info
                  "<5-300>;;seconds";
                range "5..600";
              }
            }
          }
        }
        leaf holdtime {
          tailf:info
            "LDP session holdtime";
          tailf:cli-full-command;
          type uint32 {
            tailf:info
              "<15-2147483>;;Holdtime in seconds";
            range "15..2147483";
          }
        }
        container logging {
          tailf:info
            "Enable LDP logging";
          leaf neighbor-changes {
            tailf:info
              "Log LDP neighbor state changes";
            type empty;
          }
        }
        leaf maxhops {
          tailf:info
            "Limit hop count for LDP LSP setup";
          tailf:cli-full-command;
          type uint8 {
            tailf:info
              "<1-255>;;Maximum hop count value";
          }
        }
        list neighbor {
          tailf:info
            "Configure neighbor parameters";
          tailf:cli-suppress-mode;
          tailf:cli-delete-when-empty;
          key "address";
          leaf address {
            type inet:ipv4-address {
              tailf:info
                "A.B.C.D;;IP address for LDP neighbor";
            }
          }
          leaf implicit-withdraw {
            tailf:info
              "Enable LDP Implicit Withdraw Label";
            tailf:cli-full-command;
            type empty;
          }
          container lables {
            tailf:info
              "Configure label binding exchange controls";
            leaf accept {
              tailf:info
                "Specify label bindings to accept";
              type string {
                tailf:info
                  "WORD;;IP access-list for LDP peers; name or number (1-99)";
              }
            }
          }
          container password {
            tailf:info
              "Set a password";
            tailf:cli-compact-syntax;
            leaf enctype {
              tailf:cli-drop-node-name;
              tailf:cli-incomplete-command;
              tailf:cli-reset-container;
              type uint8 {
                tailf:info
                  "<0-7>;;Encryption type (0 to disable encryption, 7 for proprietary)";
                range "0..7";
              }
              default "0";
            }
            leaf text {
              tailf:cli-drop-node-name;
              tailf:cli-full-command;
              tailf:cli-multi-value;
              tailf:cli-reset-container;
              type string {
                pattern '[a-zA-Z].*';
                tailf:info
                  "LINE;;The password";
              }
            }
          }
          container targeted {
            tailf:info
              "Establish targeted session";
            presence "Establish targeted session";
            leaf protocol {
              tailf:cli-drop-node-name;
              type enumeration {
                enum "ldp" {
                  tailf:code-name "target_ldp";
                  tailf:info
                    "User LDP";
                }
                enum "tdp" {
                  tailf:code-name "target_tdp";
                  tailf:info
                    "Use TDP";
                }
              }
            }
          }
        }
        container request-labels {
          tailf:info
            "Access list to specify valid downstream on demand destinations.";
          leaf for {
            tailf:info
              "Access list to specify acceptable downstream on demand destinations";
            type string {
              tailf:info
                "WORD;;IP access-list for destination prefixes; name or number (1-99)";
            }
          }
        }
        container router-id {
          tailf:info
            "Select interface to prefer for LDP identifier address";
          tailf:cli-sequence-commands {
            tailf:cli-reset-siblings;
          }
          tailf:cli-compact-syntax;
          leaf interface {
            tailf:cli-drop-node-name;
            type string {
              tailf:info
                "WORD;;intrace name";
            }
          }
          leaf force {
            tailf:info
              "Forcibly change the LDP router id";
            type empty;
          }
        }
        container session {
          tailf:info
            "Configure session parameters";
          container protection {
            tailf:info
              "Configure session protection parameters";
            tailf:cli-compact-syntax;
            presence "true";
            leaf duration {
              tailf:info
                "Period to sustain session protection after loss of link discovery";
              type union {
                type enumeration {
                  enum "infinite" {
                    tailf:info
                      "Protect session forever after loss of link discovery";
                  }
                }
                type uint32 {
                  tailf:info
                    "<30-2147483>;;Holdup time in seconds";
                  range "30..2147483";
                }
              }
            }
          }
        }
        container label {
          tailf:cli-add-mode;
          tailf:cli-mode-name "config-ldp-lbl";
          container allocate {
            tailf:info
              "Allocate local labels for specified destination prefixes";
            container global {
              tailf:info
                "Specify global Routing/Forwarding instance";
              tailf:cli-delete-when-empty;
              presence "true";
              choice global-choice {
                leaf host-routes {
                  tailf:info
                    "allocate local label for host routes only";
                  type empty;
                }
                leaf prefix-list {
                  tailf:info
                    "Specify a prefix list for local label filtering";
                  type string {
                    tailf:info
                      "WORD;;IP prefix-list for destination prefixes; name or number (1-99)";
                  }
                }
              }
            }
          }
        }
      }
      container prefix-map {
        tailf:info
          "Configure MPLS CoS Tag-VC Multi-VC Prefix Map";
        tailf:cli-compact-syntax;
        tailf:cli-sequence-commands;
        leaf nr {
          tailf:cli-drop-node-name;
          tailf:cli-incomplete-command;
          type uint8 {
            tailf:info
              "<1-255>;;prefix-map number";
            range "1..255";
          }
        }
        leaf access-list {
          tailf:info
            "Configure access-list for this prefix-map";
          tailf:cli-incomplete-command;
          type uint8 {
            tailf:info
              "<1-255>;;access-list number";
            range "1..255";
          }
        }
        leaf cos-map {
          tailf:info
            "Configure cos-map for this prefix-map";
          type uint8 {
            tailf:info
              "<1-255>;;cos-map number";
            range "1..255";
          }
        }
      }
      container traffic-eng {
        tailf:info
          "Configure Traffic Engineering parameters";
        container auto-bw {
          tailf:info
            "auto-bw parameters";
          container timers {
            tailf:info
              "Enable auto-bw Timers Collection and Application";
            presence "Enable auto-bw Timers Collection and Application";
            leaf frequency {
              tailf:info
                "Interval between auto-bw data collection";
              type uint32 {
                tailf:info
                  "<1-604800>;;seconds between auto-bw";
                range "1..604800";
              }
            }
          }
        }
        container link-management {
          tailf:info
            "Link Management configuration";
          container timers {
            tailf:info
              "Link Management timers configuration";
            leaf bandwidth-hold {
              tailf:info
                "Link Management bandwidth hold timer";
              tailf:cli-full-command;
              type uint16 {
                tailf:info
                  "<1-300>;;seconds";
                range "1..300";
              }
            }
            leaf periodic-flooding {
              tailf:info
                "Link Management periodic flooding interval";
              tailf:cli-full-command;
              type uint16 {
                tailf:info
                  "<0-3600>;;seconds";
                range "0..3600";
              }
            }
          }
        }
        container logging {
          tailf:info
            "Trap logging configuration";
          container lsp {
            tailf:info
              "LSP-specific traps logging configuration";
            container path-errors {
              tailf:info
                "Log LSP Path Error traps";
              presence "Log LSP Path Error traps";
              leaf access-list {
                tailf:cli-drop-node-name;
                type exp-ip-acl-type;
              }
            }
            container preemption {
              tailf:info
                "Log LSP Preemption traps";
              presence "Log LSP Preemption traps";
              leaf access-list {
                tailf:cli-drop-node-name;
                type exp-ip-acl-type;
              }
            }
            container reservation-errors {
              tailf:info
                "Log LSP Reservation Error traps";
              presence "Log LSP Reservation Error traps";
              leaf access-list {
                tailf:cli-drop-node-name;
                type exp-ip-acl-type;
              }
            }
            container setups {
              tailf:info
                "Log LSP Establishment Traps";
              presence "Log LSP Establishment Traps";
              leaf access-list {
                tailf:cli-drop-node-name;
                type exp-ip-acl-type;
              }
            }
            container teardowns {
              tailf:info
                "Log LSP Teardown Traps";
              presence "Log LSP Teardown Traps";
              leaf access-list {
                tailf:cli-drop-node-name;
                type exp-ip-acl-type;
              }
            }
          }
          container tunnel {
            tailf:info
              "Tunnel-specific traps logging configuration";
            container lsp-selection {
              tailf:info
                "Log Tunnel LSP Selection traps";
              presence "Log Tunnel LSP Selection traps";
              leaf access-list {
                tailf:cli-drop-node-name;
                type exp-ip-acl-type;
              }
            }
            container path {
              tailf:info
                "Log Tunnel Path-related traps";
              container change {
                tailf:info
                  "Log Tunnel Path change traps";
                presence "Log Tunnel Path change traps";
                leaf access-list {
                  tailf:cli-drop-node-name;
                  type exp-ip-acl-type;
                }
              }
            }
          }
        }
        container path-selection {
          tailf:info
            "Path Selection Configuration";
          leaf metric {
            tailf:info
              "Metric Type Configuration";
            tailf:cli-full-command;
            type enumeration {
              enum "igp" {
                tailf:info
                  "Use IGP metric";
              }
              enum "te" {
                tailf:info
                  "User TE metric";
              }
            }
          }
          container overload {
            tailf:info
              "Overload Node Configuration";
            container allow {
              tailf:info
                "Allow overloaded nodes in CSPFs";
              tailf:cli-sequence-commands;
              leaf head {
                tailf:info
                  "Allow overloaded head node in TE CSPF";
                tailf:cli-optional-in-sequence;
                tailf:cli-reset-container;
                type empty;
              }
              leaf middle {
                tailf:info
                  "Allow overloaded middle node in TE CSPF";
                tailf:cli-optional-in-sequence;
                tailf:cli-reset-container;
                type empty;
              }
              leaf tail {
                tailf:info
                  "Allow overloaded middle node in TE CSPF";
                tailf:cli-optional-in-sequence;
                tailf:cli-reset-container;
                type empty;
              }
            }
          }
        }
        container reoptimize {
          tailf:info
            "Reoptimization parameters";
          container events {
            tailf:info
              "Reoptimization triggers";
            leaf link-up {
              tailf:info
                "Reoptimize tunnels on link up events";
              type empty;
            }
          }
          container timers {
            tailf:info
              "Reoptimization timers";
            container delay {
              tailf:info
                "Delay reoptimization action";
              leaf cleanup {
                tailf:info
                  "Delay cleanup of reoptimized LSP";
                tailf:cli-full-command;
                type uint8 {
                  tailf:info
                    "<0-60>;;seconds to delay cleanup of replaced tunnel LSP";
                  range "0..60";
                }
              }
              leaf installation {
                tailf:info
                  "Delay replacement of current LSP by reoptimized LSP";
                tailf:cli-full-command;
                type uint16 {
                  tailf:info
                    "<0-3600>;;seconds to delay replacement of tunnel LSP";
                  range "0..3600";
                }
              }
            }
            leaf frequency {
              tailf:info
                "Interval between reoptimization scans";
              tailf:cli-full-command;
              type uint32 {
                tailf:info
                  "<0-604800>;;seconds between reoptimizations (0 disables reoptimization)";
                range "0..604800";
              }
            }
          }
        }
        container signalling {
          tailf:info
            "Traffic Engineering Signalling Parameters";
          container advertise {
            tailf:info
              "Signalling advertisement parameters";
            container implicit-null {
              tailf:info
                "Use MPLS encoding for Implicit-Null Label in signalling messages";
              presence "Use MPLS encoding for Implicit-Null Label in signalling messages";
              leaf nr {
                tailf:cli-drop-node-name;
                type uint8 {
                  tailf:info
                    "<1-99>;;Number of IP access-list to determine applicable signalling peers";
                  range "1..99";
                }
              }
            }
          }
          container forwarding {
            tailf:info
              "Control interaction of LSP signalling and LFIB maintenance";
            leaf sync {
              tailf:info
                "Program linecard LFIBs before signalling LSP label upstream";
              type empty;
            }
          }
          container restart {
            tailf:info
              "Signalling restart parameters";
            container neighbors {
              tailf:info
                "Identify signalling restart capable neighbors";
              presence "Identify signalling restart capable neighbors";
              leaf nr {
                tailf:cli-drop-node-name;
                type uint8 {
                  tailf:info
                    "<1-99>;;Number of IP access-list to determine applicable signalling peers";
                  range "1..99";
                }
              }
            }
          }
        }
        container topology {
          tailf:info
            "Topology Database Configuration";
          container holddown {
            tailf:info
              "Topology Database hold down timers";
            leaf sigerr {
              tailf:info
                "Link hold down time for signalling errors";
              type uint16 {
                tailf:info
                  "<0-300>;;Hold down time in seconds";
                range "0..300";
              }
            }
          }
        }
        leaf tunnels {
          tailf:info
            "Traffic Engineering tunnels";
          tailf:cli-full-command;
          type empty;
        }
      }
    }
    container l3vpn {
      tailf:ncs-device-type "cli-ned";
      tailf:display-when "not(../../ncs:module) or ../../ncs:module[ncs:name='tailf-ned-cisco-ios']";
      tailf:info
        "l3vpn encapsulation ip commands";
      container encapsulation {
        tailf:info
          "l3vpn encapsulation ip";
        list ip {
          tailf:info
            "l3vpn encapsulation ip";
          tailf:cli-mode-name "config-l3vpn-encap-ip";
          tailf:cli-full-command;
          key "name";
          leaf name {
            type string {
              tailf:info
                "WORD;;profile name";
            }
          }
          container transport {
            tailf:info
              "transport mode";
            container ipv4 {
              tailf:info
                "transport ipv4 mode";
              presence "true";
              container source {
                tailf:info
                  "transport source";
                tailf:cli-diff-dependency "/ios:interface" {
                  tailf:xpath-root 3;
                }
                uses interface-name-grouping;
              }
            }
          }
        }
      }
    }
    container router {
      tailf:ncs-device-type "cli-ned";
      tailf:display-when "not(../../ncs:module) or ../../ncs:module[ncs:name='tailf-ned-cisco-ios']";
      tailf:info
        "Enable a routing process";
      container mobile {
        tailf:info
          "Mobile routes";
        tailf:cli-add-mode;
        tailf:cli-mode-name "config-router";
        tailf:cli-diff-dependency "../../ip/routing" {
          tailf:xpath-root 3;
          tailf:cli-trigger-on-set;
        }
        presence "true";
      }
      list bgp {
        tailf:info
          "Border Gateway Protocol (BGP)";
        tailf:cli-mode-name "config-router";
        tailf:cli-diff-dependency "/ios:ip/vrf" {
          tailf:xpath-root 3;
        }
        tailf:cli-diff-dependency "/ios:vrf/definition" {
          tailf:xpath-root 3;
        }
        tailf:cli-diff-dependency "../../ip/routing" {
          tailf:xpath-root 3;
          tailf:cli-trigger-on-set;
        }
        key "as-no";
        max-elements 1;
        leaf as-no {
          tailf:cli-suppress-range;
          type uint16 {
            tailf:info
              "<1-65535>;;Autonomous system number";
            range "1..65535";
          }
        }
        uses router-bgp-af-grouping;
        uses router-bgp-grouping;
        container template {
          tailf:info
            "Enter template command mode";
          list peer-policy {
            tailf:info
              "Template configuration for policy parameters";
            tailf:cli-mode-name "config-router-ptmp";
            tailf:cli-exit-command "exit-peer-policy" {
              tailf:info
                "Exit from template configuration mode";
            }
            key "name";
            leaf name {
              type string {
                tailf:info
                  "WORD;;Name of peer-policy template";
              }
            }
            uses router-bgp-peer-policy-grouping;
          }
          list peer-session {
            tailf:info
              "Template configuration for session parameters";
            tailf:cli-mode-name "config-router-stmp";
            tailf:cli-exit-command "exit-peer-session" {
              tailf:info
                "Exit from template configuration mode";
            }
            key "name";
            leaf name {
              type string {
                tailf:info
                  "WORD;;Name of peer-session template";
              }
            }
            uses router-bgp-peer-session-grouping;
          }
        }
        container address-family {
          tailf:info
            "Enter Address Family command mode";
          list ipv4 {
            tailf:info
              "Address family";
            tailf:cli-mode-name "config-router-af";
            tailf:cli-full-command;
            tailf:cli-exit-command "exit-address-family" {
              tailf:info
                "Exit from Address Family configuration mode";
            }
            key "af";
            leaf af {
              type enumeration {
                enum "unicast" {
                  tailf:info
                    "Address Family modifier";
                }
                enum "multicast" {
                  tailf:info
                    "Address Family modifier";
                }
                enum "mdt" {
                  tailf:info
                    "IPv4 multicast distribution tree (MDT)";
                }
                enum "tunnel" {
                  tailf:info
                    "IPv4 tunnel address prefixes.";
                }
                enum "labeled-unicast" {
                  tailf:info
                    "IPv4 labeled-unicast address prefixes";
                }
              }
              tailf:key-default "unicast";
            }
            uses router-bgp-af-grouping;
          }
          list ipv6 {
            tailf:info
              "Address family";
            tailf:cli-mode-name "config-router-af";
            tailf:cli-full-command;
            tailf:cli-exit-command "exit-address-family" {
              tailf:info
                "Exit from Address Family configuration mode";
            }
            key "af";
            leaf af {
              type enumeration {
                enum "unicast" {
                  tailf:info
                    "Address Family modifier";
                }
                enum "multicast" {
                  tailf:info
                    "Address Family modifier";
                }
              }
              tailf:key-default "unicast";
            }
            uses router-bgp-af-grouping;
          }
          container with-vrf {
            tailf:cli-drop-node-name;
            list ipv4 {
              tailf:info
                "Address family";
              tailf:cli-suppress-mode;
              tailf:cli-delete-when-empty;
              tailf:cli-incomplete-command;
              tailf:cli-incomplete-no;
              key "af";
              leaf af {
                type enumeration {
                  enum "unicast" {
                    tailf:info
                      "Address Family modifier";
                  }
                  enum "multicast" {
                    tailf:info
                      "Address Family modifier";
                  }
                  enum "mdt" {
                    tailf:info
                      "IPv4 multicast distribution tree (MDT)";
                  }
                  enum "tunnel" {
                    tailf:info
                      "IPv4 tunnel address prefixes.";
                  }
                  enum "labeled-unicast" {
                    tailf:info
                      "IPv4 labeled-unicast address prefixes";
                  }
                }
                tailf:key-default "unicast";
              }
              list vrf {
                tailf:cli-mode-name "config-router-af";
                tailf:cli-full-command;
                tailf:cli-diff-dependency "/ios:ip/vrf" {
                  tailf:xpath-root 3;
                }
                tailf:cli-diff-dependency "/ios:vrf/definition" {
                  tailf:xpath-root 3;
                }
                tailf:cli-exit-command "exit-address-family" {
                  tailf:info
                    "Exit from Address Family configuration mode";
                }
                key "name";
                leaf name {
                  type string {
                    tailf:info
                      "WORD;;VPN Routing/Forwarding instance name";
                  }
                }
                uses router-bgp-af-grouping;
              }
            }
          }
          container ipv6-with-vrf {
            tailf:cli-drop-node-name;
            list ipv6 {
              tailf:info
                "Address family";
              tailf:cli-suppress-mode;
              tailf:cli-delete-when-empty;
              tailf:cli-incomplete-command;
              tailf:cli-incomplete-no;
              key "af";
              leaf af {
                type enumeration {
                  enum "unicast" {
                    tailf:info
                      "Address Family modifier";
                  }
                  enum "multicast" {
                    tailf:info
                      "Address Family modifier";
                  }
                }
                tailf:key-default "unicast";
              }
              list vrf {
                tailf:cli-mode-name "config-router-af";
                tailf:cli-full-command;
                tailf:cli-diff-dependency "/ios:vrf/definition" {
                  tailf:xpath-root 3;
                }
                tailf:cli-exit-command "exit-address-family" {
                  tailf:info
                    "Exit from Address Family configuration mode";
                }
                key "name";
                leaf name {
                  type string {
                    tailf:info
                      "WORD;;VPN Routing/Forwarding instance name";
                  }
                }
                uses router-bgp-af-grouping;
              }
              uses router-bgp-af-grouping;
            }
          }
          list vpnv4 {
            tailf:info
              "Address family";
            tailf:cli-mode-name "config-router-af";
            tailf:cli-exit-command "exit-address-family" {
              tailf:info
                "Exit from Address Family configuration mode";
            }
            key "af";
            leaf af {
              type enumeration {
                enum "unicast" {
                  tailf:info
                    "Address Family modifier";
                }
              }
              tailf:key-default "unicast";
            }
            uses router-bgp-af-grouping;
          }
          list vpnv6 {
            tailf:info
              "Address family";
            tailf:cli-mode-name "config-router-af";
            tailf:cli-exit-command "exit-address-family" {
              tailf:info
                "Exit from Address Family configuration mode";
            }
            key "af";
            leaf af {
              type enumeration {
                enum "unicast" {
                  tailf:info
                    "Address Family modifier";
                }
              }
              tailf:key-default "unicast";
            }
            uses router-bgp-af-grouping;
          }
          list l2vpn {
            tailf:info
              "Address family";
            tailf:cli-mode-name "config-router-af";
            tailf:cli-exit-command "exit-address-family" {
              tailf:info
                "Exit from Address Family configuration mode";
            }
            key "af";
            leaf af {
              type enumeration {
                enum "vpls" {
                  tailf:info
                    "Address Family modifier";
                }
              }
              tailf:key-default "vpls";
            }
            uses router-bgp-af-grouping;
          }
          list nsap {
            tailf:info
              "Address family";
            tailf:cli-mode-name "config-router-af";
            tailf:cli-exit-command "exit-address-family" {
              tailf:info
                "Exit from Address Family configuration mode";
            }
            key "af";
            leaf af {
              type enumeration {
                enum "unicast" {
                  tailf:info
                    "Address Family modifier";
                }
              }
              tailf:key-default "unicast";
            }
            uses router-bgp-af-grouping;
          }
          list rtfilter {
            tailf:info
              "Address family";
            tailf:cli-mode-name "config-router-af";
            tailf:cli-exit-command "exit-address-family" {
              tailf:info
                "Exit from Address Family configuration mode";
            }
            key "af";
            leaf af {
              type enumeration {
                enum "unicast" {
                  tailf:info
                    "Address Family modifier";
                }
              }
              tailf:key-default "unicast";
            }
            uses router-bgp-af-grouping;
          }
        }
      }
      list eigrp {
        tailf:info
          "Enhanced Interior Gateway Routing Protocol (EIGRP)";
        tailf:cli-mode-name "config-router";
        tailf:cli-diff-dependency "../../ip/routing" {
          tailf:xpath-root 3;
          tailf:cli-trigger-on-set;
        }
        key "id";
        leaf id {
          type union {
            type uint16 {
              tailf:info
                "<1-65535>;;Autonomous System";
              range "1..65535";
            }
            type string {
              tailf:info
                "WORD;;EIGRP Virtual-Instance Name";
            }
          }
        }
        list network {
          tailf:info
            "Enable routing on an IP network";
          tailf:cli-compact-syntax;
          tailf:cli-suppress-mode;
          tailf:cli-delete-when-empty;
          key "ip";
          leaf ip {
            type inet:ipv4-address {
              tailf:info
                "A.B.C.D;;Network number";
            }
          }
          leaf mask {
            tailf:cli-drop-node-name;
            type inet:ipv4-address {
              tailf:info
                "A.B.C.D;;EIGRP wild card bits";
            }
          }
        }
        container redistribute {
          tailf:info
            "Redistribute IPv4 routes from another routing protocol";
          container connected {
            tailf:info
              "Connected";
            tailf:cli-compact-syntax;
            tailf:cli-delete-when-empty;
            presence "true";
            uses eigrp-metric-route-map-grouping;
          }
          container bgp {
            tailf:info
              "Border Gateway Protocol (BGP)";
            tailf:cli-compact-syntax;
            tailf:cli-sequence-commands {
              tailf:cli-reset-all-siblings;
            }
            leaf as-number {
              tailf:cli-drop-node-name;
              type union {
                type uint32 {
                  tailf:info
                    "<1-4294967295>;;Autonomous system number";
                }
                type string {
                  tailf:info
                    "<1.0-XX.YY>;;Autonomous system number";
                }
              }
            }
            uses eigrp-metric-route-map-grouping;
          }
          list eigrp {
            tailf:info
              "Enhanced Interior Gateway Routing Protocol (EIGRP)";
            tailf:cli-suppress-mode;
            tailf:cli-delete-when-empty;
            tailf:cli-compact-syntax;
            key "as-number";
            leaf as-number {
              type uint16 {
                tailf:info
                  "<1-65535>;;Autonomous system number";
                range "1..65535";
              }
            }
            uses eigrp-metric-route-map-grouping;
          }
          container isis {
            tailf:info
              "ISO IS-IS";
            tailf:cli-compact-syntax;
            presence "true";
            list isis-list {
              tailf:cli-drop-node-name;
              tailf:cli-suppress-mode;
              tailf:cli-delete-when-empty;
              tailf:cli-compact-syntax;
              key "name";
              leaf name {
                tailf:cli-disallow-value "level-1|level-2|level-1-2|metric|route-map";
                type string {
                  tailf:info
                    "WORD;;ISO routing area tag";
                }
              }
              leaf level {
                tailf:cli-drop-node-name;
                type isis-level-type;
              }
              uses eigrp-metric-route-map-grouping;
            }
            leaf level {
              tailf:cli-drop-node-name;
              type isis-level-type;
            }
            uses eigrp-metric-route-map-grouping;
          }
          container iso-igrp {
            tailf:info
              "IGRP for OSI networks";
            presence "true";
            list iso-igrp-list {
              tailf:info
                "Border Gateway Protocol (BGP)";
              tailf:cli-suppress-mode;
              tailf:cli-delete-when-empty;
              tailf:cli-drop-node-name;
              key "name";
              leaf name {
                tailf:cli-disallow-value "metric|route-map";
                type string {
                  tailf:info
                    "WORD;;ISO routing area tag";
                }
              }
              uses eigrp-metric-route-map-grouping;
            }
            uses eigrp-metric-route-map-grouping;
          }
          container mobile {
            tailf:info
              "Mobile routes";
            tailf:cli-compact-syntax;
            presence "true";
            uses eigrp-metric-route-map-grouping;
          }
          container odr {
            tailf:info
              "On Demand stub Routes";
            tailf:cli-compact-syntax;
            presence "true";
            uses eigrp-metric-route-map-grouping;
          }
          list ospf {
            tailf:info
              "Open Shortest Path First (OSPF)";
            tailf:cli-suppress-mode;
            tailf:cli-delete-when-empty;
            tailf:cli-compact-syntax;
            key "id";
            leaf id {
              tailf:cli-suppress-range;
              type uint16 {
                tailf:info
                  "<1-65535>;;Process ID";
                range "1..65535";
              }
            }
            uses eigrp-metric-route-map-grouping;
            container match {
              tailf:info
                "Redistribution of OSPF routes";
              tailf:cli-flatten-container;
              tailf:cli-compact-syntax;
              uses redistribute-ospf-match-grouping;
              uses eigrp-metric-route-map-grouping;
            }
          }
          container static {
            tailf:info
              "Static routes";
            tailf:cli-compact-syntax;
            tailf:cli-delete-when-empty;
            presence "Static routes";
            uses eigrp-metric-route-map-grouping;
          }
          container rip {
            tailf:info
              "Routing Information Protocol (RIP)";
            tailf:cli-compact-syntax;
            presence "true";
            uses eigrp-metric-route-map-grouping;
          }
        }
        leaf auto-summary {
          tailf:info
            "Enable automatic network number summarization";
          tailf:cli-full-command;
          type empty;
        }
      }
      list ospfv3 {
        tailf:info
          "OSPFv3";
        tailf:cli-mode-name "config-router";
        tailf:cli-diff-dependency "../../ip/routing" {
          tailf:xpath-root 3;
          tailf:cli-trigger-on-set;
        }
        key "id";
        leaf id {
          tailf:cli-suppress-range;
          type uint16 {
            tailf:info
              "<1-65535>;;Process ID";
            range "1..65535";
          }
        }
        uses router-ospfv3-grouping;
        uses router-ospf-common-grouping;
        container address-family {
          tailf:info
            "Enter Address Family command mode";
          container ipv4 {
            tailf:info
              "Address family";
            container unicast {
              tailf:info
                "Address Family Modifier";
              tailf:cli-add-mode;
              tailf:cli-mode-name "config-router-af";
              tailf:cli-full-command;
              tailf:cli-exit-command "exit-address-family" {
                tailf:info
                  "Exit from Address Family configuration mode";
              }
              uses router-ospfv3-grouping;
              uses router-ospf-common-grouping;
              uses router-ospf-common-af-grouping;
              uses router-ospfv3-af-grouping;
            }
          }
          container ipv6 {
            tailf:info
              "Address family";
            container unicast {
              tailf:info
                "Address Family Modifier";
              tailf:cli-add-mode;
              tailf:cli-mode-name "config-router-af";
              tailf:cli-full-command;
              tailf:cli-exit-command "exit-address-family" {
                tailf:info
                  "Exit from Address Family configuration mode";
              }
              uses router-ospfv3-grouping;
              uses router-ospf-common-grouping;
              uses router-ospf-common-af-grouping;
              uses router-ospfv3-af-grouping;
            }
          }
        }
      }
      list ospf {
        tailf:info
          "Open Shortest Path First (OSPF)";
        tailf:cli-mode-name "config-router";
        tailf:cli-sequence-commands;
        tailf:cli-diff-dependency "../../ip/routing" {
          tailf:xpath-root 3;
          tailf:cli-trigger-on-set;
        }
        key "id";
        leaf id {
          tailf:cli-suppress-range;
          type uint16 {
            tailf:info
              "<1-65535>;;Process ID";
            range "1..65535";
          }
        }
        leaf vrf {
          tailf:info
            "VPN Routing/Forwarding Instance";
          tailf:cli-hide-in-submode;
          tailf:cli-full-command;
          tailf:cli-diff-dependency "/ios:ip/vrf" {
            tailf:xpath-root 3;
          }
          tailf:cli-diff-dependency "/ios:vrf/definition" {
            tailf:xpath-root 3;
          }
          type string {
            tailf:info
              "WORD;;VPN Routing/Forwarding Instance (VRF) name";
          }
        }
        uses router-ospf-common-grouping;
        uses router-ospf-common-af-grouping;
        uses router-ospf-grouping;
      }
      container isis {
        tailf:cli-add-mode;
        tailf:info
          "ISO IS-IS";
        tailf:cli-mode-name "config-router";
        tailf:cli-diff-dependency "/ios:ip/routing" {
          tailf:xpath-root 3;
        }
        presence "true";
        uses router-isis-grouping;
      }
      container isis-container {
        tailf:cli-drop-node-name;
        list isis {
          tailf:info
            "ISO IS-IS";
          tailf:cli-mode-name "config-router";
          tailf:cli-diff-dependency "/ios:ip/routing" {
            tailf:xpath-root 3;
          }
          key "area-tag";
          leaf area-tag {
            type string {
              tailf:info
                "WORD;;ISO routing area tag";
            }
          }
          uses router-isis-grouping;
        }
      }
      container rip {
        tailf:info
          "Routing Information Protocol (RIP)";
        tailf:cli-add-mode;
        tailf:cli-mode-name "config-router";
        tailf:cli-full-command;
        uses router-rip-grouping;
        container address-family {
          tailf:info
            "Enter Address Family command mode";
          container ipv4 {
            tailf:info
              "Address family";
            container unicast {
              tailf:cli-add-mode;
              tailf:cli-mode-name "config-router-af";
              tailf:info
                "Address Family Modifier";
              tailf:cli-full-command;
              tailf:cli-exit-command "exit-address-family" {
                tailf:info
                  "Exit from Address Family configuration mode";
              }
              tailf:cli-diff-dependency "/ios:ip/routing" {
                tailf:xpath-root 3;
                tailf:cli-trigger-on-set;
              }
              uses router-rip-grouping;
            }
            list vrf {
              tailf:info
                "Specify parameters for a VPN Routing/Forwarding instance";
              tailf:cli-mode-name "config-router-af";
              tailf:cli-full-command;
              tailf:cli-diff-dependency "/ios:ip/vrf" {
                tailf:xpath-root 3;
              }
              tailf:cli-diff-dependency "/ios:vrf/definition" {
                tailf:xpath-root 3;
              }
              tailf:cli-exit-command "exit-address-family" {
                tailf:info
                  "Exit from Address Family configuration mode";
              }
              tailf:cli-diff-dependency "/ios:ip/routing" {
                tailf:xpath-root 3;
                tailf:cli-trigger-on-set;
              }
              key "name";
              leaf name {
                type string {
                  tailf:info
                    "WORD;;VPN Routing/Forwarding instance name";
                }
              }
              uses router-rip-af-grouping;
            }
          }
        }
      }
      container lisp {
        tailf:info
          "Locator/ID Separation Protocol";
        tailf:cli-add-mode;
        tailf:cli-mode-name "config-router-lisp";
        presence "true";
        uses router-lisp-grouping;
      }
      container router-lisp {
        tailf:cli-drop-node-name;
        list lisp {
          tailf:cli-mode-name "config-router-lisp";
          key "id";
          leaf id {
            type uint8 {
              tailf:info
                "<0-15>;;router lisp ID";
              range "0..15";
            }
          }
          uses router-lisp-grouping;
        }
      }
    }
    container snmp {
      tailf:ncs-device-type "cli-ned";
      tailf:display-when "not(../../ncs:module) or ../../ncs:module[ncs:name='tailf-ned-cisco-ios']";
      tailf:info
        "Modify non engine SNMP parameters";
      container ifmib {
        tailf:info
          "IF-MIB commands";
        container ifindex {
          tailf:info
            "ifindex persistence";
          leaf persist {
            tailf:info
              "Persist interface indices";
            type empty;
          }
        }
        container ifalias {
          tailf:info
            "ifAlias description option, by default it is limited to 64 character";
          leaf long {
            tailf:info
              "ifAlias description can be up to 256 characters";
            type empty;
          }
        }
      }
      container mib {
        tailf:info
          "MIB commands";
        container bulkstat {
          tailf:info
            "Bulkstat Configuration commands";
          list object-list {
            tailf:info
              "Configure an Object List.";
            tailf:cli-suppress-mode;
            tailf:cli-delete-when-empty;
            key "name";
            leaf name {
              type string {
                tailf:info
                  "WORD;;Name of object list";
              }
            }
          }
        }
        leaf persist {
          tailf:info
            "Persistence for MIBS";
          tailf:cli-full-command;
          type enumeration {
            enum "cbqos" {
              tailf:info
                "CBQOS MIB index persistence";
            }
            enum "circuit" {
              tailf:info
                "Circuit MIB persistence";
            }
          }
        }
      }
    }
    container snmp-server {
      tailf:ncs-device-type "cli-ned";
      tailf:display-when "not(../../ncs:module) or ../../ncs:module[ncs:name='tailf-ned-cisco-ios']";
      tailf:info
        "Modify SNMP engine parameters";
      leaf chassis-id {
        tailf:info
          "String to uniquely identify this chassis";
        tailf:cli-multi-value;
        type string {
          tailf:info
            "LINE;;Unique ID string";
        }
      }
      list community {
        tailf:info
          "Enable SNMP; set community string and access privs";
        tailf:cli-suppress-mode;
        tailf:cli-delete-when-empty;
        tailf:cli-compact-syntax;
        tailf:cli-sequence-commands {
          tailf:cli-reset-siblings;
        }
        key "name";
        leaf name {
          type string {
            tailf:info
              "WORD;;SNMP community string";
          }
        }
        leaf view {
          tailf:info
            "Restrict this community to a named MIB view";
          tailf:cli-optional-in-sequence;
          type string {
            tailf:info
              "WORD;;MIB view to which this community has access";
          }
        }
        choice access-choice {
          leaf RO {
            tailf:info
              "Read-only access with this community string";
            tailf:cli-optional-in-sequence;
            type empty;
          }
          leaf RW {
            tailf:info
              "Read-write access with this community string";
            tailf:cli-optional-in-sequence;
            type empty;
          }
        }
        leaf ipv6 {
          tailf:info
            "Specify IPv6 Named Access-List";
          tailf:cli-optional-in-sequence;
          type string {
            tailf:info
              "WORD;;IPv6 Access-list name";
          }
        }
        leaf access-list-name {
          tailf:cli-drop-node-name;
          type std-ip-acl-type;
        }
      }
      leaf contact {
        tailf:info
          "Text for mib object sysContact";
        tailf:cli-multi-value;
        type string {
          tailf:info
            "LINE;;identification of the contact person for this managed node";
        }
      }
      list context {
        tailf:info
          "Create/Delete a context apart from default";
        tailf:cli-suppress-mode;
        tailf:cli-delete-when-empty;
        key "name";
        leaf name {
          type string {
            tailf:info
              "WORD;;Context Name";
          }
        }
      }
      container drop {
        tailf:info
          "Silently drop SNMP packets";
        leaf vrf-traffic {
          tailf:info
            "Silently drop SNMP packets that come on VRF interface";
          type empty;
        }
      }
      container enable {
        tailf:info
          "Enable SNMP Traps or Informs";
        choice enable-choice {
          leaf informs {
            tailf:info
              "Enable SNMP Informs";
            type empty;
          }
          list traps {
            tailf:info
              "Enable SNMP Traps";
            tailf:cli-suppress-mode;
            tailf:cli-delete-when-empty;
            tailf:cli-full-command;
            ordered-by user;
            key "name";
            leaf name {
              tailf:cli-multi-word-key;
              type string {
                tailf:info
                  "WORD;;Trap name";
              }
            }
          }
        }
      }
      container engineID {
        tailf:info
          "Configure a local or remote SNMPv3 engineID";
        leaf local {
          tailf:info
            "engineID of the local agent";
          type string {
            tailf:info
              "WORD;;engine ID octet string";
            length "1..24";
          }
        }
        list remote {
          tailf:info
            "engineID of the remote agent";
          tailf:cli-suppress-mode;
          tailf:cli-delete-when-empty;
          tailf:cli-compact-syntax;
          tailf:cli-sequence-commands;
          tailf:cli-incomplete-command;
          key "address";
          leaf address {
            type host-v4v6-type;
          }
          leaf udp-port {
            tailf:info
              "The remote notification host's UDP port number";
            tailf:cli-optional-in-sequence;
            type uint16 {
              tailf:info
                "<0-65535>;;The remote notification host's UDP port number";
            }
          }
          leaf vrf {
            tailf:info
              "The remote notification host's VPN routing instance";
            tailf:cli-diff-dependency "/ios:ip/vrf" {
              tailf:xpath-root 3;
            }
            tailf:cli-diff-dependency "/ios:vrf/definition" {
              tailf:xpath-root 3;
            }
            type string {
              tailf:info
                "WORD;;VPN Routing/Forwarding instance name";
            }
          }
          leaf engineid-string {
            tailf:cli-drop-node-name;
            type string {
              tailf:info
                "WORD;;engine ID octet string";
            }
          }
        }
      }
      list group {
        tailf:info
          "Define a User Security Model group";
        tailf:cli-suppress-mode;
        tailf:cli-delete-when-empty;
        tailf:cli-compact-syntax;
        tailf:cli-sequence-commands;
        key "id";
        leaf id {
          type string {
            tailf:info
              "WORD;;Name of the group";
          }
        }
        choice security-model {
          container v1 {
            tailf:info
              "group using the v1 security model";
          }
          container v2c {
            tailf:info
              "group using the v2c security model";
          }
          container v3 {
            tailf:info
              "group using the User Security Model (SNMPv3)";
            tailf:cli-compact-syntax;
            tailf:cli-sequence-commands {
              tailf:cli-reset-siblings;
            }
            leaf security-level {
              tailf:cli-drop-node-name;
              type enumeration {
                enum "auth" {
                  tailf:info
                    "group using the authNoPriv Security Level";
                }
                enum "noauth" {
                  tailf:info
                    "group using the noAuthNoPriv Security Level";
                }
                enum "priv" {
                  tailf:info
                    "group using SNMPv3 authPriv security level";
                }
              }
            }
            leaf context {
              tailf:cli-optional-in-sequence;
              tailf:info
                "specify a context to associate these views for the group";
              type string {
                tailf:info
                  "WORD;;context name";
              }
            }
            leaf match {
              tailf:cli-optional-in-sequence;
              tailf:info
                "context name match criteria";
              type enumeration {
                enum "exact" {
                  tailf:info
                    "match the exact context";
                }
                enum "prefix" {
                  tailf:info
                    "only match the context prefix";
                }
              }
            }
            leaf read {
              tailf:cli-optional-in-sequence;
              tailf:info
                "specify a read view for the group";
              type string {
                tailf:info
                  "WORD;;read view name";
              }
            }
            leaf write {
              tailf:cli-optional-in-sequence;
              tailf:info
                "specify a write view for the group";
              type string {
                tailf:info
                  "WORD;;write view name";
              }
            }
            leaf notify {
              tailf:cli-optional-in-sequence;
              tailf:info
                "specify a notify view for the group";
              type string {
                tailf:info
                  "WORD;;notify view name";
              }
            }
            leaf access {
              tailf:info
                "specify an access-list associated with this group";
              type union {
                type uint8 {
                  tailf:info
                    "<1-99>;;Std IP accesslist allowing access with this group";
                  range "1..99";
                }
                type string {
                  tailf:info
                    "WORD;;Access-list name";
                }
              }
            }
          }
        }
      }
      list host {
        tailf:info
          "Specify hosts to receive SNMP notifications";
        tailf:cli-suppress-mode;
        tailf:cli-delete-when-empty;
        tailf:cli-compact-syntax;
        tailf:cli-sequence-commands {
          tailf:cli-reset-all-siblings;
        }
        tailf:cli-incomplete-command;
        key "ip-address";
        leaf ip-address {
          tailf:cli-disallow-value "vrf";
          tailf:cli-case-sensitive;
          type host-type {
            tailf:info
              "WORD;;Hostname or IP/IPv6 address of SNMP notification host";
          }
        }
        list vrf {
          tailf:info
            "VPN Routing instance for this host";
          tailf:cli-optional-in-sequence;
          tailf:cli-suppress-mode;
          tailf:cli-delete-when-empty;
          tailf:cli-compact-syntax;
          tailf:cli-sequence-commands {
            tailf:cli-reset-all-siblings;
          }
          tailf:cli-incomplete-command;
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding instance name";
            }
          }
          uses snmp-server-host-grouping;
        }
        uses snmp-server-host-grouping;
      }
      container ip {
        tailf:info
          "IP ToS configuration for SNMP traffic";
        leaf dscp {
          tailf:info
            "IP DSCP value for SNMP traffic";
          type uint8 {
            tailf:info
              "<0-63>;;ip dscp value (default value 0 )";
            range "0..63";
          }
        }
        leaf precedence {
          tailf:info
            "IP Precedence value for SNMP traffic";
          tailf:cli-full-command;
          type uint8 {
            tailf:info
              "<0-7>;;ip precedence value (default value 0)";
            range "0..7";
          }
        }
      }
      container ifindex {
        tailf:info
          "Enable ifindex persistence";
        leaf persist {
          tailf:info
            "Persist interface indices";
          type empty;
        }
      }
      leaf location {
        tailf:info
          "Text for mib object sysLocation";
        tailf:cli-multi-value;
        type string {
          tailf:info
            "LINE;;The physical location of this node";
        }
      }
      container manager {
        tailf:info
          "Modify SNMP manager parameters";
        tailf:cli-display-separated;
        presence "true";
        leaf session-timeout {
          tailf:info
            "Timeout value for destroying sessions";
          type uint32 {
            tailf:info
              "<10-2147483>;;seconds";
            range "10..2147483";
          }
        }
      }
      leaf packetsize {
        tailf:info
          "Largest SNMP packet size";
        type uint16 {
          tailf:info
            "<484-17940>;;Packet size";
          range "484..17940";
        }
      }
      leaf queue-length {
        tailf:info
          "Message queue length for each TRAP host";
        type uint16 {
          tailf:info
            "<1-5000>;;Queue length (default 10)";
          range "1..5000";
        }
      }
      container queue-limit {
        tailf:info
          "Message queue size for different queues";
        leaf notification-host {
          tailf:info
            "Message queue length for each notification host";
          type uint16 {
            tailf:info
              "<1-5000>;;notification host queue length";
            range "1..5000";
          }
        }
      }
      container source-interface {
        tailf:info
          "Assign an source interface";
        container informs {
          tailf:info
            "source interface for informs";
          uses interface-name-grouping;
        }
        container traps {
          tailf:info
            "source interface for traps";
          uses interface-name-grouping;
        }
      }
      container trap {
        tailf:info
          "SNMP trap options";
        leaf timeout {
          tailf:info
            "Set timeout for TRAP message retransmissions";
          type uint16 {
            tailf:info
              "<1-1000>;;Timeout (default 30 seconds)";
            range "1..1000";
          }
        }
      }
      container trap-source {
        tailf:info
          "Assign an interface for the source address of all traps";
        uses interface-name-grouping;
      }
      leaf trap-timeout {
        tailf:info
          "Set timeout for TRAP message retransmissions";
        tailf:cli-full-command;
        type uint16 {
          tailf:info
            "<1-1000>;;Timeout (default 30 seconds)";
        }
      }
      list view {
        tailf:info
          "Define an SNMPv2 MIB view";
        tailf:cli-suppress-mode;
        tailf:cli-delete-when-empty;
        tailf:cli-compact-syntax;
        key "name mib";
        leaf name {
          type string {
            tailf:info
              "WORD;;Name of the view";
          }
        }
        leaf mib {
          type string {
            tailf:info
              "WORD;;MIB view family name";
          }
        }
        leaf inc-exl {
          tailf:cli-drop-node-name;
          type enumeration {
            enum "excluded" {
              tailf:info
                "MIB family is excluded from the view";
            }
            enum "included" {
              tailf:info
                "MIB family is included in the view";
            }
          }
        }
      }
    }
    container dot11 {
      tailf:ncs-device-type "cli-ned";
      tailf:display-when "not(../../ncs:module) or ../../ncs:module[ncs:name='tailf-ned-cisco-ios']";
      tailf:info
        "IEEE 802.11 config commands";
      leaf syslog {
        tailf:info
          "Enable syslog";
        tailf:cli-full-command;
        type empty;
      }
    }
    container ipc {
      tailf:ncs-device-type "cli-ned";
      tailf:display-when "not(../../ncs:module) or ../../ncs:module[ncs:name='tailf-ned-cisco-ios']";
      tailf:info
        "Configure IPC system";
      container zone {
        tailf:info
          "Configure an IPC Zone";
        container default {
          tailf:info
            "Configure the default zone";
          tailf:cli-add-mode;
          tailf:cli-mode-name "config-ipczone";
          presence "true";
        }
      }
    }
    container cts {
      tailf:ncs-device-type "cli-ned";
      tailf:display-when "not(../../ncs:module) or ../../ncs:module[ncs:name='tailf-ned-cisco-ios']";
      tailf:info
        "Cisco Trusted Security commands";
      container logging {
        tailf:info
          "Set logging parameters";
        leaf verbose {
          tailf:info
            "Show verbose messages in system logs";
          type empty;
        }
      }
    }
    container license {
      tailf:ncs-device-type "cli-ned";
      tailf:display-when "not(../../ncs:module) or ../../ncs:module[ncs:name='tailf-ned-cisco-ios']";
      tailf:info
        "Configure license features";
      container accept {
        tailf:info
          "Accept all further License Agreements";
        container end {
          tailf:info
            "Accept all further License Agreements";
          container user {
            tailf:info
              "Accept all further License Agreements";
            leaf agreement {
              tailf:info
                "Accept all further License Agreements";
              type empty;
            }
          }
        }
      }
      container udi {
        tailf:cli-compact-syntax;
        tailf:cli-sequence-commands {
          tailf:cli-reset-all-siblings;
        }
        leaf pid {
          type string;
        }
        leaf sn {
          type string;
        }
      }
      list boot {
        tailf:info
          "license boot config commands";
        tailf:cli-suppress-mode;
        tailf:cli-delete-when-empty;
        ordered-by user;
        key "line";
        leaf line {
          tailf:cli-multi-word-key;
          type string {
            tailf:info
              "WORD;;License line";
          }
        }
      }
      container smart {
        tailf:info
          "Smart licensing";
        leaf enable {
          tailf:info
            "Enable Smart Licensing";
          type empty;
        }
      }
    }
    container trunk {
      tailf:ncs-device-type "cli-ned";
      tailf:display-when "not(../../ncs:module) or ../../ncs:module[ncs:name='tailf-ned-cisco-ios']";
      tailf:info
        "Global trunk configuration";
      list group {
        tailf:info
          "Specify a trunk group";
        tailf:cli-mode-name "config-trunk-group";
        key "name";
        leaf name {
          type string {
            tailf:info
              "WORD;;Trunk group label";
          }
        }
        container hunt-scheme {
          tailf:info
            "The hunt scheme in trunk group";
          choice hunt-scheme-choice {
            container round-robin {
              tailf:info
                "The next interface with free timeslots is selected";
              tailf:cli-compact-syntax;
              tailf:cli-delete-when-empty;
              presence "true";
            }
            leaf random {
              tailf:info
                "The timeslot is selected randomly";
              type empty;
            }
            leaf sequential {
              type empty;
            }
          }
        }
      }
    }
    list voice-card {
      tailf:ncs-device-type "cli-ned";
      tailf:display-when "not(../ncs:module) or ../ncs:module[ncs:name='tailf-ned-cisco-ios']";
      tailf:info
        "Configure a specific voice-card";
      tailf:cli-mode-name "config-voicecard";
      key "slot";
      leaf slot {
        type uint8 {
          tailf:info
            "<0-2>;;Voice interface slot #";
          range "0..2";
        }
      }
      leaf dspfarm {
        tailf:info
          "Enable dspFarm feature for this voice card";
        type empty;
      }
    }
    container voice {
      tailf:ncs-device-type "cli-ned";
      tailf:display-when "not(../../ncs:module) or ../../ncs:module[ncs:name='tailf-ned-cisco-ios']";
      tailf:info
        "Global voice configuration";
      container service {
        tailf:info
          "Global packet telephony service commands";
        container voip {
          tailf:info
            "Voice over IP";
          tailf:cli-add-mode;
          tailf:cli-mode-name "conf-voi-serv";
          container sip {
            tailf:info
              "SIP configuration commands";
            tailf:cli-add-mode;
            tailf:cli-mode-name "conf-serv-sip";
            tailf:cli-delete-when-empty;
            presence "true";
            container bind {
              tailf:info
                "SIP bind command";
              container control {
                tailf:info
                  "bind only SIP control packets";
                container source-interface {
                  tailf:info
                    "Specify interface for source address of SIP packets";
                  tailf:cli-compact-syntax;
                  uses interface-name-grouping;
                }
              }
              container media {
                tailf:info
                  "bind only SIP media packets";
                container source-interface {
                  tailf:info
                    "Specify interface for source address of SIP packets";
                  tailf:cli-compact-syntax;
                  uses interface-name-grouping;
                }
              }
            }
          }
        }
      }
      container iec {
        tailf:info
          "Configure Internal Error Code behavior";
        leaf syslog {
          tailf:info
            "Enable syslog reporting whenever an IEC is triggered";
          type empty;
        }
      }
      list translation-rule {
        tailf:info
          "Translation Rule configuration commands";
        tailf:cli-mode-name "cfg-translation-rule";
        key "tag";
        leaf tag {
          type uint32 {
            tailf:info
              "<1-2147483647>;;Translation rule tag";
            range "1..2147483647";
          }
        }
        list rule {
          tailf:info
            "Translation rule";
          tailf:cli-suppress-mode;
          tailf:cli-delete-when-empty;
          tailf:cli-incomplete-command;
          tailf:cli-compact-syntax;
          tailf:cli-sequence-commands {
            tailf:cli-reset-all-siblings;
          }
          ordered-by user;
          key "tag";
          leaf tag {
            type uint8 {
              tailf:info
                "<1-15>;;Translation rule tag";
              range "1..15";
            }
          }
          leaf reject {
            tailf:info
              "Call block rule";
            tailf:cli-optional-in-sequence;
            type empty;
          }
          leaf pattern {
            tailf:cli-drop-node-name;
            tailf:cli-full-command;
            tailf:cli-multi-value;
            type string {
              tailf:info
                "WORD;;Matching pattern";
            }
          }
        }
      }
      list translation-profile {
        tailf:info
          "Translation profile configuration commands";
        tailf:cli-mode-name "cfg-translation-profile";
        key "name";
        leaf name {
          type string {
            tailf:info
              "WORD;;Translation profile name";
          }
        }
        container translate {
          tailf:info
            "Specify numbers that should be translated";
          list called {
            tailf:info
              "Translation rule for the called-number";
            tailf:cli-suppress-mode;
            tailf:cli-delete-when-empty;
            key "tag";
            leaf tag {
              type uint32 {
                tailf:info
                  "<1-2147483647>;;Translation rule tag";
                range "1..2147483647";
              }
            }
          }
        }
      }
    }
    container event {
      tailf:ncs-device-type "cli-ned";
      tailf:display-when "not(../../ncs:module) or ../../ncs:module[ncs:name='tailf-ned-cisco-ios']";
      tailf:info
        "Event related configuration commands";
      container manager {
        tailf:info
          "Event Manager configuration commands";
        list environment {
          tailf:info
            "Set an Embedded Event Manager global environment variable";
          tailf:cli-suppress-mode;
          tailf:cli-delete-when-empty;
          key "name";
          leaf name {
            type string {
              tailf:info
                "WORD;;Name of the global environment variable";
            }
          }
          leaf value {
            tailf:cli-drop-node-name;
            type string {
              tailf:info
                "LINE;;Value of the global environment variable";
            }
          }
        }
        container directory {
          tailf:info
            "Set Embedded Event Manager directory information";
          container user {
            tailf:info
              "Set Embedded Event Manager user directory information";
            leaf policy {
              tailf:info
                "Set Embedded Event Manager user policy directory";
              type string {
                tailf:info
                  "WORD;;Path of the Embedded Event Manager user policy directory";
              }
            }
          }
        }
        list applet {
          tailf:info
            "Register an Event Manager applet";
          tailf:cli-mode-name "config-applet";
          tailf:cli-exit-command "exit" {
            tailf:info
              "Exit from Event Manager applet configuration submode";
          }
          key "name";
          leaf name {
            type string {
              tailf:info
                "WORD;;Name of the Event Manager applet";
            }
          }
          leaf description {
            tailf:info
              "Add or modify an applet description";
            tailf:cli-full-command;
            tailf:cli-multi-value;
            type string {
              tailf:info
                "LINE;;description";
            }
          }
          leaf authorization {
            tailf:info
              "Specify an authorization type for the applet";
            tailf:cli-hide-in-submode;
            type enumeration {
              enum "bypass" {
                tailf:info
                  "EEM aaa authorization type bypass";
              }
            }
          }
          leaf class {
            tailf:info
              "Specify a class for the applet";
            tailf:cli-hide-in-submode;
            type string {
              tailf:info
                "Class A-Z | default - default class";
              pattern '[A-Z]|default';
            }
          }
          leaf trap {
            tailf:info
              "Generate an SNMP trap when applet is triggered.";
            tailf:cli-hide-in-submode;
            type empty;
          }
          container event {
            tailf:info
              "Add or modify event information";
            uses event-manager-applet-event-grouping;
            list tag {
              tailf:info
                "event tag identifier";
              tailf:cli-suppress-mode;
              tailf:cli-delete-when-empty;
              key "name";
              leaf name {
                type string {
                  tailf:info
                    "WORD;;tag name";
                }
              }
              uses event-manager-applet-event-grouping;
            }
          }
          list action {
            tailf:info
              "Add or modify an action statement";
            tailf:cli-suppress-mode;
            tailf:cli-delete-when-empty;
            tailf:cli-compact-syntax;
            tailf:cli-reset-container;
            tailf:cli-incomplete-command;
            ordered-by user;
            key "name";
            leaf name {
              type string {
                tailf:info
                  "WORD;;Label";
              }
            }
            leaf cmd {
              tailf:cli-drop-node-name;
              tailf:cli-multi-value;
              type string {
                tailf:info
                  "Action string within quotes";
              }
            }
          }
          container trigger {
            tailf:info
              "Enter applet trigger configuration submode";
            tailf:cli-add-mode;
            tailf:cli-mode-name "config-applet-trigger";
          }
        }
        list policy {
          tailf:info
            "Run a pre-registered policy";
          tailf:cli-suppress-mode;
          tailf:cli-delete-when-empty;
          tailf:cli-compact-syntax;
          key "name";
          leaf name {
            type string {
              tailf:info
                "WORD;;Name of the Embedded Event Manager policy file";
            }
          }
          leaf type {
            tailf:info
              "Type of Embedded Event Manager policy";
            type enumeration {
              enum "system" {
                tailf:info
                  "Search for a Embedded Event Manager system policy";
              }
              enum "user" {
                tailf:info
                  "Search for a Embedded Event Manager user policy";
              }
            }
          }
        }
      }
    }
    leaf disable-eadi {
      tailf:ncs-device-type "cli-ned";
      tailf:display-when "not(../../ncs:module) or ../../ncs:module[ncs:name='tailf-ned-cisco-ios']";
      tailf:cli-full-command;
      type empty;
    }
    container memory-size {
      tailf:ncs-device-type "cli-ned";
      tailf:display-when "not(../../ncs:module) or ../../ncs:module[ncs:name='tailf-ned-cisco-ios']";
      tailf:info
        "Adjust memory size by percentage";
      leaf iomem {
        tailf:info
          "I/O memory";
        type uint8 {
          tailf:info
            "<5-25>;;percentage of DRAM to use for I/O memory: 5, 10, 15, 20, 25";
          range "5..25" {
            tailf:step "5";
          }
        }
      }
    }
    container transceiver {
      tailf:ncs-device-type "cli-ned";
      tailf:display-when "not(../../ncs:module) or ../../ncs:module[ncs:name='tailf-ned-cisco-ios']";
      tailf:info
        "Select from transceiver configuration commands";
      container type {
        tailf:info
          "type keyword";
        container all {
          tailf:cli-add-mode;
          tailf:cli-mode-name "config-xcvr-type";
          tailf:cli-full-command;
          container monitoring {
            tailf:info
              "Enable/disable monitoring";
            presence "true";
            leaf interval {
              tailf:info
                "Set interval for monitoring";
              type uint16 {
                tailf:info
                  "<300-3600>;;Time interval for monitoring transceiver in seconds";
                range "300..3600";
              }
            }
          }
        }
      }
    }
    list alias {
      tailf:ncs-device-type "cli-ned";
      tailf:display-when "not(../ncs:module) or ../ncs:module[ncs:name='tailf-ned-cisco-ios']";
      tailf:info
        "Create command alias";
      tailf:cli-suppress-mode;
      tailf:cli-delete-when-empty;
      ordered-by user;
      key "line";
      leaf line {
        tailf:cli-multi-word-key;
        type string {
          tailf:info
            "WORD;;alias line";
        }
      }
    }
  }
  augment "/ncs:devices/ncs:template/ncs:ned-id/ncs:config" {
    container upgrade {
      container fpd {
        leaf auto {
          type empty;
        }
        leaf path {
          type string;
        }
      }
    }
    container tailfned {
      leaf device {
        type string;
      }
      leaf police {
        type string;
      }
    }
    leaf version {
      type string;
    }
    container service {
      leaf config {
        type empty;
      }
      leaf exec-callback {
        type empty;
      }
      leaf nagle {
        type empty;
      }
      leaf slave-log {
        type string;
        // NCS drop default statement
      }
      container pad {
        leaf to-xot {
          type empty;
        }
        leaf from-xot {
          type empty;
        }
        leaf cmns {
          type empty;
        }
      }
      container conf {
        leaf pad {
          type string;
          // NCS drop default statement
        }
      }
      leaf tcp-keepalives-in {
        type empty;
      }
      leaf tcp-keepalives-out {
        type empty;
      }
      container timestamps {
        presence "true";
        container debug {
          choice timestamp-choice {
            leaf uptime {
              type empty;
            }
            container datetime {
              presence "true";
              leaf msec {
                type empty;
              }
              leaf localtime {
                type empty;
              }
              leaf show-timezone {
                type empty;
              }
              leaf year {
                type empty;
              }
            }
          }
        }
        container log {
          choice timestamp-choice {
            leaf uptime {
              type empty;
            }
            container datetime {
              presence "true";
              leaf msec {
                type empty;
              }
              leaf localtime {
                type empty;
              }
              leaf show-timezone {
                type empty;
              }
              leaf year {
                type empty;
              }
            }
          }
        }
      }
      container password-encryption {
        presence "true";
      }
      leaf exec-wait {
        type empty;
      }
      leaf linenumber {
        type empty;
      }
      leaf compress-config {
        type empty;
      }
      leaf udp-small-servers {
        type empty;
      }
      leaf tcp-small-servers {
        type empty;
      }
      leaf old-slip-prompts {
        type empty;
      }
      leaf pt-vty-logging {
        type empty;
      }
      leaf disable-ip-fast-frag {
        type empty;
      }
      leaf sequence-numbers {
        type empty;
      }
      container divert-rate-limit {
        list ip {
          // NCS patched for predictable order
          ordered-by user;
          key "divert-code";
          leaf divert-code {
            type string;
          }
          leaf rate {
            type string;
          }
          leaf limit {
            type string;
          }
        }
        list ipv6 {
          // NCS patched for predictable order
          ordered-by user;
          key "divert-code";
          leaf divert-code {
            type string;
          }
          leaf rate {
            type string;
          }
          leaf limit {
            type string;
          }
        }
        list trusted-site {
          // NCS patched for predictable order
          ordered-by user;
          key "ip-address mask-ip-address tos mask";
          // NCS drop max-elements statement
          leaf ip-address {
            type string;
          }
          leaf mask-ip-address {
            type string;
          }
          leaf tos {
            type string;
          }
          leaf mask {
            type string;
          }
        }
        list trusted-site-ipv6 {
          // NCS patched for predictable order
          ordered-by user;
          key "ip-address traffic-class mask";
          // NCS drop max-elements statement
          leaf ip-address {
            type string;
          }
          leaf traffic-class {
            type string;
          }
          leaf mask {
            type string;
          }
        }
      }
      container counters {
        container max {
          leaf age {
            type string;
          }
        }
      }
      container alignment {
        leaf detection {
          type string;
          // NCS drop default statement
        }
        leaf logging {
          type string;
          // NCS drop default statement
        }
      }
      leaf call-home {
        type empty;
      }
      leaf dhcp {
        type string;
        // NCS drop default statement
      }
      leaf finger {
        type empty;
      }
      container heartbeat {
        leaf fatal-count {
          type string;
        }
        leaf interrupt-interval {
          type string;
        }
        leaf interrupt-max {
          type string;
        }
        leaf transmit-interval {
          type string;
        }
        leaf warning-timeout {
          type string;
        }
      }
      leaf hide-telnet-addresses {
        type empty;
      }
      leaf unsupported-transceiver {
        type empty;
      }
      leaf internal {
        type empty;
      }
    }
    container cdp {
      leaf run {
        type string;
        // NCS drop default statement
      }
    }
    list platform {
      // NCS patched for predictable order
      ordered-by user;
      key "name";
      leaf name {
        type string;
      }
    }
    leaf hostname {
      type string;
    }
    container vrf {
      list definition {
        // NCS patched for predictable order
        ordered-by user;
        key "name";
        leaf name {
          type string;
        }
        leaf description {
          type string;
        }
        leaf rd {
          type string;
        }
        container route-target {
          uses ncs_template_vrf-route-target-grouping;
        }
        container address-family {
          container ipv4 {
            presence "true";
            uses ncs_template_vrf-definition-af-grouping;
            container mdt {
              container default {
                leaf address {
                  type string;
                }
                container mpls {
                  leaf mldp {
                    type string;
                  }
                }
              }
              container data {
                list multicast {
                  // NCS patched for predictable order
                  ordered-by user;
                  key "address wildcard";
                  leaf address {
                    type string;
                  }
                  leaf wildcard {
                    type string;
                  }
                }
                leaf list {
                  type string;
                }
                leaf threshold {
                  type string;
                }
              }
              leaf log-reuse {
                type empty;
              }
              leaf-list preference {
                // NCS patched for predictable order
                ordered-by user;
                type string;
              }
            }
          }
          container ipv6 {
            presence "true";
            uses ncs_template_vrf-definition-af-grouping;
          }
        }
      }
    }
    container security {
      container passwords {
        leaf min-length {
          type string;
        }
      }
    }
    container enable {
      container password {
        uses ncs_template_password-07-grouping;
        list level {
          // NCS patched for predictable order
          ordered-by user;
          key "level";
          leaf level {
            type string;
          }
          uses ncs_template_password-07-grouping;
        }
      }
      leaf last-resort {
        type string;
      }
      container secret {
        leaf level {
          type string;
        }
        leaf type {
          type string;
        }
        leaf secret {
          type string;
        }
      }
      leaf use-tacacs {
        type empty;
      }
    }
    container aaa {
      leaf new-model {
        type empty;
      }
      container group {
        // NCS drop tailf-common:cli-diff-dependency statement
        container server {
          list radius {
            // NCS patched for predictable order
            ordered-by user;
            key "name";
            leaf name {
              type string;
            }
            container server {
              list name {
                // NCS patched for predictable order
                ordered-by user;
                key "name";
                leaf name {
                  type string;
                }
              }
              list direct {
                // NCS patched for predictable order
                ordered-by user;
                key "name";
                leaf name {
                  type string;
                }
                leaf auth-port {
                  type string;
                }
                leaf acct-port {
                  type string;
                }
              }
            }
            container ip {
              container radius {
                container source-interface {
                  uses ncs_template_interface-name-grouping;
                }
              }
              container vrf {
                leaf forwarding {
                  // NCS drop tailf-common:cli-diff-dependency statement
                  // NCS drop tailf-common:cli-diff-dependency statement
                  type string;
                }
              }
            }
          }
          list tacacsplus {
            // NCS patched for predictable order
            ordered-by user;
            tailf:alt-name "tacacs+";
            key "name";
            leaf name {
              type string;
            }
            list server-private {
              // NCS patched for predictable order
              ordered-by user;
              key "name";
              leaf name {
                type string;
              }
              leaf timeout {
                type string;
              }
              container key {
                leaf encryption {
                  type string;
                }
                leaf key {
                  type string;
                }
              }
            }
            container ip {
              container tacacs {
                container source-interface {
                  uses ncs_template_interface-name-grouping;
                }
              }
            }
          }
        }
      }
      container authentication {
        // NCS drop tailf-common:cli-diff-dependency statement
        list dot1x {
          // NCS patched for predictable order
          ordered-by user;
          key "name";
          leaf name {
            type string;
          }
          leaf cache {
            type string;
          }
          leaf group {
            type string;
          }
        }
        list login {
          // NCS patched for predictable order
          ordered-by user;
          key "name";
          leaf name {
            type string;
          }
          uses ncs_template_aaa-authentication-method-grouping;
        }
        container enable {
          container default {
            leaf cache {
              type string;
            }
            leaf group {
              type string;
            }
            leaf line {
              type empty;
            }
            leaf enable {
              type empty;
            }
            leaf none {
              type empty;
            }
          }
        }
        list ppp {
          // NCS patched for predictable order
          ordered-by user;
          key "name";
          leaf name {
            type string;
          }
          uses ncs_template_aaa-authentication-method-grouping;
        }
      }
      container authorization {
        // NCS drop tailf-common:cli-diff-dependency statement
        leaf console {
          type empty;
        }
        leaf config-commands {
          type empty;
        }
        list exec {
          // NCS patched for predictable order
          ordered-by user;
          key "name";
          leaf name {
            type string;
          }
          uses ncs_template_aaa-authorization-method-grouping;
        }
        list commands {
          // NCS patched for predictable order
          ordered-by user;
          key "level name";
          leaf level {
            type string;
          }
          leaf name {
            type string;
          }
          uses ncs_template_aaa-authorization-method-grouping;
        }
        list eventmanager {
          // NCS patched for predictable order
          ordered-by user;
          key "name";
          leaf name {
            type string;
          }
          uses ncs_template_aaa-authorization-method-grouping;
        }
        list network {
          // NCS patched for predictable order
          ordered-by user;
          key "name";
          leaf name {
            type string;
          }
          uses ncs_template_aaa-authorization-method-grouping;
        }
      }
      container accounting {
        // NCS drop tailf-common:cli-diff-dependency statement
        list commands {
          // NCS patched for predictable order
          ordered-by user;
          key "level name";
          leaf level {
            type string;
          }
          leaf name {
            type string;
          }
          uses ncs_template_aaa-accounting-method-grouping;
        }
        list exec {
          // NCS patched for predictable order
          ordered-by user;
          key "name";
          leaf name {
            type string;
          }
          uses ncs_template_aaa-accounting-method-grouping;
        }
        list network {
          // NCS patched for predictable order
          ordered-by user;
          key "name";
          leaf name {
            type string;
          }
          uses ncs_template_aaa-accounting-method-grouping;
        }
        list connection {
          // NCS patched for predictable order
          ordered-by user;
          key "name";
          leaf name {
            type string;
          }
          uses ncs_template_aaa-accounting-method-grouping;
        }
        container system {
          container default {
            presence "true";
            uses ncs_template_aaa-accounting-method-grouping;
          }
        }
        container suppress {
          leaf null-username {
            type empty;
          }
        }
        container update {
          leaf periodic {
            type string;
          }
        }
      }
      leaf session-id {
        // NCS drop tailf-common:cli-diff-dependency statement
        type string;
      }
      container attribute {
        list list {
          // NCS patched for predictable order
          ordered-by user;
          key "name";
          leaf name {
            type string;
          }
          container attribute {
            container type {
              leaf interface-config {
                type string;
              }
            }
          }
        }
      }
    }
    container clock {
      container timezone {
        leaf zone {
          type string;
        }
        leaf offset {
          type string;
        }
        leaf hours {
          type string;
        }
        leaf minutes {
          type string;
        }
      }
      container summer-time {
        leaf zone {
          type string;
        }
        choice summer-choice {
          case date-case {
            leaf date {
              type empty;
            }
          }
          case recurring-case {
            leaf recurring {
              type empty;
            }
            leaf start {
              type string;
            }
            leaf start-day {
              type string;
            }
            leaf start-month {
              type string;
            }
            leaf start-time {
              type string;
            }
            leaf end {
              type string;
            }
            leaf end-day {
              type string;
            }
            leaf end-month {
              type string;
            }
            leaf end-time {
              type string;
            }
          }
        }
      }
      container calendar-valid {
        presence "true";
      }
    }
    container facility-alarm {
      container core-temperature {
        uses ncs_template_facility-alarm-grouping;
      }
      container outlet-temperature {
        uses ncs_template_facility-alarm-grouping;
      }
      container intake-temperature {
        uses ncs_template_facility-alarm-grouping;
      }
      container critical {
        leaf exceed-action {
          type string;
        }
      }
    }
    container cef {
      container table {
        container output-chain {
          container build {
            leaf favor {
              type string;
            }
          }
        }
      }
    }
    container ipdr {
      list session {
        // NCS patched for predictable order
        ordered-by user;
        key "session-id";
        leaf session-id {
          type string;
        }
        leaf session-name {
          type string;
        }
        leaf session-descr {
          type string;
        }
      }
      list type {
        // NCS patched for predictable order
        ordered-by user;
        key "session-id";
        leaf session-id {
          type string;
        }
        choice type-choice {
          leaf ad-hoc {
            type empty;
          }
          leaf event {
            type empty;
          }
          leaf time-interval {
            type string;
          }
        }
      }
      list collector {
        // NCS patched for predictable order
        ordered-by user;
        key "name";
        leaf name {
          type string;
        }
        leaf ip-addr {
          type string;
        }
        leaf port {
          type string;
        }
      }
      list associate {
        // NCS patched for predictable order
        ordered-by user;
        key "session-id";
        leaf session-id {
          type string;
        }
        leaf collector-name {
          type string;
        }
        leaf priority {
          type string;
        }
      }
      list template {
        // NCS patched for predictable order
        ordered-by user;
        key "session-id";
        leaf session-id {
          type string;
        }
        leaf template-name {
          type string;
        }
      }
      container exporter {
        leaf start {
          type empty;
        }
      }
    }
    container card {
      list card-slot {
        // NCS patched for predictable order
        ordered-by user;
        key "slot card-type";
        leaf slot {
          type string;
        }
        leaf card-type {
          type string;
        }
      }
      list card-slot-subslot {
        // NCS patched for predictable order
        ordered-by user;
        key "slot-subslot card-type";
        leaf slot-subslot {
          type string;
        }
        leaf card-type {
          type string;
        }
        leaf SPA-DOCSIS-HD-V1-port {
          // NCS drop when statement
          type string;
        }
        leaf license {
          type string;
        }
      }
      container type {
        list t1 {
          // NCS patched for predictable order
          ordered-by user;
          key "slot";
          leaf slot {
            type string;
          }
        }
        container t1-bay {
          list t1 {
            // NCS patched for predictable order
            ordered-by user;
            key "slot bay";
            leaf slot {
              type string;
            }
            leaf bay {
              type string;
            }
          }
        }
        list t3 {
          // NCS patched for predictable order
          ordered-by user;
          key "slot";
          leaf slot {
            type string;
          }
        }
      }
    }
    container hw-module {
      list bay {
        // NCS patched for predictable order
        ordered-by user;
        key "name";
        leaf name {
          type string;
        }
        leaf shutdown {
          type empty;
        }
        choice power-choice {
          leaf powered {
            type empty;
          }
          leaf unpowered {
            type empty;
          }
        }
      }
    }
    container cable {
      container upstream {
        container rate-adapt {
          leaf priority {
            type string;
          }
          leaf rate {
            type string;
          }
          leaf local {
            type empty;
          }
        }
      }
      container admission-control {
        container preempt {
          leaf priority-voice {
            type empty;
          }
        }
      }
      container flap-list {
        leaf aging {
          type string;
        }
      }
      container source-verify {
        container leasequery-filter {
          container downstream {
            leaf threshold {
              type string;
            }
            leaf interval {
              type string;
            }
          }
        }
      }
      container modem {
        container remote-query {
          container gather {
            leaf polling-interval {
              type string;
            }
            leaf community-string {
              type string;
            }
          }
          leaf src-ip {
            type string;
          }
        }
        leaf max-cpe {
          type string;
        }
        leaf v6-max-cpe-prefix {
          type string;
        }
        list vendor {
          // NCS patched for predictable order
          ordered-by user;
          key "oui";
          leaf oui {
            type string;
          }
          leaf vendor-name {
            type string;
          }
        }
      }
      container modulation-profile {
        list modulation-profile-list {
          // NCS patched for predictable order
          ordered-by user;
          key "profile";
          leaf profile {
            type string;
          }
          container request {
            uses ncs_template_cable-modulation-profile-grouping;
          }
          container initial {
            uses ncs_template_cable-modulation-profile-grouping;
          }
          container station {
            uses ncs_template_cable-modulation-profile-grouping;
          }
          container short {
            uses ncs_template_cable-modulation-profile-grouping;
          }
          container long {
            uses ncs_template_cable-modulation-profile-grouping;
          }
          container a-short {
            uses ncs_template_cable-modulation-profile-grouping;
          }
          container a-long {
            uses ncs_template_cable-modulation-profile-grouping;
          }
          container a-ugs {
            uses ncs_template_cable-modulation-profile-grouping;
          }
        }
      }
      list tag {
        // NCS patched for predictable order
        ordered-by user;
        key "id";
        leaf id {
          type string;
        }
        leaf name {
          type string;
        }
        leaf docsis-version {
          type string;
        }
        leaf service-class {
          type string;
        }
      }
      container service {
        list class {
          // NCS patched for predictable order
          ordered-by user;
          key "class-index";
          leaf class-index {
            type string;
          }
          leaf name {
            type string;
          }
          leaf downstream {
            type empty;
          }
          leaf upstream {
            type empty;
          }
          leaf peak-rate {
            type string;
          }
          leaf max-concat-burst {
            type string;
          }
          container tos-overwrite {
            leaf and-mask {
              type string;
            }
            leaf or-mask {
              type string;
            }
          }
          leaf max-rate {
            type string;
          }
          leaf max-burst {
            type string;
          }
          leaf min-rate {
            type string;
          }
          leaf priority {
            type string;
          }
          leaf sched-type {
            type string;
          }
        }
        container attribute {
          container ds-bonded {
            container downstream-type {
              container bonding-enabled {
                presence "true";
                leaf enforce {
                  type empty;
                }
              }
            }
          }
          container withhold-tlvs {
            leaf peak-rate {
              type empty;
            }
          }
        }
      }
      container qos {
        container permission {
          leaf create {
            type empty;
          }
          leaf update {
            type empty;
          }
          leaf modems {
            type empty;
          }
        }
      }
      container filter {
        list group {
          // NCS patched for predictable order
          ordered-by user;
          key "group-id";
          leaf group-id {
            type string;
          }
          list index {
            // NCS patched for predictable order
            ordered-by user;
            key "index-num";
            leaf index-num {
              type string;
            }
            leaf src-ip {
              type string;
            }
            leaf src-mask {
              type string;
            }
            leaf dest-ip {
              type string;
            }
            leaf dest-mask {
              type string;
            }
            leaf v6-src-address {
              type string;
            }
            leaf v6-src-pfxlen {
              type string;
            }
            leaf v6-dest-address {
              type string;
            }
            leaf v6-dest-pfxlen {
              type string;
            }
            leaf v6-flow-label {
              type string;
            }
            leaf ip-proto {
              type string;
            }
            container ip-tos {
              leaf tos-mask {
                type string;
              }
              leaf tos-value {
                type string;
              }
            }
            leaf src-port {
              type string;
            }
            leaf dest-port {
              type string;
            }
            leaf ip-version {
              type string;
              // NCS drop default statement
            }
            container tcp-flags {
              leaf flags-mask {
                type string;
              }
              leaf flags-value {
                type string;
              }
            }
            leaf match-action {
              type string;
            }
            leaf status {
              type string;
              // NCS drop default statement
            }
          }
        }
      }
      container submgmt {
        container default {
          container filter-group {
            container cm {
              uses ncs_template_cable-submgmt-default-filter-group-grouping;
            }
            container cpe {
              uses ncs_template_cable-submgmt-default-filter-group-grouping;
            }
            container mta {
              uses ncs_template_cable-submgmt-default-filter-group-grouping;
            }
            container stb {
              uses ncs_template_cable-submgmt-default-filter-group-grouping;
            }
            container ps {
              uses ncs_template_cable-submgmt-default-filter-group-grouping;
            }
          }
          leaf active {
            type empty;
          }
        }
      }
      container logging {
        container badipsource {
          presence "true";
          leaf buffer-size {
            type string;
          }
        }
        container layer2events {
          presence "true";
          leaf buffer-size {
            type string;
          }
        }
        container overlapip {
          presence "true";
          leaf buffer-size {
            type string;
          }
        }
        container ironbus {
          presence "true";
          leaf buffer-size {
            type string;
          }
        }
        container downstream-index {
          presence "true";
          leaf buffer-size {
            type string;
          }
        }
      }
      container default-tos-qos10 {
        container tos-overwrite {
          leaf tos-and {
            type string;
          }
          leaf tos-or {
            type string;
          }
        }
      }
      container primary-sflow-qos11 {
        leaf keep {
          type string;
        }
      }
      container sflog {
        leaf max-entry {
          type string;
        }
        leaf entry-duration {
          type string;
        }
      }
      container dynamic-secret {
        container exclude {
          leaf modem {
            type string;
          }
          leaf oui {
            type string;
          }
        }
        container tftp {
          leaf insert-upgrade-server {
            type empty;
          }
        }
      }
      container docsis30-voice {
        container downstream {
          leaf req-attr-mask {
            type string;
          }
          leaf forb-attr-mask {
            type string;
          }
        }
      }
      leaf util-interval {
        type string;
      }
      container clock {
        leaf dti {
          type empty;
        }
      }
      container bgsync {
        leaf active {
          type string;
          // NCS drop default statement
        }
        leaf ptime {
          type string;
          // NCS drop default statement
        }
        leaf itime {
          type string;
          // NCS drop default statement
        }
      }
      container privacy {
        leaf encrypt-alg-priority {
          type string;
        }
      }
      container dsg {
        list client-list {
          // NCS patched for predictable order
          ordered-by user;
          key "client-list-id";
          leaf client-list-id {
            type string;
          }
          list id-index {
            // NCS patched for predictable order
            ordered-by user;
            key "id";
            leaf id {
              type string;
            }
            choice parameter-choice {
              leaf application-id {
                type string;
              }
              leaf broadcast {
                type string;
              }
              leaf ca-system-id {
                type string;
              }
              leaf mac-addr {
                type string;
              }
            }
          }
        }
        list tg {
          // NCS patched for predictable order
          ordered-by user;
          key "group-id";
          leaf group-id {
            type string;
          }
          list channel {
            // NCS patched for predictable order
            ordered-by user;
            key "channel-id";
            leaf channel-id {
              type string;
            }
            leaf priority {
              type string;
            }
            leaf status {
              type string;
              // NCS drop default statement
            }
          }
        }
        list tunnel {
          // NCS patched for predictable order
          ordered-by user;
          key "tunnel-id";
          leaf tunnel-id {
            type string;
          }
          leaf mac-addr {
            type string;
          }
          leaf tg {
            type string;
          }
          leaf clients {
            type string;
          }
          leaf status {
            type string;
            // NCS drop default statement
          }
        }
        list cfr {
          // NCS patched for predictable order
          ordered-by user;
          key "index";
          leaf index {
            type string;
          }
          leaf dest-ip {
            type string;
          }
          leaf tunnel {
            type string;
          }
          leaf priority {
            type string;
          }
          leaf src-ip {
            type string;
          }
          leaf in-dcd {
            type string;
          }
        }
        list timer {
          // NCS patched for predictable order
          ordered-by user;
          key "index";
          leaf index {
            type string;
          }
          leaf Tdsg1 {
            type string;
          }
          leaf Tdsg2 {
            type string;
          }
          leaf Tdsg3 {
            type string;
          }
          leaf Tdsg4 {
            type string;
          }
        }
      }
      container load-balance {
        leaf docsis-enable {
          type empty;
        }
        leaf docsis30-enable {
          type empty;
        }
        container modem {
          leaf max-failures {
            type string;
          }
        }
        list rule {
          // NCS patched for predictable order
          ordered-by user;
          key "rule-id";
          leaf rule-id {
            type string;
          }
          choice status-choice {
            container ds {
              container disable-throughput-lowerbound {
                leaf ds {
                  type string;
                }
              }
            }
            container us {
              container disable-throughput-lowerbound {
                leaf us {
                  type string;
                }
              }
            }
            leaf disabled {
              type empty;
            }
            leaf enabled {
              type empty;
            }
          }
        }
        list docsis-policy {
          // NCS patched for predictable order
          ordered-by user;
          key "policy-id";
          leaf policy-id {
            type string;
          }
          list rule {
            // NCS patched for predictable order
            ordered-by user;
            key "rule-id";
            leaf rule-id {
              type string;
            }
          }
          leaf tag {
            type string;
          }
          leaf override {
            type empty;
          }
        }
        container d30-ggrp-default {
          leaf disable {
            type empty;
          }
          leaf init-tech-list {
            type string;
          }
          leaf docsis-policy {
            type string;
          }
        }
        container docsis-group {
          list FN {
            // NCS patched for predictable order
            ordered-by user;
            key "fn-id";
            leaf fn-id {
              type string;
            }
            container MD {
              leaf Cable {
                type string;
              }
            }
            uses ncs_template_cable-load-balance-docsis-group-grouping;
          }
          list docsis-group-list {
            // NCS patched for predictable order
            ordered-by user;
            key "docsis-group-id";
            leaf docsis-group-id {
              type string;
            }
            uses ncs_template_cable-load-balance-docsis-group-grouping;
          }
        }
        container exclude {
          list oui {
            // NCS patched for predictable order
            ordered-by user;
            key "word";
            leaf word {
              type string;
            }
            leaf assignment {
              type empty;
            }
            leaf enforce {
              type empty;
            }
            leaf static {
              type empty;
            }
            leaf strict {
              type empty;
            }
          }
        }
      }
      container metering {
        choice cable-metering-choice {
          container destination {
            leaf ip-address {
              type string;
            }
            leaf port {
              type string;
            }
            leaf ip-address2 {
              type string;
            }
            leaf port2 {
              // NCS drop when statement
              type string;
            }
            leaf retries {
              type string;
            }
            leaf minutes {
              type string;
            }
            leaf security {
              type string;
            }
            leaf flow-aggregate {
              type empty;
            }
            leaf cpe-list-suppress {
              type empty;
            }
            leaf full-records {
              type empty;
            }
          }
          container ipdr-d3 {
            container session {
              leaf session-id {
                type string;
              }
              leaf type {
                type string;
              }
              leaf flow-aggregate {
                type empty;
              }
              leaf full-records {
                type empty;
              }
            }
          }
        }
        container source-interface {
          uses ncs_template_interface-name-grouping;
        }
        container data-per-session {
          leaf data-per-session {
            type string;
          }
          leaf timer {
            type string;
          }
        }
      }
      container rf-change-trigger {
        leaf percent {
          type string;
        }
        leaf count {
          type string;
        }
        leaf secondary {
          type empty;
        }
      }
      container throttle-modem {
        leaf init-rate {
          type string;
        }
        leaf holdoff-time {
          type string;
        }
        leaf flush-rate {
          type string;
        }
      }
      container ds-max-burst {
        presence "true";
        choice optional {
          leaf burst-threshold {
            type string;
            // NCS drop default statement
          }
          leaf peak-rate {
            type string;
          }
        }
      }
      container acfe {
        leaf enable {
          type empty;
        }
      }
      container l2-vpn-service {
        container xconnect {
          container nsi {
            container dot1q {
              presence "true";
              container interface {
                uses ncs_template_interface-name-grouping;
              }
            }
            container mpls {
              presence "true";
            }
          }
        }
      }
      list dot1q-vc-map {
        // NCS patched for predictable order
        ordered-by user;
        key "mac-address";
        leaf mac-address {
          type string;
        }
        container ethernet-interface {
          uses ncs_template_interface-name-grouping;
        }
        leaf vlan-id {
          type string;
        }
        leaf cust-name {
          type string;
        }
      }
      list l2vpn {
        // NCS patched for predictable order
        ordered-by user;
        key "mac-address";
        leaf mac-address {
          type string;
        }
        leaf customer-name {
          type string;
        }
        container service {
          list instance {
            // NCS patched for predictable order
            ordered-by user;
            // NCS drop max-elements statement
            key "id";
            leaf id {
              type string;
            }
            leaf ethernet {
              type empty;
            }
            uses ncs_template_interface-xconnect-grouping;
            container cable {
              container set {
                leaf mpls-experimental {
                  type string;
                }
              }
            }
          }
        }
      }
      container wideband {
        leaf auto-reset {
          type empty;
        }
      }
      list rcc-template {
        // NCS patched for predictable order
        ordered-by user;
        key "index";
        leaf index {
          type string;
        }
        leaf rcp-id {
          type string;
        }
        list receive-module {
          // NCS patched for predictable order
          ordered-by user;
          key "index";
          leaf index {
            type string;
          }
          leaf first-center-frequency {
            type string;
          }
          leaf connected-receive-module {
            type string;
          }
        }
        list receive-channel {
          // NCS patched for predictable order
          ordered-by user;
          key "index";
          leaf index {
            type string;
          }
          leaf center-frequency {
            type string;
          }
          leaf connected-receive-module {
            type string;
          }
          leaf primary {
            type empty;
          }
        }
      }
      list fiber-node {
        // NCS patched for predictable order
        ordered-by user;
        key "fiber-node-id";
        leaf fiber-node-id {
          type string;
        }
        leaf description {
          type string;
        }
        container downstream {
          choice downstream-choice {
            leaf Modular-Cable {
              type string;
            }
            leaf Cable {
              type string;
            }
          }
          leaf rf-channel {
            type string;
          }
        }
        container upstream {
          leaf Cable {
            type string;
          }
          leaf connector {
            type string;
          }
        }
      }
      container ipv6 {
        container pd-route {
          leaf prefix {
            type string;
          }
          leaf Bundle {
            type string;
          }
        }
        container source-verify {
          container leasequery-filter {
            container downstream {
              leaf threshold {
                type string;
              }
              leaf interval {
                type string;
              }
            }
          }
        }
      }
    }
    list l2tp-class {
      // NCS patched for predictable order
      ordered-by user;
      key "l2tp-class-name";
      leaf l2tp-class-name {
        type string;
      }
      leaf hello {
        type string;
        // NCS drop default statement
      }
      container retransmit {
        leaf retries {
          type string;
        }
        container timeout {
          choice timeout-choice {
            leaf max {
              type string;
            }
            leaf min {
              type string;
            }
          }
        }
      }
    }
    container packetcable {
      presence "true";
      leaf multimedia {
        type empty;
      }
    }
    list depi-class {
      // NCS patched for predictable order
      ordered-by user;
      key "depi-class-name";
      leaf depi-class-name {
        type string;
      }
      container mode {
        leaf mpt {
          type empty;
        }
      }
    }
    list depi-tunnel {
      // NCS patched for predictable order
      ordered-by user;
      key "depi-tunnel-name";
      leaf depi-tunnel-name {
        type string;
      }
      leaf dest-ip {
        type string;
      }
      leaf l2tp-class {
        type string;
      }
      leaf depi-class {
        type string;
      }
      leaf protect-tunnel {
        type string;
      }
    }
    list chat-script {
      // NCS patched for predictable order
      ordered-by user;
      key "name";
      leaf name {
        type string;
      }
      leaf line {
        type string;
      }
    }
    container autonomic {
      container registrar {
        leaf domain-id {
          type string;
        }
        container CA {
          leaf local {
            type empty;
          }
        }
      }
    }
    container controller {
      list controller-tx-ex-list {
        // NCS patched for predictable order
        ordered-by user;
        key "name number";
        leaf name {
          type string;
        }
        leaf number {
          type string;
        }
        leaf framing {
          type string;
        }
        container clock {
          container source {
            choice source-choice {
              container line {
                presence "true";
                leaf line-mode {
                  type string;
                }
              }
              leaf internal {
                type empty;
              }
              leaf loop-timed {
                type empty;
              }
              leaf free-running {
                type empty;
              }
            }
          }
        }
        leaf linecode {
          type string;
        }
        container cablelength {
          choice cablelength-choice {
            leaf value {
              type string;
            }
            leaf long {
              type string;
            }
            leaf short {
              type string;
            }
          }
        }
        container pri-group {
          list timeslots {
            // NCS patched for predictable order
            ordered-by user;
            key "id";
            leaf id {
              type string;
            }
            leaf nfas_d {
              type string;
            }
            leaf nfas_int {
              // NCS drop when statement
              type string;
            }
            leaf nfas_group {
              // NCS drop when statement
              type string;
            }
            leaf service {
              type string;
            }
          }
        }
        list channel-group {
          // NCS patched for predictable order
          ordered-by user;
          key "number";
          leaf number {
            type string;
          }
          leaf-list timeslots {
            // NCS patched for predictable order
            ordered-by user;
            type string;
          }
        }
        leaf description {
          type string;
        }
        list t1 {
          // NCS patched for predictable order
          ordered-by user;
          key "id";
          leaf id {
            type string;
          }
          leaf channel-group {
            type string;
          }
          leaf-list timeslots {
            // NCS patched for predictable order
            ordered-by user;
            type string;
          }
          leaf speed {
            type string;
          }
        }
        leaf shutdown {
          type empty;
        }
      }
      container BITS {
        container input {
          container applique {
            container E1 {
              choice E1-choice {
                case clock-case {
                  leaf clock-if {
                    type string;
                  }
                }
                case framing-case {
                  leaf framing {
                    type string;
                  }
                  leaf linecode {
                    type string;
                  }
                }
              }
            }
          }
        }
      }
      list Cellular {
        // NCS patched for predictable order
        ordered-by user;
        key "id";
        leaf id {
          type string;
        }
        leaf description {
          type string;
        }
        container lte {
          container gps {
            leaf enable {
              type empty;
            }
            container mode {
              leaf standalone {
                type empty;
              }
            }
            container nmea {
              choice nmea-choice {
                container ip {
                  presence "true";
                }
                container serial {
                  presence "true";
                  leaf streaming {
                    type string;
                  }
                }
              }
            }
          }
          container modem {
            container link-recovery {
              leaf enable {
                type empty;
              }
              container rssi {
                leaf onset-threshold {
                  type string;
                }
              }
              leaf monitor-timer {
                type string;
              }
              leaf wait-timer {
                type string;
              }
              leaf debounce-count {
                type string;
              }
            }
          }
        }
      }
      list Modular-Cable {
        // NCS patched for predictable order
        ordered-by user;
        key "name";
        leaf name {
          type string;
        }
        leaf ip-address {
          type string;
        }
        container modular-host {
          leaf subslot {
            type string;
          }
        }
        list rf-channel {
          // NCS patched for predictable order
          ordered-by user;
          key "rf-port";
          leaf rf-port {
            type string;
          }
          leaf description {
            type string;
          }
          container cable {
            container downstream {
              leaf channel-id {
                type string;
              }
            }
          }
          container frequency {
            leaf freq {
              type string;
            }
            leaf annex {
              type string;
            }
            leaf modulation {
              type string;
            }
            leaf interleave-depth {
              type string;
            }
          }
          container ip-address {
            leaf ip-address {
              type string;
            }
            leaf mac-address {
              type string;
            }
            leaf depi-remote-id {
              type string;
            }
            leaf eqam-headroom {
              type string;
            }
          }
          container depi-tunnel {
            leaf depi-tunnel-name {
              type string;
            }
            leaf tsid {
              type string;
            }
          }
          leaf rf-power {
            type string;
          }
          leaf rf-shutdown {
            type string;
            // NCS drop default statement
          }
        }
      }
      list wanphy {
        // NCS patched for predictable order
        ordered-by user;
        key "name";
        leaf name {
          type string;
        }
      }
    }
    container ip {
      leaf subnet-zero {
        type string;
        // NCS drop default statement
      }
      leaf source-route {
        type string;
        // NCS drop default statement
      }
      leaf routing {
        // NCS drop tailf-common:cli-diff-dependency statement
        type string;
        // NCS drop default statement
      }
      container arp {
        container proxy {
          leaf disable {
            type empty;
          }
        }
        container inspection {
          leaf-list bridge-domain {
            // NCS patched for predictable order
            ordered-by user;
            type string;
          }
          container bridge-domain-list {
            list bridge-domain {
              // NCS patched for predictable order
              ordered-by user;
              key "id";
              leaf id {
                type string;
              }
              container logging {
                choice logging-choice {
                  leaf acl-match {
                    type string;
                  }
                  leaf dhcp-bindings {
                    type string;
                  }
                }
              }
            }
          }
          leaf-list validate {
            // NCS patched for predictable order
            ordered-by user;
            type string;
          }
          container log-buffer {
            leaf entries {
              type string;
            }
            container logs {
              leaf number {
                type string;
              }
              leaf interval {
                type string;
              }
            }
          }
        }
      }
      choice gratuitous-arps-choice {
        container gratuitous-arps-conf {
          leaf gratuitous-arps {
            type string;
          }
        }
        container gratuitous-arps {
          leaf non-local {
            type string;
            // NCS drop default statement
          }
        }
        // NCS drop default statement
      }
      container cef-conf {
        leaf cef {
          type empty;
        }
      }
      container cef {
        leaf distributed {
          type empty;
        }
        container optimize {
          container neighbor {
            leaf resolution {
              type string;
              // NCS drop default statement
            }
          }
        }
      }
      list vrf {
        // NCS patched for predictable order
        ordered-by user;
        key "name";
        leaf name {
          type string;
        }
        leaf description {
          type string;
        }
        leaf rd {
          type string;
        }
        container vpn {
          leaf id {
            type string;
          }
        }
        leaf context {
          type string;
        }
        container import {
          leaf map {
            // NCS drop tailf-common:cli-diff-dependency statement
            type string;
          }
          container ipv4 {
            // NCS drop tailf-common:cli-diff-dependency statement
            leaf ipv4-type {
              type string;
            }
            leaf upper-limit {
              type string;
            }
            leaf map {
              type string;
            }
          }
        }
        container export {
          leaf map {
            type string;
          }
        }
        container maximum {
          presence "true";
          leaf routes {
            type string;
          }
          choice maximum-choice {
            // NCS drop mandatory statement
            case threshold-case {
              leaf threshold {
                type string;
              }
              leaf reinstall {
                type string;
              }
            }
            case warning-case {
              leaf warning-only {
                type empty;
              }
            }
          }
        }
        container bgp {
          container next-hop {
            leaf Loopback {
              type string;
            }
          }
        }
        container mdt {
          presence "Backbone Multicast Distribution Tree";
          leaf default {
            type string;
          }
          container data {
            leaf mulicast-address {
              type string;
            }
            leaf wildcard-bits {
              type string;
            }
            choice mdt-data-choice {
              case mdt-data-threshold {
                leaf threshold {
                  type string;
                }
                leaf threshold-list {
                  tailf:alt-name "list";
                  type string;
                }
              }
              case mdt-data-list {
                leaf list {
                  type string;
                }
              }
            }
          }
          leaf log-reuse {
            type empty;
          }
        }
        list route-target {
          // NCS patched for predictable order
          ordered-by user;
          key "direction target";
          leaf direction {
            type string;
          }
          leaf target {
            type string;
          }
        }
      }
      container dhcp-server {
        list dhcp-server-list {
          // NCS patched for predictable order
          ordered-by user;
          key "server";
          leaf server {
            type string;
          }
        }
      }
      container dhcp {
        leaf smart-relay {
          type empty;
        }
        container use {
          container vrf {
            leaf connected {
              type string;
              // NCS drop default statement
            }
          }
        }
        container conflict {
          leaf logging {
            type string;
            // NCS drop default statement
          }
        }
        container excluded-address {
          uses ncs_template_ip-dhcp-excluded-address-grouping;
          list vrf {
            // NCS patched for predictable order
            ordered-by user;
            key "name";
            leaf name {
              type string;
            }
            uses ncs_template_ip-dhcp-excluded-address-grouping;
          }
        }
        list pool {
          // NCS patched for predictable order
          ordered-by user;
          key "id";
          leaf id {
            type string;
          }
          leaf vrf {
            type string;
          }
          container network {
            leaf network-number {
              type string;
            }
            leaf mask {
              type string;
            }
          }
          leaf-list dns-server {
            // NCS patched for predictable order
            ordered-by user;
            type string;
          }
          leaf domain-name {
            type string;
          }
          leaf-list default-router {
            // NCS patched for predictable order
            ordered-by user;
            type string;
          }
          list option {
            // NCS patched for predictable order
            ordered-by user;
            key "code";
            leaf code {
              type string;
            }
            leaf ascii {
              type string;
            }
            leaf hex {
              type string;
            }
            leaf instance {
              type string;
            }
            leaf-list ip {
              // NCS patched for predictable order
              ordered-by user;
              type string;
            }
          }
          leaf netbios-name-server {
            type string;
          }
          container lease {
            choice lease-choice {
              case a {
                leaf infinite {
                  type empty;
                }
              }
              case b {
                leaf days {
                  type string;
                }
                leaf hours {
                  type string;
                }
                leaf minutes {
                  type string;
                }
              }
            }
          }
        }
        list class {
          // NCS patched for predictable order
          ordered-by user;
          key "id";
          leaf id {
            type string;
          }
          leaf remark {
            type string;
          }
          container relay {
            container agent {
              container information {
                presence "true";
              }
            }
          }
        }
        container snooping {
          presence "true";
          leaf-list bridge-domain {
            // NCS patched for predictable order
            ordered-by user;
            // NCS drop tailf-common:cli-diff-dependency statement
            type string;
          }
          container information {
            container option {
              presence "true";
              leaf allow-untrusted {
                type empty;
              }
              container format {
                container remote-id {
                  choice remote-id-choice {
                    leaf hostname {
                      type empty;
                    }
                    leaf string {
                      type string;
                    }
                  }
                }
              }
            }
          }
          container database {
            leaf url {
              type string;
            }
          }
          container track {
            leaf host {
              type empty;
            }
          }
          container verify {
            leaf mac-address {
              type empty;
            }
            leaf no-relay-agent-address {
              type empty;
            }
          }
          leaf-list vlan {
            // NCS patched for predictable order
            ordered-by user;
            type string;
          }
        }
        container relay {
          container information {
            container option {
              presence "true";
            }
            leaf check {
              type string;
              // NCS drop default statement
            }
            leaf trust-all {
              type empty;
            }
          }
        }
      }
      container bootp {
        leaf server {
          type string;
          // NCS drop default statement
        }
      }
      container domain {
        leaf round-robin {
          type empty;
        }
        container list-vrf {
          container list {
            list vrf {
              // NCS patched for predictable order
              ordered-by user;
              key "name";
              leaf name {
                type string;
              }
              leaf domain-name {
                type string;
              }
            }
          }
        }
        list list {
          // NCS patched for predictable order
          ordered-by user;
          key "name";
          leaf name {
            type string;
          }
        }
        leaf retry {
          type string;
        }
        leaf timeout {
          type string;
        }
        container lookup-conf {
          leaf lookup {
            type string;
            // NCS drop default statement
          }
        }
        container lookup {
          leaf nsap {
            type string;
            // NCS drop default statement
          }
          leaf recursive {
            type empty;
          }
          container source-interface {
            uses ncs_template_interface-name-grouping;
          }
          leaf vrf {
            // NCS drop tailf-common:cli-diff-dependency statement
            // NCS drop tailf-common:cli-diff-dependency statement
            type string;
          }
        }
        container name-vrf {
          container name {
            list vrf {
              // NCS patched for predictable order
              ordered-by user;
              key "name";
              leaf name {
                type string;
              }
              leaf domain-name {
                type string;
              }
            }
          }
        }
        leaf name {
          type string;
        }
        leaf multicast {
          type string;
        }
        container recursive {
          leaf retry {
            type string;
          }
          leaf allow-soa {
            type empty;
          }
        }
      }
      container host {
        // NCS drop tailf-common:cli-diff-dependency statement
        // NCS drop tailf-common:cli-diff-dependency statement
        uses ncs_template_ip-host-grouping;
        list vrf {
          // NCS patched for predictable order
          ordered-by user;
          key "name";
          leaf name {
            type string;
          }
          uses ncs_template_ip-host-grouping;
        }
      }
      container name-server {
        uses ncs_template_ip-name-server-grouping;
        list vrf {
          // NCS patched for predictable order
          ordered-by user;
          key "name";
          leaf name {
            type string;
          }
          uses ncs_template_ip-name-server-grouping;
        }
      }
      container mcr-conf {
        leaf multicast-routing {
          type empty;
        }
      }
      container multicast-routing {
        // NCS drop tailf-common:cli-diff-dependency statement
        // NCS drop tailf-common:cli-diff-dependency statement
        // NCS drop tailf-common:cli-diff-dependency statement
        list vrf {
          // NCS patched for predictable order
          ordered-by user;
          // NCS drop tailf-common:cli-diff-dependency statement
          key "name";
          leaf name {
            type string;
          }
          leaf distributed {
            type empty;
          }
        }
        leaf distributed {
          type empty;
        }
      }
      container multicast {
        leaf route-limit {
          type string;
        }
        container multipath {
          presence "true";
          leaf s-g-hash {
            type string;
          }
        }
      }
      container icmp {
        container rate-limit {
          container unreachable {
            leaf DF {
              type empty;
            }
            leaf ms {
              type string;
            }
            container log {
              presence "true";
              leaf packets {
                type string;
              }
              leaf interval-ms {
                type string;
              }
            }
          }
        }
      }
      container igmp {
        leaf limit {
          type string;
        }
        container snooping {
          presence "true";
          leaf l2-entry-limit {
            type string;
          }
        }
      }
      container device {
        container tracking {
          presence "true";
        }
      }
      container finger {
        presence "true";
        leaf rfc-compliant {
          type empty;
        }
      }
      container tcp {
        leaf mss {
          type string;
        }
        container path-mtu-discovery {
          presence "true";
          leaf age-timer {
            type string;
          }
        }
      }
      container telnet {
        container source-interface {
          uses ncs_template_interface-name-grouping;
        }
      }
      container ftp {
        leaf passive {
          type string;
          // NCS drop default statement
        }
        container source-interface {
          uses ncs_template_interface-name-grouping;
        }
        leaf username {
          type string;
        }
        container password {
          uses ncs_template_password-grouping;
        }
      }
      container tftp {
        container source-interface {
          uses ncs_template_interface-name-grouping;
        }
        container boot-interface {
          uses ncs_template_interface-name-grouping;
        }
      }
      container ssh {
        leaf time-out {
          type string;
        }
        leaf authentication-retries {
          type string;
        }
        leaf dscp {
          type string;
        }
        container logging {
          leaf events {
            type empty;
          }
        }
        leaf version {
          type string;
        }
        leaf precedence {
          type string;
        }
        leaf stricthostkeycheck {
          type empty;
        }
        container source-interface {
          uses ncs_template_interface-name-grouping;
        }
      }
      container scp {
        container server {
          leaf enable {
            type empty;
          }
        }
      }
      container local {
        list pool {
          // NCS patched for predictable order
          ordered-by user;
          key "id";
          leaf id {
            type string;
          }
          leaf start {
            type string;
          }
          leaf last {
            type string;
          }
          leaf group {
            type string;
          }
        }
      }
      leaf default-gateway {
        type string;
      }
      leaf classless {
        type string;
        // NCS drop default statement
      }
      container forward-protocol {
        leaf nd {
          type empty;
        }
        leaf sdns {
          type string;
        }
        leaf turbo-flood {
          type string;
        }
        container spanning-tree {
          presence "true";
          leaf any-local-broadcast {
            type empty;
          }
        }
        container udp {
          presence "true";
          leaf service {
            type string;
          }
        }
      }
      container http {
        leaf server {
          type string;
        }
        leaf access-class {
          type string;
        }
        container authentication {
          choice authentication-choice {
            leaf aaa {
              type empty;
            }
            leaf local {
              type empty;
            }
          }
        }
        leaf secure-server {
          type string;
        }
        container timeout-policy {
          leaf idle {
            type string;
          }
          leaf life {
            type string;
          }
          leaf requests {
            type string;
          }
        }
        container client {
          leaf source-interface {
            type string;
          }
        }
      }
      container bgp-community {
        leaf new-format {
          type empty;
        }
      }
      container community-list {
        list number-standard {
          // NCS patched for predictable order
          ordered-by user;
          key "no";
          leaf no {
            type string;
          }
          uses ncs_template_ip-community-list-standard-grouping;
        }
        list number-expanded {
          // NCS patched for predictable order
          ordered-by user;
          key "no";
          leaf no {
            type string;
          }
          uses ncs_template_ip-community-list-expanded-grouping;
        }
        list expanded {
          // NCS patched for predictable order
          ordered-by user;
          key "name";
          leaf name {
            type string;
          }
          uses ncs_template_ip-community-list-expanded-grouping;
        }
        list standard {
          // NCS patched for predictable order
          ordered-by user;
          key "name";
          leaf name {
            type string;
          }
          uses ncs_template_ip-community-list-standard-grouping;
        }
      }
      container as-path {
        list access-list {
          // NCS patched for predictable order
          ordered-by user;
          key "name";
          leaf name {
            type string;
          }
          list as-path-rule {
            // NCS patched for predictable order
            ordered-by user;
            key "operation rule";
            leaf operation {
              type string;
            }
            leaf rule {
              type string;
            }
          }
        }
      }
      container flow-cache {
        leaf entries {
          type string;
        }
        container timeout {
          leaf inactive {
            type string;
          }
          leaf active {
            type string;
          }
        }
      }
      container flow-export {
        container source {
          uses ncs_template_interface-name-grouping;
        }
        leaf version {
          type string;
        }
        container template {
          // NCS drop tailf-common:cli-diff-dependency statement
          container options {
            leaf export-stats {
              type empty;
            }
          }
          leaf timeout-rate {
            type string;
            // NCS drop default statement
          }
          leaf refresh-rate {
            type string;
            // NCS drop default statement
          }
        }
        container destination {
          leaf ip {
            type string;
          }
          leaf port {
            type string;
          }
        }
      }
      container flow-aggregation {
        list cache {
          // NCS patched for predictable order
          ordered-by user;
          key "name";
          leaf name {
            type string;
          }
          container cache {
            container timeout {
              leaf active {
                type string;
              }
            }
          }
          container export {
            list destination {
              // NCS patched for predictable order
              ordered-by user;
              key "address";
              leaf address {
                type string;
              }
              leaf port {
                type string;
              }
            }
          }
        }
      }
      container dns {
        container server {
          presence "true";
        }
      }
      container mobile {
        container secure {
          list home-agent {
            // NCS patched for predictable order
            ordered-by user;
            // NCS drop tailf-common:cli-diff-dependency statement
            key "lower-address";
            leaf lower-address {
              type string;
            }
            leaf upper-address {
              type string;
            }
            choice spi-choice {
              case single-spi {
                container spi {
                  uses ncs_template_mobile-ip-spi-grouping;
                }
              }
              case range-spi {
                container inbound-spi {
                  uses ncs_template_mobile-ip-spi-grouping;
                }
                container outbound-spi {
                  uses ncs_template_mobile-ip-spi-grouping;
                }
              }
            }
            container key {
              choice key-choice {
                leaf ascii {
                  type string;
                }
                leaf hex {
                  type string;
                }
              }
            }
            container algorithm {
              choice algorithm-choice {
                leaf hmac-md5 {
                  type empty;
                }
                container md5 {
                  container mode {
                    leaf prefix-suffix {
                      type empty;
                    }
                  }
                }
              }
            }
            leaf ignore-spi {
              type empty;
            }
          }
        }
        container router {
          // NCS drop tailf-common:cli-diff-dependency statement
          presence "true";
          container address {
            leaf ipv4-address {
              // NCS drop tailf-common:cli-diff-dependency statement
              type string;
            }
            leaf ipv4-mask {
              type string;
            }
          }
          container collocated {
            leaf single-tunnel {
              // NCS drop tailf-common:cli-diff-dependency statement
              type empty;
            }
          }
          list home-agent {
            // NCS patched for predictable order
            ordered-by user;
            // NCS drop tailf-common:cli-diff-dependency statement
            key "address";
            leaf address {
              type string;
            }
            leaf priority {
              type string;
              // NCS drop default statement
            }
          }
          list mobile-network {
            // NCS patched for predictable order
            ordered-by user;
            // NCS drop tailf-common:cli-diff-dependency statement
            key "name";
            leaf name {
              type string;
            }
            container policy {
              leaf mobile-map {
                type string;
              }
            }
          }
          container register {
            container extend {
              leaf expire {
                // NCS drop tailf-common:cli-diff-dependency statement
                type string;
              }
              leaf retry {
                type string;
              }
              leaf interval {
                type string;
              }
              leaf reverse-tunnel {
                type empty;
              }
            }
          }
          leaf reverse-tunnel {
            type empty;
          }
          container tunnel {
            container mode {
              leaf gre {
                type empty;
              }
            }
          }
          container template {
            leaf Tunnel {
              type string;
            }
          }
        }
      }
      container pim {
        // NCS drop tailf-common:cli-diff-dependency statement
        // NCS drop tailf-common:cli-diff-dependency statement
        // NCS drop tailf-common:cli-diff-dependency statement
        uses ncs_template_ip-pim-grouping;
        list vrf {
          // NCS patched for predictable order
          ordered-by user;
          key "id";
          leaf id {
            type string;
          }
          uses ncs_template_ip-pim-grouping;
        }
      }
      container rsvp {
        container signalling {
          container hello {
            presence "true";
            container graceful-restart {
              leaf mode {
                type string;
              }
            }
          }
        }
      }
      container nat {
        // NCS drop tailf-common:cli-diff-dependency statement
        // NCS drop tailf-common:cli-diff-dependency statement
        list pool {
          // NCS patched for predictable order
          ordered-by user;
          key "id";
          leaf id {
            type string;
          }
          leaf start-address {
            type string;
          }
          leaf end-address {
            // NCS drop when statement
            type string;
          }
          choice prefix-choice {
            leaf netmask {
              type string;
            }
            leaf prefix-length {
              type string;
            }
          }
          leaf accounting {
            type string;
          }
          choice nat-choice {
            leaf arp-ping {
              type empty;
            }
            leaf type {
              type string;
            }
            leaf add-route {
              type empty;
            }
          }
        }
        container inside {
          container source {
            list list {
              // NCS patched for predictable order
              ordered-by user;
              key "id";
              leaf id {
                type string;
              }
              uses ncs_template_ip-nat-inside-grouping;
            }
            container static {
              list nat-static-address-list {
                // NCS patched for predictable order
                ordered-by user;
                key "local-ip global-ip";
                leaf local-ip {
                  type string;
                }
                leaf global-ip {
                  type string;
                }
                uses ncs_template_ip-nat-inside-souce-static-grouping;
              }
              list nat-static-transport-list {
                // NCS patched for predictable order
                ordered-by user;
                key "proto local-ip local-port global-ip global-port";
                leaf proto {
                  type string;
                }
                leaf local-ip {
                  type string;
                }
                leaf local-port {
                  type string;
                }
                leaf global-ip {
                  type string;
                }
                leaf global-port {
                  type string;
                }
                uses ncs_template_ip-nat-inside-souce-static-grouping;
              }
              list nat-static-transport-interface-list {
                // NCS patched for predictable order
                ordered-by user;
                key "proto local-ip local-port";
                leaf proto {
                  type string;
                }
                leaf local-ip {
                  type string;
                }
                leaf local-port {
                  type string;
                }
                container interface {
                  uses ncs_template_interface-name-grouping;
                }
                leaf global-port {
                  type string;
                }
              }
            }
            list route-map {
              // NCS patched for predictable order
              ordered-by user;
              key "id";
              leaf id {
                type string;
              }
              uses ncs_template_ip-nat-inside-grouping;
            }
          }
          container destination {
            list list {
              // NCS patched for predictable order
              ordered-by user;
              key "id";
              leaf id {
                type string;
              }
              leaf pool {
                type string;
              }
              leaf redundancy {
                type string;
              }
              leaf mapping-id {
                type string;
              }
            }
          }
        }
        container outside {
          container source {
            list list {
              // NCS patched for predictable order
              ordered-by user;
              key "id";
              leaf id {
                type string;
              }
              leaf pool {
                type string;
              }
              leaf mapping-id {
                type string;
              }
              leaf vrf {
                // NCS drop tailf-common:cli-diff-dependency statement
                // NCS drop tailf-common:cli-diff-dependency statement
                type string;
              }
              leaf add-route {
                type empty;
              }
            }
            list route-map {
              // NCS patched for predictable order
              ordered-by user;
              key "id";
              leaf id {
                type string;
              }
              leaf pool {
                type string;
              }
              leaf mapping-id {
                type string;
              }
              leaf vrf {
                // NCS drop tailf-common:cli-diff-dependency statement
                // NCS drop tailf-common:cli-diff-dependency statement
                type string;
              }
              leaf add-route {
                type empty;
              }
            }
          }
        }
      }
      container route {
        // NCS drop tailf-common:cli-diff-dependency statement
        // NCS drop tailf-common:cli-diff-dependency statement
        // NCS drop tailf-common:cli-diff-dependency statement
        container static {
          leaf adjust-time {
            type string;
          }
          leaf inter-vrf {
            type string;
            // NCS drop default statement
          }
          container bfd {
            list ip-route-bfd-forwarding-list {
              // NCS patched for predictable order
              ordered-by user;
              key "interface ip-address";
              leaf interface {
                type string;
              }
              leaf ip-address {
                type string;
              }
              leaf group {
                type string;
              }
            }
          }
        }
        leaf profile {
          type empty;
        }
        uses ncs_template_ip-route-grouping;
        list vrf {
          // NCS patched for predictable order
          ordered-by user;
          // NCS drop tailf-common:cli-diff-dependency statement
          // NCS drop tailf-common:cli-diff-dependency statement
          key "name";
          leaf name {
            type string;
          }
          uses ncs_template_ip-route-grouping;
        }
      }
      container explicit-path {
        list identifier {
          // NCS patched for predictable order
          ordered-by user;
          key "number";
          leaf number {
            type string;
          }
          leaf mode {
            type string;
          }
          list index {
            // NCS patched for predictable order
            ordered-by user;
            key "id";
            leaf id {
              type string;
            }
            choice address-choice {
              leaf next-address {
                type string;
              }
              leaf exclude-address {
                type string;
              }
            }
          }
        }
        list name {
          // NCS patched for predictable order
          ordered-by user;
          key "name";
          leaf name {
            type string;
          }
          leaf mode {
            type string;
          }
          list index {
            // NCS patched for predictable order
            ordered-by user;
            key "id";
            leaf id {
              type string;
            }
            choice address-choice {
              leaf next-address {
                type string;
              }
              leaf exclude-address {
                type string;
              }
            }
          }
        }
      }
      container tacacs {
        container source-interface {
          uses ncs_template_interface-name-grouping;
        }
      }
      container access-list {
        container standard {
          list std-named-acl {
            // NCS patched for predictable order
            ordered-by user;
            key "name";
            leaf name {
              type string;
            }
            list std-access-list-rule {
              // NCS patched for predictable order
              ordered-by user;
              key "rule";
              leaf rule {
                type string;
              }
            }
          }
        }
        container extended {
          list ext-named-acl {
            // NCS patched for predictable order
            ordered-by user;
            key "name";
            leaf name {
              type string;
            }
            list ext-access-list-rule {
              // NCS patched for predictable order
              ordered-by user;
              key "rule";
              leaf rule {
                type string;
              }
            }
          }
        }
      }
      container prefix-list {
        list prefixes {
          // NCS patched for predictable order
          ordered-by user;
          key "name";
          leaf name {
            type string;
          }
          leaf description {
            type string;
          }
          leaf permit {
            type string;
          }
          list seq {
            // NCS patched for predictable order
            ordered-by user;
            key "no";
            leaf no {
              type string;
            }
            container deny {
              leaf ip {
                type string;
              }
              leaf ge {
                type string;
              }
              leaf le {
                type string;
              }
            }
            container permit {
              leaf ip {
                type string;
              }
              leaf ge {
                type string;
              }
              leaf le {
                type string;
              }
            }
          }
        }
        leaf sequence-number {
          type empty;
        }
      }
      container radius {
        container source-interface {
          uses ncs_template_interface-name-grouping;
        }
      }
      container sla {
        container auto {
          leaf discovery {
            type empty;
          }
        }
        container responder {
          presence "true";
        }
        container logging {
          leaf traps {
            type empty;
          }
        }
        list ip-sla-list {
          // NCS patched for predictable order
          ordered-by user;
          key "id";
          leaf id {
            type string;
          }
          list udp-jitter {
            // NCS patched for predictable order
            ordered-by user;
            key "destination destination-port";
            leaf destination {
              type string;
            }
            leaf destination-port {
              type string;
            }
            leaf source-ip {
              type string;
            }
            leaf source-port {
              type string;
            }
            leaf codec {
              type string;
            }
            leaf codec-numpackets {
              // NCS drop when statement
              type string;
            }
            leaf interval {
              type string;
              // NCS drop default statement
            }
            leaf control {
              type string;
              // NCS drop default statement
            }
            uses ncs_template_ip-sla-proto-grouping;
          }
          list icmp-echo {
            // NCS patched for predictable order
            ordered-by user;
            key "host";
            leaf host {
              type string;
            }
            choice source-choice {
              container source-interface {
                uses ncs_template_interface-name-grouping;
              }
              leaf source-ip {
                type string;
              }
            }
            uses ncs_template_ip-sla-proto-grouping;
          }
          list udp-echo {
            // NCS patched for predictable order
            ordered-by user;
            key "host port";
            leaf host {
              type string;
            }
            leaf port {
              type string;
            }
            leaf control {
              type string;
            }
            leaf source-ip {
              type string;
            }
            leaf source-port {
              type string;
            }
            uses ncs_template_ip-sla-proto-grouping;
          }
          container ethernet {
            container y1731 {
              list delay {
                // NCS patched for predictable order
                ordered-by user;
                key "name";
                leaf name {
                  type string;
                }
                leaf burst {
                  type empty;
                }
                leaf domain {
                  type string;
                }
                choice evc-or-vlan {
                  leaf evc {
                    type string;
                  }
                  leaf vlan {
                    type string;
                  }
                }
                choice mpid-or-mac {
                  leaf mac-address {
                    type string;
                  }
                  leaf mpid {
                    type string;
                  }
                }
                leaf cos {
                  type string;
                }
                container source {
                  choice mpid-or-mac {
                    leaf mac-address {
                      type string;
                    }
                    leaf mpid {
                      type string;
                    }
                  }
                }
              }
              container delay-receive {
                container delay {
                  list receive {
                    // NCS patched for predictable order
                    ordered-by user;
                    key "name";
                    leaf name {
                      type string;
                    }
                    leaf domain {
                      type string;
                    }
                    choice evc-or-vlan {
                      leaf evc {
                        type string;
                      }
                      leaf vlan {
                        type string;
                      }
                    }
                    leaf cos {
                      type string;
                    }
                    choice mpid-or-mac {
                      leaf mac-address {
                        type string;
                      }
                      leaf mpid {
                        type string;
                      }
                    }
                  }
                }
              }
              list loss {
                // NCS patched for predictable order
                ordered-by user;
                key "name";
                leaf name {
                  type string;
                }
                leaf burst {
                  type empty;
                }
                leaf domain {
                  type string;
                }
                choice evc-or-vlan {
                  leaf evc {
                    type string;
                  }
                  leaf vlan {
                    type string;
                  }
                }
                choice mpid-or-mac {
                  leaf mac-address {
                    type string;
                  }
                  leaf mpid {
                    type string;
                  }
                }
                leaf cos {
                  type string;
                }
                container source {
                  choice mpid-or-mac {
                    leaf mac-address {
                      type string;
                    }
                    leaf mpid {
                      type string;
                    }
                  }
                }
                container availability {
                  leaf algorithm {
                    type string;
                  }
                }
              }
            }
          }
        }
        list schedule {
          // NCS patched for predictable order
          ordered-by user;
          key "operation-number";
          leaf operation-number {
            type string;
          }
          leaf life {
            type string;
          }
          container start-time {
            choice start-time-choice {
              leaf after {
                type string;
              }
              leaf now {
                type empty;
              }
              leaf pending {
                type empty;
              }
              leaf time {
                type string;
              }
            }
          }
          leaf ageout {
            type string;
          }
          leaf recurring {
            type empty;
          }
        }
        list reaction-configuration {
          // NCS patched for predictable order
          ordered-by user;
          key "operation-number";
          leaf operation-number {
            type string;
          }
          leaf react {
            type string;
          }
          leaf action-type {
            type string;
          }
          container threshold-value {
            leaf upper-threshold {
              type string;
            }
            leaf lower-threshold {
              type string;
            }
          }
          container threshold-type {
            choice threshold-type-choice {
              leaf average {
                type string;
              }
              leaf consecutive {
                type string;
              }
              leaf immediate {
                type empty;
              }
              leaf never {
                type empty;
              }
              leaf xOfy {
                type string;
              }
            }
          }
        }
        container enable {
          leaf reaction-alerts {
            type empty;
          }
        }
      }
    }
    container isdn {
      leaf switch-type {
        type string;
      }
    }
    container vmps {
      leaf reconfirm {
        type string;
      }
      leaf retry {
        type string;
      }
      list server {
        // NCS patched for predictable order
        ordered-by user;
        key "name";
        leaf name {
          type string;
        }
        leaf primary {
          type empty;
        }
      }
    }
    container ipv6 {
      leaf unicast-routing {
        type empty;
      }
      leaf source-route {
        type empty;
      }
      container cef {
        presence "true";
        container accounting {
          leaf per-prefix {
            type empty;
          }
          leaf prefix-length {
            type empty;
          }
        }
        leaf distributed {
          type empty;
        }
      }
      leaf multicast-routing {
        type empty;
      }
      container multicast {
        container rpf {
          container backoff {
            leaf initial-delay {
              type string;
            }
            leaf max-delay {
              type string;
            }
          }
          leaf use-bgp {
            type empty;
          }
        }
      }
      container route {
        // NCS drop tailf-common:cli-diff-dependency statement
        // NCS drop tailf-common:cli-diff-dependency statement
        // NCS drop tailf-common:cli-diff-dependency statement
        list vrf {
          // NCS patched for predictable order
          ordered-by user;
          key "name";
          leaf name {
            type string;
          }
          uses ncs_template_ipv6-route-grouping;
        }
        uses ncs_template_ipv6-route-grouping;
      }
      container prefix-list {
        list prefixes {
          // NCS patched for predictable order
          ordered-by user;
          key "name";
          leaf name {
            type string;
          }
          leaf description {
            type string;
          }
          leaf permit {
            type string;
          }
          list seq {
            // NCS patched for predictable order
            ordered-by user;
            key "no";
            leaf no {
              type string;
            }
            container deny {
              leaf ip {
                type string;
              }
              leaf ge {
                type string;
              }
              leaf le {
                type string;
              }
            }
            container permit {
              leaf ip {
                type string;
              }
              leaf ge {
                type string;
              }
              leaf le {
                type string;
              }
            }
          }
        }
        leaf sequence-number {
          type empty;
        }
      }
      container access-list {
        list named-acl {
          // NCS patched for predictable order
          ordered-by user;
          key "name";
          leaf name {
            type string;
          }
          list access-list-rule {
            // NCS patched for predictable order
            ordered-by user;
            key "rule";
            leaf rule {
              type string;
            }
          }
        }
      }
    }
    container subscriber {
      leaf templating {
        type empty;
      }
    }
    container multilink {
      leaf virtual-template {
        type string;
      }
      leaf bundle-name {
        type string;
      }
    }
    container archive {
      container log {
        container config {
          container logging {
            leaf enable {
              type empty;
            }
            leaf size {
              type string;
              // NCS drop default statement
            }
          }
          leaf hidekeys {
            type empty;
          }
        }
      }
      leaf path {
        type string;
      }
      leaf maximum {
        type string;
      }
      leaf write-memory {
        type empty;
      }
    }
    container key {
      list chain {
        // NCS patched for predictable order
        ordered-by user;
        key "name";
        leaf name {
          type string;
        }
        list key {
          // NCS patched for predictable order
          ordered-by user;
          key "id";
          leaf id {
            type string;
          }
          container key-string {
            leaf encryption {
              type string;
            }
            leaf key {
              type string;
            }
          }
        }
      }
    }
    list username {
      // NCS patched for predictable order
      ordered-by user;
      key "name";
      leaf name {
        type string;
      }
      container password {
        leaf encryption {
          type string;
        }
        leaf password {
          type string;
        }
      }
      leaf privilege {
        type string;
      }
      container secret {
        leaf encryption {
          type string;
        }
        leaf secret {
          type string;
        }
      }
    }
    list table-map {
      // NCS patched for predictable order
      ordered-by user;
      key "name";
      leaf name {
        type string;
      }
      list map {
        // NCS patched for predictable order
        ordered-by user;
        key "from to";
        leaf from {
          type string;
        }
        leaf to {
          type string;
        }
      }
      leaf default {
        type string;
      }
    }
    container sdm {
      container prefer {
        presence "true";
        choice sdm-prefer-choice {
          leaf default {
            type empty;
          }
          leaf qos {
            type empty;
          }
        }
      }
    }
    container mls {
      container acl {
        container tcam {
          leaf default-result {
            type string;
          }
          container log-update {
            presence "true";
            leaf rate-limit-msg {
              type string;
            }
          }
          leaf share-global {
            type string;
            // NCS drop default statement
          }
        }
      }
      container cef {
        container error {
          leaf action {
            type string;
          }
        }
      }
      container ip {
        container multicast {
          presence "true";
          container consistency-check {
            presence "true";
            container type {
              container rp-sp {
                presence "true";
              }
            }
            leaf settle-time {
              type string;
            }
          }
          leaf flow-stat-timer {
            type string;
          }
        }
      }
      container aging {
        container fast {
          presence "true";
          leaf time {
            type string;
          }
          leaf threshold {
            type string;
          }
        }
        container normal {
          leaf seconds {
            type string;
          }
        }
      }
      container netflow {
        presence "true";
        leaf interface {
          type empty;
        }
        container usage {
          container notify {
            leaf percentage {
              type string;
            }
            leaf seconds {
              type string;
            }
          }
        }
      }
      container flow {
        leaf ip {
          type string;
        }
      }
      container mls-qos-conf {
        leaf qos {
          type empty;
        }
      }
      container qos {
        list aggregate-policer {
          // NCS patched for predictable order
          ordered-by user;
          key "name";
          leaf name {
            type string;
          }
          leaf target-bit-rate {
            type string;
          }
          leaf burst-normal {
            type string;
          }
          leaf burst-max {
            // NCS drop when statement
            type string;
          }
          leaf pir {
            type string;
          }
          container conform-action {
            choice action-choice {
              leaf drop {
                type empty;
              }
              leaf set-dscp-transmit {
                type string;
              }
              leaf set-mpls-exp-imposition-transmit {
                type string;
              }
              leaf set-prec-transmit {
                type string;
              }
              leaf transmit {
                type empty;
              }
            }
          }
          leaf exceed-action {
            type string;
          }
          leaf violate-action {
            type string;
          }
        }
        container rewrite {
          container ip {
            container dscp {
              presence "true";
              leaf slot {
                type string;
              }
            }
          }
        }
        container map {
          leaf-list cos-dscp {
            // NCS patched for predictable order
            ordered-by user;
            type string;
          }
          leaf-list ip-prec-dscp {
            // NCS patched for predictable order
            ordered-by user;
            type string;
          }
          list exp-mutation {
            // NCS patched for predictable order
            ordered-by user;
            key "name";
            leaf name {
              type string;
            }
            leaf mutated-exp1 {
              type string;
            }
            leaf mutated-exp2 {
              type string;
            }
            leaf mutated-exp3 {
              type string;
            }
            leaf mutated-exp4 {
              type string;
            }
            leaf mutated-exp5 {
              type string;
            }
            leaf mutated-exp6 {
              type string;
            }
            leaf mutated-exp7 {
              type string;
            }
            leaf mutated-exp8 {
              type string;
            }
          }
        }
        container srr-queue {
          list cos-dscp-list {
            // NCS patched for predictable order
            ordered-by user;
            key "direction maptype queue threshold";
            leaf direction {
              type string;
            }
            leaf maptype {
              type string;
            }
            leaf queue {
              type string;
            }
            leaf threshold {
              type string;
            }
            list values {
              // NCS patched for predictable order
              ordered-by user;
              key "value";
              leaf value {
                type string;
              }
            }
          }
          container input {
            list priority-queue {
              // NCS patched for predictable order
              ordered-by user;
              key "queue";
              leaf queue {
                type string;
              }
              leaf bandwidth {
                type string;
              }
            }
            container bandwidth {
              leaf weight1 {
                type string;
              }
              leaf weight2 {
                type string;
              }
            }
            list threshold {
              // NCS patched for predictable order
              ordered-by user;
              key "queue";
              leaf queue {
                type string;
              }
              leaf threshold-percentage1 {
                type string;
              }
              leaf threshold-percentage2 {
                type string;
              }
            }
            container buffers {
              leaf percentage1 {
                type string;
              }
              leaf percentage2 {
                type string;
              }
            }
          }
        }
        container queue-set {
          container output {
            list threshold-list {
              // NCS patched for predictable order
              ordered-by user;
              key "queue threshold";
              leaf queue {
                type string;
              }
              leaf threshold {
                type string;
              }
              leaf drop-threshold1 {
                type string;
              }
              leaf drop-threshold2 {
                type string;
              }
              leaf reserved-threshold {
                type string;
              }
              leaf maximum-threshold {
                type string;
              }
            }
            list buffers-list {
              // NCS patched for predictable order
              ordered-by user;
              key "queue";
              leaf queue {
                type string;
              }
              container buffers {
                leaf allocation1 {
                  type string;
                }
                leaf allocation2 {
                  type string;
                }
                leaf allocation3 {
                  type string;
                }
                leaf allocation4 {
                  type string;
                }
              }
            }
          }
        }
      }
      container rate-limit {
        container multicast {
          container ipv4 {
            container igmp {
              leaf pps {
                type string;
              }
              leaf packets-in-burst {
                type string;
              }
            }
          }
        }
        container all {
          container ttl-failure {
            leaf pps {
              type string;
            }
            leaf packets-in-burst {
              type string;
            }
          }
        }
        container layer2 {
          container l2pt {
            leaf packets-per-second {
              type string;
            }
            leaf packets-in-burst {
              type string;
            }
          }
          container pdu {
            leaf packets-per-second {
              type string;
            }
            leaf packets-in-burst {
              type string;
            }
          }
        }
      }
      container verify {
        container ip {
          leaf checksum {
            type string;
            // NCS drop default statement
          }
          container length {
            leaf consistent {
              type string;
              // NCS drop default statement
            }
            leaf minimum {
              type string;
              // NCS drop default statement
            }
          }
          leaf same-address {
            type empty;
          }
          leaf syslog {
            type empty;
          }
        }
      }
    }
    container policer {
      list aggregate {
        // NCS patched for predictable order
        ordered-by user;
        key "name";
        leaf name {
          type string;
        }
        leaf cir {
          type string;
        }
        leaf bc {
          type string;
        }
        leaf conform-action {
          type empty;
        }
        leaf set-qos-transmit {
          // NCS drop when statement
          type string;
        }
        leaf set-dot1ad-dei-transmit {
          // NCS drop when statement
          type string;
        }
        leaf set-prec-transmit {
          // NCS drop when statement
          type string;
        }
        container set-prec-transmit-table {
          // NCS drop when statement
          leaf table {
            type string;
          }
        }
        leaf set-dscp-transmit {
          // NCS drop when statement
          type string;
        }
        container set-dscp-transmit-table {
          // NCS drop when statement
          leaf table {
            type string;
          }
        }
        leaf set-cos-transmit {
          // NCS drop when statement
          type string;
        }
        container set-cos-transmit-table {
          // NCS drop when statement
          leaf table {
            type string;
          }
        }
        leaf transmit {
          // NCS drop when statement
          type empty;
        }
        leaf exceed-action {
          type empty;
        }
        leaf drop {
          // NCS drop when statement
          type empty;
        }
        container exceed-transmit {
          leaf transmit {
            // NCS drop when statement
            type empty;
          }
        }
      }
    }
    container redundancy {
      presence "true";
      leaf maintenance-mode {
        type empty;
      }
      list linecard-group {
        // NCS patched for predictable order
        ordered-by user;
        key "id";
        leaf id {
          type string;
        }
        leaf cable {
          type empty;
        }
        leaf description {
          type string;
        }
        container rf-switch {
          leaf snmp-community {
            type string;
          }
        }
        container member {
          list subslot {
            // NCS patched for predictable order
            ordered-by user;
            key "id";
            leaf id {
              type string;
            }
            leaf working {
              type empty;
            }
            container protect {
              presence "true";
              choice config-choice {
                leaf config {
                  type string;
                }
                container no-config {
                  leaf config {
                    type string;
                    // NCS drop default statement
                  }
                }
              }
            }
          }
        }
        container conf {
          leaf revertive {
            type empty;
          }
        }
      }
      leaf mode {
        type string;
      }
      container main-cpu {
        container auto-sync {
          leaf running-config {
            type empty;
          }
          leaf config-register {
            type empty;
          }
          leaf bootvar {
            type empty;
          }
        }
        container switchover {
          container pxf {
            container restart {
              leaf number-of-crashes {
                type string;
              }
              leaf time-period {
                type string;
              }
            }
          }
        }
      }
      container interchassis {
        list group {
          // NCS patched for predictable order
          ordered-by user;
          key "id";
          leaf id {
            type string;
          }
          container member {
            leaf ip {
              type string;
            }
          }
          container mlacp {
            leaf system-mac {
              type string;
            }
            leaf system-priority {
              type string;
            }
            leaf node-id {
              type string;
            }
          }
        }
      }
    }
    list class-map {
      // NCS patched for predictable order
      ordered-by user;
      key "name";
      leaf name {
        type string;
      }
      leaf type {
        type string;
      }
      leaf protocol {
        // NCS drop when statement
        type string;
      }
      leaf prematch {
        type string;
        // NCS drop mandatory statement
      }
      leaf description {
        type string;
      }
      container match {
        uses ncs_template_class-map-match-grouping;
        container not {
          uses ncs_template_class-map-match-grouping;
        }
      }
    }
    list policy-map {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "name";
      leaf name {
        type string;
      }
      leaf type {
        type string;
      }
      leaf protocol {
        type string;
      }
      leaf description {
        type string;
      }
      list class {
        // NCS patched for predictable order
        ordered-by user;
        key "name";
        leaf name {
          type string;
        }
        leaf type {
          type string;
        }
        container policy {
          // NCS drop when statement
          leaf action {
            type string;
          }
          leaf log {
            // NCS drop when statement
            type empty;
          }
          leaf parameter-map {
            // NCS drop when statement
            type string;
          }
        }
        container inspect-police {
          // NCS drop when statement
          container police {
            leaf rate {
              type string;
            }
            leaf burst {
              type string;
            }
          }
        }
        container bandwidth {
          leaf bits {
            type string;
          }
          leaf percent {
            type string;
          }
          container remaining {
            leaf percent {
              type string;
            }
          }
        }
        container compression {
          presence "Activate Compression";
          container header {
            presence "configure header compression";
            leaf ip {
              type string;
            }
          }
        }
        leaf drop {
          type empty;
        }
        container estimate {
          container bandwidth {
            presence "bandwidth required to service this class";
            container delay-one-in {
              leaf doi {
                type string;
              }
              leaf milliseconds {
                type string;
              }
            }
            leaf drop-one-in {
              type string;
            }
          }
        }
        container fair-queue {
          presence "true";
          leaf dynamic-queues {
            type string;
          }
          leaf queue-limit {
            type string;
          }
        }
        leaf netflow-sampler {
          type string;
        }
        container police-aggregate {
          container police {
            leaf aggregate {
              // NCS drop tailf-common:cli-diff-dependency statement
              type string;
            }
          }
        }
        choice police-choice {
          case police-cirmode-case {
            container police-policy-map {
              container police {
                // NCS drop when statement
                leaf cir {
                  // NCS drop tailf-common:cli-diff-dependency statement
                  type string;
                }
                leaf bc {
                  type string;
                }
                leaf be {
                  // NCS drop when statement
                  type string;
                }
                leaf pir {
                  type string;
                }
                container pir-be {
                  // NCS drop when statement
                  leaf be {
                    type string;
                  }
                }
                uses ncs_template_police-action-grouping;
              }
            }
          }
          case police-cir-percent-case {
            container police-cir-percent {
              container police {
                container cir {
                  container percent {
                    leaf percentage {
                      type string;
                    }
                    leaf bc {
                      type string;
                    }
                    container bc-ms {
                      // NCS drop when statement
                      leaf ms {
                        type empty;
                      }
                    }
                    leaf be {
                      // NCS drop when statement
                      type string;
                    }
                    container be-ms {
                      // NCS drop when statement
                      leaf ms {
                        type empty;
                      }
                    }
                    container pir {
                      leaf percent {
                        type string;
                      }
                    }
                    container pir-be {
                      // NCS drop when statement
                      leaf be {
                        type string;
                      }
                    }
                    container pir-be-ms {
                      // NCS drop when statement
                      leaf ms {
                        type empty;
                      }
                    }
                    uses ncs_template_police-action-grouping;
                  }
                }
              }
            }
          }
          case police-rate-unit-case {
            container police-rate-unit {
              container police {
                container rate {
                  leaf units {
                    type string;
                  }
                  leaf xps {
                    type string;
                  }
                  container burst {
                    leaf burst-value {
                      type string;
                    }
                    leaf burst-type {
                      type string;
                    }
                  }
                  container peak-rate {
                    leaf peak-rate-value {
                      type string;
                    }
                    leaf xps {
                      type string;
                    }
                  }
                  container peak-burst {
                    leaf burst-value {
                      type string;
                    }
                    leaf burst-type {
                      type string;
                    }
                  }
                  uses ncs_template_police-action-grouping;
                }
              }
            }
          }
          case police-rate-percent-case {
            container police-rate-percent {
              container police {
                container rate {
                  container percent {
                    leaf percentage {
                      type string;
                    }
                    leaf burst {
                      type string;
                    }
                    leaf ms {
                      // NCS drop when statement
                      type empty;
                    }
                    container peak-rate {
                      leaf percent {
                        type string;
                      }
                    }
                    leaf peak-burst {
                      type string;
                    }
                    container peak-burst-ms {
                      // NCS drop when statement
                      leaf ms {
                        type empty;
                      }
                    }
                    uses ncs_template_police-action-grouping;
                  }
                }
              }
            }
          }
          case police-rate-pdp-case {
            container police-rate-pdp {
              container police {
                container rate {
                  container pdp {
                    leaf burst {
                      type string;
                    }
                    leaf peak-rate {
                      type string;
                    }
                    leaf peak-burst {
                      // NCS drop when statement
                      type string;
                    }
                    uses ncs_template_police-action-grouping;
                  }
                }
              }
            }
          }
          case police-flow-case {
            container police-flow {
              container police {
                container flow {
                  leaf mask {
                    type string;
                  }
                  leaf bps {
                    type string;
                  }
                  leaf burst-normal {
                    // NCS drop when statement
                    type string;
                  }
                  uses ncs_template_police-action-grouping;
                }
              }
            }
          }
          case police-bpsflat-case {
            container police-catalyst {
              container police {
                // NCS drop when statement
                leaf bps-value {
                  type string;
                }
                leaf bps {
                  // NCS drop when statement
                  type empty;
                }
                leaf byte-value {
                  type string;
                }
                leaf byte {
                  // NCS drop when statement
                  type empty;
                }
                container actions {
                  uses ncs_template_police-conform-action-grouping;
                  uses ncs_template_police-exceed-action-grouping;
                  uses ncs_template_police-violate-action-grouping;
                }
              }
            }
          }
          case police-switch-case {
            container police-switch {
              container police {
                // NCS drop when statement
                leaf cir {
                  // NCS drop tailf-common:cli-diff-dependency statement
                  type string;
                }
                leaf bc {
                  type string;
                }
                leaf exceed-action {
                  type string;
                }
              }
            }
          }
          case police-numflat-case {
            container police-numflat {
              container police {
                // NCS drop when statement
                leaf cir {
                  // NCS drop tailf-common:cli-diff-dependency statement
                  type string;
                }
                leaf bc {
                  type string;
                }
                leaf be {
                  type string;
                }
                container actions {
                  uses ncs_template_police-conform-action-grouping;
                  uses ncs_template_police-exceed-action-grouping;
                  uses ncs_template_police-violate-action-grouping;
                }
              }
            }
          }
          case police-cirflat-case {
            container police-cirflat {
              container police {
                // NCS drop when statement
                leaf cir {
                  // NCS drop tailf-common:cli-diff-dependency statement
                  type string;
                }
                leaf bc {
                  type string;
                }
                container actions {
                  uses ncs_template_police-conform-action-grouping;
                  uses ncs_template_police-exceed-action-grouping;
                  uses ncs_template_police-violate-action-grouping;
                }
              }
            }
          }
        }
        container priority {
          presence "true";
          leaf level {
            type string;
          }
          choice priority-type {
            leaf kilo-bits {
              type string;
            }
            leaf percent {
              type string;
            }
          }
          leaf burst {
            type string;
          }
        }
        container queue-limit {
          leaf queue-limit-value {
            type string;
          }
          leaf queue-limit-type {
            type string;
          }
        }
        container random-detect {
          presence "true";
          container aggregate {
            presence "true";
            leaf minimum-thresh {
              type string;
            }
            leaf maximum-thresh {
              type string;
            }
            leaf mark-probability {
              type empty;
            }
            leaf denominator {
              type string;
            }
          }
          leaf cos-based {
            // NCS drop tailf-common:cli-diff-dependency statement
            // NCS drop tailf-common:cli-diff-dependency statement
            // NCS drop tailf-common:cli-diff-dependency statement
            // NCS drop tailf-common:cli-diff-dependency statement
            // NCS drop tailf-common:cli-diff-dependency statement
            // NCS drop tailf-common:cli-diff-dependency statement
            type empty;
          }
          leaf precedence-based {
            // NCS drop tailf-common:cli-diff-dependency statement
            // NCS drop tailf-common:cli-diff-dependency statement
            // NCS drop tailf-common:cli-diff-dependency statement
            // NCS drop tailf-common:cli-diff-dependency statement
            type empty;
          }
          leaf discard-class-based {
            // NCS drop tailf-common:cli-diff-dependency statement
            // NCS drop tailf-common:cli-diff-dependency statement
            type empty;
          }
          leaf dscp-based {
            type empty;
          }
          leaf exponential-weighting-constant {
            type string;
          }
          leaf ecn {
            type empty;
          }
          list cos {
            // NCS patched for predictable order
            ordered-by user;
            // NCS drop tailf-common:cli-diff-dependency statement
            key "cos";
            leaf cos {
              type string;
            }
            uses ncs_template_random-detect-grouping;
          }
          list precedence {
            // NCS patched for predictable order
            ordered-by user;
            // NCS drop tailf-common:cli-diff-dependency statement
            key "prec";
            leaf prec {
              type string;
            }
            uses ncs_template_random-detect-grouping;
          }
          list discard-class {
            // NCS patched for predictable order
            ordered-by user;
            // NCS drop tailf-common:cli-diff-dependency statement
            key "dclass";
            leaf dclass {
              type string;
            }
            uses ncs_template_random-detect-grouping;
          }
          list dscp {
            // NCS patched for predictable order
            ordered-by user;
            // NCS drop tailf-common:cli-diff-dependency statement
            key "dscpvalue";
            leaf dscpvalue {
              type string;
            }
            uses ncs_template_random-detect-grouping;
          }
        }
        container set {
          leaf atm-clp {
            type empty;
          }
          container cos {
            choice cos-type {
              case a {
                leaf val {
                  type string;
                }
              }
              case b {
                leaf pack {
                  type string;
                }
                leaf table {
                  type string;
                }
              }
            }
          }
          leaf discard-class {
            type string;
          }
          leaf dscp {
            type string;
          }
          leaf fr-de {
            type empty;
          }
          container ip {
            choice ip-choice {
              leaf dscp {
                type string;
              }
              container precedence {
                presence "Set IP precedence";
                leaf precedence-val {
                  type string;
                }
              }
            }
          }
          container mpls {
            container experimental {
              container imposition {
                leaf exp-value {
                  type string;
                }
              }
            }
          }
          container qos-group {
            leaf qos-group-value {
              type string;
            }
          }
          container precedence {
            choice precedence-choice {
              case precedence-value {
                leaf precedence-value {
                  type string;
                }
              }
              case precedence-from-field {
                leaf from-field {
                  type string;
                }
                leaf table {
                  type string;
                }
              }
            }
          }
        }
        container shape {
          leaf adaptive {
            type string;
          }
          container average {
            choice average-choice {
              case a {
                leaf bit-rate {
                  type string;
                }
                leaf bits-per-interval-sustained {
                  type string;
                }
                leaf bits-per-interval-excess {
                  type string;
                }
              }
              case b {
                leaf percent {
                  type string;
                }
                leaf burst-size-sustained {
                  type string;
                }
                leaf ms {
                  type empty;
                }
                container bse {
                  leaf burst-size-excess {
                    type string;
                  }
                  leaf ms {
                    type empty;
                  }
                }
              }
            }
          }
          leaf fecn-adapt {
            type empty;
          }
          container fr-voice-adapt {
            presence "true";
            leaf deactivation {
              type string;
            }
          }
          leaf max-buffers {
            type string;
          }
        }
        leaf service-policy {
          type string;
        }
        leaf trust {
          type string;
        }
      }
    }
    container bridge-domain {
      list bridge-domain-list {
        // NCS patched for predictable order
        ordered-by user;
        key "id";
        leaf id {
          type string;
        }
        container member {
          leaf vfi {
            type string;
          }
          list interface-list {
            // NCS patched for predictable order
            ordered-by user;
            key "name";
            leaf name {
              type string;
            }
            leaf service-instance {
              type string;
            }
          }
        }
        container mac {
          leaf aging-time {
            type string;
          }
        }
      }
    }
    list service-group {
      // NCS patched for predictable order
      ordered-by user;
      key "id";
      leaf id {
        type string;
      }
      leaf description {
        type string;
      }
      container service-policy {
        uses ncs_template_service-policy-grouping;
      }
    }
    container vlan {
      choice vlan-accounting-choice {
        leaf accounting {
          type string;
          // NCS drop default statement
        }
        container accounting-input {
          container accounting {
            leaf input {
              type string;
              // NCS drop default statement
            }
          }
        }
        container accounting-output {
          container accounting {
            leaf output {
              type string;
              // NCS drop default statement
            }
          }
        }
      }
      container internal {
        container allocation {
          leaf policy {
            type string;
          }
        }
      }
      container dot1q {
        container tag {
          leaf native {
            type empty;
          }
        }
      }
      container access-log {
        leaf maxflow {
          type string;
        }
        leaf ratelimit {
          type string;
        }
        leaf threshold {
          type string;
        }
      }
      list vlan-list {
        // NCS patched for predictable order
        ordered-by user;
        key "id";
        leaf id {
          type string;
        }
        leaf name {
          type string;
        }
        leaf remote-span {
          type empty;
        }
        leaf uni-vlan {
          type string;
        }
      }
    }
    container lldp {
      leaf run {
        type empty;
      }
    }
    container EXEC {
      container crypto-key;
      container crypto-pki {
        container crypto {
          container pki;
        }
      }
    }
    container crypto {
      list keyring {
        // NCS patched for predictable order
        ordered-by user;
        key "name";
        leaf name {
          type string;
        }
        leaf vrf {
          type string;
        }
      }
      container logging {
        leaf session {
          type empty;
        }
        leaf ikev2 {
          type empty;
        }
      }
      container ikev2 {
        list name-mangler {
          // NCS patched for predictable order
          ordered-by user;
          key "name";
          leaf name {
            type string;
          }
          leaf fqdn {
            type string;
          }
        }
        container authorization {
          list policy {
            // NCS patched for predictable order
            ordered-by user;
            key "name";
            leaf name {
              type string;
            }
            container aaa {
              container attribute {
                leaf list {
                  type string;
                }
              }
            }
            container route {
              container set {
                container access-list {
                  leaf ipv4 {
                    type string;
                  }
                  leaf ipv6 {
                    type string;
                  }
                }
                container interface {
                  presence "true";
                  list interface-list {
                    // NCS patched for predictable order
                    ordered-by user;
                    key "name";
                    leaf name {
                      type string;
                    }
                  }
                }
              }
              container accept {
                container any {
                  choice any-choice {
                    leaf distance {
                      type string;
                      // NCS drop default statement
                    }
                    leaf tag {
                      type string;
                    }
                  }
                }
              }
            }
          }
        }
        list keyring {
          // NCS patched for predictable order
          ordered-by user;
          key "name";
          leaf name {
            type string;
          }
          list peer {
            // NCS patched for predictable order
            ordered-by user;
            key "name";
            leaf name {
              type string;
            }
            leaf description {
              type string;
            }
            container address {
              choice address-choice {
                case ipv4 {
                  leaf ipv4-address {
                    type string;
                  }
                  leaf ipv4-mask {
                    type string;
                  }
                }
                case ipv6 {
                  leaf ipv6-address {
                    type string;
                  }
                }
              }
            }
            container identity {
              container fqdn {
                leaf domain {
                  type empty;
                }
                leaf name {
                  type string;
                }
              }
            }
            container pre-shared-key {
              uses ncs_template_crypto-key-grouping;
            }
            container pre-shared-key-local {
              container pre-shared-key {
                container local {
                  uses ncs_template_crypto-key-grouping;
                }
              }
            }
            container pre-shared-key-remote {
              container pre-shared-key {
                container remote {
                  uses ncs_template_crypto-key-grouping;
                }
              }
            }
          }
        }
        list profile {
          // NCS patched for predictable order
          ordered-by user;
          key "name";
          leaf name {
            type string;
          }
          leaf description {
            type string;
          }
          container match {
            leaf fvrf {
              type string;
            }
            container identity {
              container remote {
                container fqdn {
                  list fqdn-list {
                    // NCS patched for predictable order
                    ordered-by user;
                    key "name";
                    leaf name {
                      type string;
                    }
                  }
                  list domain {
                    // NCS patched for predictable order
                    ordered-by user;
                    key "name";
                    leaf name {
                      type string;
                    }
                  }
                }
                list address {
                  // NCS patched for predictable order
                  ordered-by user;
                  key "name";
                  leaf name {
                    type string;
                  }
                  leaf mask {
                    type string;
                  }
                }
              }
            }
          }
          container identity {
            container local {
              choice local-choice {
                leaf email {
                  type string;
                }
                leaf fqdn {
                  type string;
                }
              }
            }
          }
          container authentication {
            container local {
              choice method-choice {
                container eap {
                  presence "true";
                }
                leaf ecdsa-sig {
                  type empty;
                }
                container pre-share {
                  presence "true";
                  container key {
                    uses ncs_template_crypto-key-grouping;
                  }
                }
                leaf rsa-sig {
                  type empty;
                }
              }
            }
            container remote {
              presence "true";
              choice method-choice {
                container eap {
                  presence "true";
                }
                leaf ecdsa-sig {
                  type empty;
                }
                container pre-share {
                  presence "true";
                  container key {
                    uses ncs_template_crypto-key-grouping;
                  }
                }
                leaf rsa-sig {
                  type empty;
                }
              }
            }
          }
          container keyring {
            choice keyring-choice {
              container aaa {
                leaf name {
                  type string;
                }
                leaf name-mangler {
                  type string;
                }
              }
              leaf local {
                type string;
              }
            }
          }
          container nat {
            leaf keepalive {
              type string;
            }
          }
          container aaa {
            container authorization {
              container group {
                container psk {
                  container list {
                    leaf list-name {
                      type string;
                    }
                    leaf aaa-username {
                      type string;
                    }
                    leaf name-mangler {
                      type string;
                    }
                    container password {
                      uses ncs_template_crypto-key-grouping;
                    }
                  }
                }
              }
              container user {
                container psk {
                  leaf cached {
                    type empty;
                  }
                  leaf list {
                    type string;
                  }
                }
              }
            }
          }
          leaf virtual-template {
            type string;
          }
          container dpd {
            leaf interval {
              type string;
            }
            leaf retry-interval {
              type string;
            }
            leaf queries {
              type string;
            }
          }
        }
        container dpd {
          leaf interval {
            type string;
          }
          leaf retry-interval {
            type string;
          }
          leaf mode {
            type string;
          }
        }
      }
      container pki {
        list server {
          // NCS patched for predictable order
          ordered-by user;
          // NCS drop max-elements statement
          key "cs-label";
          leaf cs-label {
            type string;
          }
          leaf shutdown {
            type empty;
          }
          container database {
            container archive {
              leaf format {
                type string;
              }
              container password {
                leaf type {
                  type string;
                }
                leaf secret {
                  type string;
                }
              }
            }
          }
          leaf grant {
            type string;
          }
          leaf hash {
            type string;
          }
        }
        list trustpoint {
          // NCS patched for predictable order
          ordered-by user;
          key "id";
          leaf id {
            type string;
          }
          container serial-number {
            presence "true";
            leaf none {
              type empty;
            }
          }
          leaf ip-address {
            // NCS drop tailf-common:cli-diff-dependency statement
            type string;
          }
          container enrollment {
            leaf http-proxy {
              type string;
            }
            container mode {
              leaf ra {
                type empty;
              }
            }
            leaf profile {
              type string;
            }
            container retry {
              leaf count {
                type string;
              }
              leaf period {
                type string;
              }
            }
            leaf selfsigned {
              type empty;
            }
            container terminal {
              leaf pem {
                type empty;
              }
            }
            leaf url {
              type string;
            }
          }
          leaf subject-name {
            type string;
          }
          leaf revocation-check {
            type string;
          }
          leaf rsakeypair {
            type string;
          }
        }
        container certificate {
          list chain {
            // NCS patched for predictable order
            ordered-by user;
            key "name";
            leaf name {
              type string;
            }
            list certificate {
              // NCS patched for predictable order
              ordered-by user;
              key "serial";
              leaf serial {
                type string;
              }
              leaf cert-type {
                type string;
              }
              leaf rollover {
                type empty;
              }
              leaf cert {
                type string;
              }
            }
          }
        }
        container token {
          list token-name {
            // NCS patched for predictable order
            ordered-by user;
            key "name";
            leaf name {
              type string;
            }
            uses ncs_template_crypto-pki-token-grouping;
          }
        }
        container default {
          uses ncs_template_crypto-pki-token-grouping;
        }
      }
      container isakmp {
        leaf enable {
          type string;
          // NCS drop default statement
        }
        list profile {
          // NCS patched for predictable order
          ordered-by user;
          key "name";
          leaf name {
            type string;
          }
          leaf vrf {
            type string;
          }
          list keyring {
            // NCS patched for predictable order
            ordered-by user;
            key "name";
            leaf name {
              type string;
            }
          }
          container match {
            leaf fvrf {
              type string;
            }
            container identity {
              container address {
                container ipv4 {
                  leaf address {
                    type string;
                  }
                  leaf mask {
                    type string;
                  }
                }
              }
            }
          }
        }
        list policy {
          // NCS patched for predictable order
          ordered-by user;
          key "priority";
          leaf priority {
            type string;
          }
          container encryption {
            leaf algorithm {
              type string;
              // NCS drop default statement
            }
            leaf bits {
              // NCS drop when statement
              type string;
              // NCS drop default statement
            }
          }
          leaf hash {
            type string;
            // NCS drop default statement
          }
          leaf authentication {
            type string;
          }
          leaf group {
            type string;
          }
          leaf lifetime {
            type string;
            // NCS drop default statement
          }
        }
        container keepalive {
          leaf seconds {
            type string;
          }
          leaf periodic {
            type empty;
          }
        }
        container nat {
          container keepalive {
            leaf seconds {
              type string;
            }
          }
        }
        list key {
          // NCS patched for predictable order
          ordered-by user;
          key "keystring";
          leaf keystring {
            type string;
          }
          leaf encrypted {
            type string;
          }
          choice peer-choice {
            container address {
              choice address-choice {
                case a {
                  leaf ipv4 {
                    type string;
                  }
                }
                case b {
                  leaf ipv4-address {
                    type string;
                  }
                  leaf ipv4-mask {
                    type string;
                  }
                }
                case c {
                  leaf ipv6 {
                    type string;
                  }
                }
              }
            }
            leaf hostname {
              type string;
            }
          }
          leaf no-xauth {
            type empty;
          }
        }
      }
      container ipsec {
        container optional {
          presence "true";
          leaf retry {
            type string;
          }
        }
        container security-association {
          leaf idle-time {
            type string;
          }
          container lifetime {
            leaf kilobytes {
              type string;
            }
            leaf seconds {
              type string;
            }
          }
          container replay {
            leaf disable {
              type empty;
            }
            leaf window-size {
              type string;
            }
          }
        }
        list transform-set {
          // NCS patched for predictable order
          ordered-by user;
          key "name";
          leaf name {
            type string;
          }
          leaf transform1 {
            type string;
          }
          leaf transform1-bits {
            // NCS drop when statement
            type string;
          }
          leaf transform2 {
            type string;
          }
          leaf transform2-bits {
            // NCS drop when statement
            type string;
          }
          leaf transform3 {
            type string;
          }
          leaf transform3-bits {
            // NCS drop when statement
            type string;
          }
          leaf transform4 {
            type string;
          }
          leaf transform4-bits {
            // NCS drop when statement
            type string;
          }
          leaf mode {
            type string;
            // NCS drop default statement
          }
        }
        container default {
          leaf transform-set {
            type string;
            // NCS drop default statement
          }
        }
        leaf fragmentation {
          type string;
        }
        leaf df-bit {
          type string;
        }
        leaf nat-transparency {
          type string;
        }
        list profile {
          // NCS patched for predictable order
          ordered-by user;
          key "name";
          leaf name {
            type string;
          }
          container set {
            container security-association {
              container lifetime {
                leaf kilobytes {
                  type string;
                }
                leaf seconds {
                  type string;
                }
              }
            }
            leaf transform-set {
              type string;
            }
            leaf ikev2-profile {
              type string;
            }
          }
        }
      }
      container gdoi {
        list group {
          // NCS patched for predictable order
          ordered-by user;
          key "name";
          leaf name {
            type string;
          }
          leaf ipv6 {
            type empty;
          }
          container identity {
            choice identify-choice {
              leaf number {
                type string;
              }
              container address {
                leaf ipv4 {
                  type string;
                }
              }
            }
          }
          container server {
            container local {
              presence "true";
              // NCS drop must statement
              // NCS drop tailf-common:cli-diff-dependency statement
              container rekey {
                container lifetime {
                  choice lifetime-choice {
                    leaf seconds {
                      type string;
                      // NCS drop default statement
                    }
                    leaf days {
                      type string;
                    }
                    // NCS drop default statement
                  }
                }
                container retransmit {
                  leaf number-of-seconds {
                    type string;
                  }
                  choice retransmit-choice {
                    leaf number {
                      type string;
                    }
                    leaf periodic {
                      type empty;
                    }
                  }
                }
                container authentication {
                  choice authentication-choice {
                    leaf mypubkey {
                      type empty;
                    }
                    leaf pubkey {
                      type empty;
                    }
                  }
                  leaf rsa {
                    type string;
                  }
                }
                container transport {
                  leaf unicast {
                    type empty;
                  }
                }
              }
              container replay {
                container time {
                  leaf window-size {
                    type string;
                  }
                }
              }
              container sa {
                list ipsec {
                  // NCS patched for predictable order
                  ordered-by user;
                  key "id";
                  leaf id {
                    type string;
                  }
                  leaf profile {
                    type string;
                  }
                  container match {
                    container address {
                      choice address-choice {
                        leaf ipv4 {
                          type string;
                        }
                        leaf ipv6 {
                          type string;
                        }
                      }
                    }
                  }
                  container replay {
                    container counter {
                      leaf window-size {
                        type string;
                      }
                    }
                  }
                }
              }
              container address {
                leaf ipv4 {
                  type string;
                }
              }
              container redundancy {
                container local {
                  presence "true";
                  leaf priority {
                    type string;
                  }
                }
                container peer {
                  container address {
                    leaf ipv4 {
                      type string;
                    }
                  }
                }
              }
            }
            container address {
              list ipv4 {
                // NCS patched for predictable order
                ordered-by user;
                // NCS drop must statement
                // NCS drop tailf-common:cli-diff-dependency statement
                key "name";
                leaf name {
                  type string;
                }
              }
            }
          }
          container client {
            container registration {
              container interface {
                uses ncs_template_interface-name-grouping;
              }
            }
          }
        }
      }
      list dynamic-map {
        // NCS patched for predictable order
        ordered-by user;
        key "name map-entry";
        leaf name {
          type string;
        }
        leaf map-entry {
          type string;
        }
        container set {
          leaf isakmp-profile {
            type string;
          }
          leaf-list transform-set {
            // NCS patched for predictable order
            ordered-by user;
            type string;
          }
        }
        container match {
          leaf address {
            type string;
          }
        }
      }
      list map {
        // NCS patched for predictable order
        ordered-by user;
        key "name";
        leaf name {
          type string;
        }
        leaf ipv6 {
          type empty;
        }
        container local-address {
          uses ncs_template_interface-name-grouping;
        }
        list seq-list {
          // NCS patched for predictable order
          ordered-by user;
          key "id";
          leaf id {
            type string;
          }
          leaf policy {
            type string;
          }
          leaf dynamic {
            // NCS drop when statement
            type string;
          }
          leaf profile {
            // NCS drop when statement
            type string;
          }
          container set {
            // NCS drop when statement
            leaf transform-set {
              type string;
            }
            leaf isakmp-profile {
              type string;
            }
            leaf peer {
              type string;
            }
          }
          container gdoi-set {
            // NCS drop when statement
            container set {
              leaf group {
                type string;
              }
            }
          }
          container match {
            leaf address {
              type string;
            }
          }
        }
      }
      container ssl {
        list proposal {
          // NCS patched for predictable order
          ordered-by user;
          key "name";
          leaf name {
            type string;
          }
          leaf-list protection {
            // NCS patched for predictable order
            ordered-by user;
            type string;
          }
        }
        container authorization {
          list policy {
            // NCS patched for predictable order
            ordered-by user;
            key "name";
            leaf name {
              type string;
            }
            leaf pool {
              type string;
            }
            container dns {
              leaf primary-server {
                type string;
              }
              leaf secondary-server {
                type string;
              }
            }
            leaf banner {
              type string;
            }
            leaf def-domain {
              type string;
            }
          }
        }
        list policy {
          // NCS patched for predictable order
          ordered-by user;
          key "name";
          leaf name {
            type string;
          }
          container ssl {
            leaf proposal {
              type string;
            }
          }
          container pki {
            leaf trustpoint {
              type string;
            }
            leaf sign {
              type empty;
            }
          }
          container ip {
            container address {
              leaf local {
                type string;
              }
              leaf port {
                type string;
              }
            }
          }
          leaf shutdown {
            type empty;
          }
        }
        list profile {
          // NCS patched for predictable order
          ordered-by user;
          key "name";
          leaf name {
            type string;
          }
          container match {
            leaf policy {
              type string;
            }
            leaf url {
              type string;
            }
          }
          container aaa {
            container authentication {
              leaf list {
                type string;
              }
            }
            container authorization {
              container user {
                leaf list {
                  type string;
                }
                leaf aaa-username {
                  type string;
                }
              }
            }
          }
          container authentication {
            container remote {
              leaf user-credentials {
                type empty;
              }
            }
          }
          leaf shutdown {
            type empty;
          }
        }
      }
    }
    container buffers {
      container huge {
        leaf size {
          type string;
        }
      }
    }
    container track {
      list track-object {
        // NCS patched for predictable order
        ordered-by user;
        key "object-number";
        leaf object-number {
          type string;
        }
        container list {
          leaf boolean {
            type string;
          }
        }
        container interface {
          uses ncs_template_interface-name-grouping;
          leaf line-protocol {
            type empty;
          }
        }
        container ip {
          container route {
            leaf prefix {
              type string;
            }
            leaf mask {
              type string;
            }
            leaf reachability {
              type empty;
            }
            container metric {
              leaf threshold {
                type empty;
              }
            }
          }
        }
        list object {
          // NCS patched for predictable order
          ordered-by user;
          key "id";
          leaf id {
            type string;
          }
          leaf not {
            type empty;
          }
        }
        container delay {
          leaf down {
            type string;
          }
          leaf up {
            type string;
          }
        }
      }
    }
    container csdb {
      container tcp {
        leaf finwait-time {
          type string;
          // NCS drop default statement
        }
        leaf idle-time {
          type string;
          // NCS drop default statement
        }
        container reassembly {
          leaf max-memory {
            type string;
            // NCS drop default statement
          }
          leaf max-queue-length {
            type string;
            // NCS drop default statement
          }
        }
        leaf synwait-time {
          type string;
          // NCS drop default statement
        }
      }
      container udp {
        leaf idle-time {
          type string;
          // NCS drop default statement
        }
      }
      container icmp {
        leaf idle-time {
          type string;
          // NCS drop default statement
        }
      }
      container session {
        leaf max-session {
          type string;
          // NCS drop default statement
        }
      }
    }
    container ethernet {
      list evc {
        // NCS patched for predictable order
        ordered-by user;
        key "name";
        leaf name {
          type string;
        }
        container oam {
          container protocol {
            container cfm {
              leaf domain {
                type string;
              }
            }
          }
        }
      }
      container cfm {
        leaf ieee {
          type empty;
        }
        leaf global {
          type empty;
        }
        container traceroute {
          container cache {
            presence "true";
            leaf hold-time {
              type string;
              // NCS drop default statement
            }
          }
        }
        container mip {
          list auto-create {
            // NCS patched for predictable order
            ordered-by user;
            key "evc";
            leaf evc {
              type string;
            }
            leaf level {
              type string;
            }
          }
        }
        list domain {
          // NCS patched for predictable order
          ordered-by user;
          key "name";
          leaf name {
            type string;
          }
          leaf level {
            type string;
          }
          list service {
            // NCS patched for predictable order
            ordered-by user;
            key "csi-id";
            leaf csi-id {
              type string;
            }
            leaf port {
              type empty;
            }
            leaf evc {
              type string;
            }
            leaf vlan {
              type string;
            }
            leaf direction {
              type string;
            }
            container continuity-check {
              presence "true";
              leaf interval {
                type string;
              }
            }
            leaf sender-id {
              type string;
            }
            container ais {
              leaf period {
                type string;
                // NCS drop default statement
              }
              leaf level {
                type string;
              }
            }
            container efd {
              container notify {
                leaf g8032 {
                  type empty;
                }
              }
            }
          }
        }
      }
      container ring {
        container g8032 {
          list profile {
            // NCS patched for predictable order
            ordered-by user;
            key "profile-name";
            leaf profile-name {
              type string;
            }
            container timer {
              leaf wtr {
                type string;
              }
              leaf guard {
                type string;
              }
            }
          }
          list g8032-list {
            // NCS patched for predictable order
            ordered-by user;
            key "ring-name";
            leaf ring-name {
              type string;
            }
            container exclusion-list {
              leaf-list vlan-ids {
                // NCS patched for predictable order
                ordered-by user;
                type string;
              }
            }
            container port0 {
              container interface {
                uses ncs_template_interface-name-grouping;
              }
              container monitor {
                container service {
                  leaf instance {
                    type string;
                  }
                }
              }
            }
            choice port1-choice {
              container port1 {
                container interface {
                  uses ncs_template_interface-name-grouping;
                }
                container monitor {
                  container service {
                    leaf instance {
                      type string;
                    }
                  }
                }
              }
              container port1-none {
                container port1 {
                  leaf none {
                    type empty;
                  }
                }
              }
            }
            list instance {
              // NCS patched for predictable order
              ordered-by user;
              key "instance-id";
              leaf instance-id {
                type string;
              }
              leaf profile {
                type string;
              }
              container rpl {
                leaf port {
                  type string;
                }
                leaf type {
                  type string;
                }
              }
              container inclusion-list {
                leaf-list vlan-ids {
                  // NCS patched for predictable order
                  ordered-by user;
                  type string;
                }
              }
              container aps-channel {
                container port0 {
                  container service {
                    leaf instance {
                      type string;
                    }
                  }
                }
                container port1 {
                  choice port1-choice {
                    container service {
                      leaf instance {
                        type string;
                      }
                    }
                    leaf none {
                      type empty;
                    }
                  }
                }
              }
            }
          }
        }
      }
      list tcn-propagation {
        // NCS patched for predictable order
        ordered-by user;
        key "source to";
        leaf source {
          type string;
        }
        leaf to {
          type string;
        }
      }
    }
    container interface {
      // NCS drop tailf-common:cli-diff-dependency statement
      list Null {
        // NCS patched for predictable order
        ordered-by user;
        key "name";
        leaf name {
          type string;
        }
        container ip {
          leaf unreachables {
            type string;
            // NCS drop default statement
          }
        }
        container ipv6 {
          leaf unreachables {
            type string;
            // NCS drop default statement
          }
        }
      }
      list Loopback {
        // NCS patched for predictable order
        ordered-by user;
        key "name";
        leaf name {
          type string;
        }
        uses ncs_template_interface-common-pre-grouping;
        uses ncs_template_interface-common-grouping;
      }
      list Embedded-Service-Engine {
        // NCS patched for predictable order
        ordered-by user;
        key "name";
        leaf name {
          type string;
        }
        uses ncs_template_interface-common-pre-grouping;
        uses ncs_template_interface-common-grouping;
      }
      list Tunnel {
        // NCS patched for predictable order
        ordered-by user;
        key "name";
        leaf name {
          type string;
        }
        uses ncs_template_interface-common-pre-grouping;
        uses ncs_template_interface-common-grouping;
        container qos {
          leaf pre-classify {
            type empty;
          }
        }
        uses ncs_template_interface-tunnel-grouping;
      }
      list Port-channel {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping {
          refine "l2protocol-tunnel" {
            // NCS drop tailf-common:cli-diff-dependency statement
          }
        }
        container lacp {
          leaf fast-switchover {
            type empty;
          }
          leaf max-bundle {
            type string;
          }
        }
        container mlacp {
          container interchassis {
            leaf group {
              type string;
            }
          }
        }
      }
      container Port-channel-subinterface {
        list Port-channel {
          // NCS patched for predictable order
          ordered-by user;
          key "name";
          leaf name {
            type string;
          }
          uses ncs_template_interface-common-pre-grouping;
          uses ncs_template_interface-ethernet-pre-grouping;
          uses ncs_template_interface-switch-grouping;
          uses ncs_template_interface-ethernet-grouping;
          uses ncs_template_interface-common-grouping {
            refine "l2protocol-tunnel" {
              // NCS drop tailf-common:cli-diff-dependency statement
            }
          }
        }
      }
      list Multilink {
        // NCS patched for predictable order
        ordered-by user;
        key "name";
        leaf name {
          type string;
        }
        uses ncs_template_interface-common-pre-grouping;
        uses ncs_template_interface-common-grouping;
        uses ncs_template_interface-pointtopoint-grouping;
      }
      list MFR {
        // NCS patched for predictable order
        ordered-by user;
        key "name";
        leaf name {
          type string;
        }
        uses ncs_template_interface-common-pre-grouping;
        uses ncs_template_interface-common-grouping;
      }
      container MFR-subinterface {
        list MFR {
          // NCS patched for predictable order
          ordered-by user;
          key "name";
          leaf name {
            type string;
          }
          leaf type {
            type string;
          }
          uses ncs_template_interface-common-pre-grouping;
          uses ncs_template_interface-common-grouping;
        }
      }
      list BRI {
        // NCS patched for predictable order
        ordered-by user;
        key "name";
        leaf name {
          type string;
        }
        uses ncs_template_interface-common-pre-grouping;
        uses ncs_template_interface-common-grouping;
      }
      list Ethernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping {
          refine "l2protocol-tunnel" {
            // NCS drop tailf-common:cli-diff-dependency statement
          }
        }
        uses ncs_template_interface-zone-member-grouping;
      }
      list FastEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping {
          refine "l2protocol-tunnel" {
            // NCS drop tailf-common:cli-diff-dependency statement
          }
        }
        uses ncs_template_interface-zone-member-grouping;
      }
      list GigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping {
          refine "l2protocol-tunnel" {
            // NCS drop tailf-common:cli-diff-dependency statement
          }
        }
        uses ncs_template_interface-zone-member-grouping;
      }
      list TenGigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping {
          refine "l2protocol-tunnel" {
            // NCS drop tailf-common:cli-diff-dependency statement
          }
        }
        uses ncs_template_interface-zone-member-grouping;
      }
      list BDI {
        // NCS patched for predictable order
        ordered-by user;
        key "name";
        leaf name {
          type string;
        }
        uses ncs_template_interface-common-pre-grouping;
        uses ncs_template_interface-switch-grouping;
        uses ncs_template_interface-common-grouping;
      }
      list Cable {
        // NCS patched for predictable order
        ordered-by user;
        key "name";
        leaf name {
          type string;
        }
        uses ncs_template_interface-common-pre-grouping;
        uses ncs_template_interface-common-grouping;
        container downstream {
          leaf Modular-Cable {
            type string;
          }
          leaf rf-channel {
            type string;
          }
        }
        container cable {
          container tftp-enforce {
            presence "true";
            leaf mark-only {
              type empty;
            }
          }
          leaf ip-init {
            type string;
            // NCS drop default statement
          }
          container mtc-mode {
            presence "true";
          }
          list rcc-template {
            // NCS patched for predictable order
            ordered-by user;
            key "index";
            leaf index {
              type string;
            }
          }
          container rcp-control {
            leaf verbose {
              type empty;
            }
          }
          container shared-secret {
            uses ncs_template_password-07-grouping;
          }
          container dynamic-secret {
            choice dynamic-secret-choice {
              case reject {
                leaf reject {
                  type empty;
                }
              }
              case mark {
                leaf mark {
                  type empty;
                }
              }
              case lock {
                leaf lock {
                  type empty;
                }
                leaf lock-qos {
                  type string;
                }
              }
            }
            leaf nocrypt {
              type empty;
            }
          }
          container enable-trap {
            leaf cmonoff-notification {
              type empty;
            }
            leaf cmonoff-interval {
              type string;
            }
          }
          leaf packet-cache {
            type string;
            // NCS drop default statement
          }
          leaf default-phy-burst {
            type string;
          }
          container insertion-interval {
            choice interval-choice {
              leaf fixed-intrvl {
                type string;
              }
              container automatic {
                leaf min-intrvl {
                  type string;
                  // NCS drop default statement
                }
                leaf max-intrvl {
                  type string;
                  // NCS drop default statement
                }
              }
            }
          }
          container map-advance {
            choice map-advance-choice {
              leaf static {
                type string;
              }
              container dynamic {
                leaf safety {
                  type string;
                }
                leaf max-delay {
                  type string;
                }
              }
            }
          }
          leaf sync-interval {
            type string;
          }
          leaf bundle {
            type string;
          }
          container downstream {
            container dsg {
              leaf timer {
                type string;
              }
              list tg {
                // NCS patched for predictable order
                ordered-by user;
                key "tgid";
                leaf tgid {
                  type string;
                }
                list channel {
                  // NCS patched for predictable order
                  ordered-by user;
                  key "channel-id";
                  leaf channel-id {
                    type string;
                  }
                }
              }
            }
          }
          container upstream {
            leaf balance-scheduling {
              type empty;
            }
            leaf max-ports {
              type string;
            }
            list bonding-group {
              // NCS patched for predictable order
              ordered-by user;
              key "id";
              leaf id {
                type string;
              }
              list upstream {
                // NCS patched for predictable order
                ordered-by user;
                key "number";
                leaf number {
                  type string;
                }
              }
              leaf attributes {
                type string;
              }
            }
            container resiliency {
              leaf on-failure {
                type string;
                // NCS drop default statement
              }
            }
            list cable-upstream-list {
              // NCS patched for predictable order
              ordered-by user;
              key "port";
              leaf port {
                type string;
              }
              leaf connector {
                type string;
              }
              leaf frequency {
                type string;
              }
              container channel-width {
                leaf first-choice-width {
                  type string;
                }
                leaf last-choice-width {
                  type string;
                }
              }
              leaf description {
                type string;
              }
              leaf docsis-mode {
                type string;
              }
              leaf minislot-size {
                type string;
              }
              container power-adjust {
                leaf continue {
                  type string;
                }
              }
              container range-backoff {
                choice range-backoff-choice {
                  case automatic {
                    leaf automatic {
                      type empty;
                    }
                  }
                  case numeric {
                    leaf start {
                      type string;
                    }
                    leaf end {
                      type string;
                    }
                  }
                }
              }
              container modulation-profile {
                leaf primary-profile-number {
                  type string;
                }
                leaf secondary-profile-number {
                  type string;
                }
                leaf tertiary-profile-number {
                  type string;
                }
              }
              leaf rate-limit {
                type empty;
              }
              leaf equalization-coefficient {
                type empty;
              }
              container rate-adapt {
                presence "true";
              }
              leaf attribute-mask {
                type string;
              }
              leaf chan-class-id {
                type string;
              }
              leaf shutdown {
                type empty;
              }
            }
          }
          container sid-cluster-group {
            leaf dynamic {
              type empty;
            }
            leaf num-of-cluster {
              type string;
            }
            leaf req-multiplier {
              type string;
            }
          }
          container sid-cluster-switching {
            leaf max-request {
              type string;
            }
            leaf max-time {
              type string;
            }
          }
          container divert-rate-limit {
            leaf rate {
              type string;
            }
            leaf limit {
              type string;
            }
          }
          container privacy {
            leaf mandatory {
              type empty;
            }
            leaf bpi-plus-policy {
              type string;
            }
          }
        }
      }
      list Modular-Cable {
        // NCS patched for predictable order
        ordered-by user;
        key "name";
        leaf name {
          type string;
        }
        uses ncs_template_interface-common-pre-grouping;
        uses ncs_template_interface-common-grouping;
        container cable {
          leaf bundle {
            type string;
          }
          container rf-bandwidth-percent {
            leaf percent-value {
              type string;
            }
            container remaining {
              leaf ratio {
                type string;
              }
            }
          }
        }
      }
      list Wideband-Cable {
        // NCS patched for predictable order
        ordered-by user;
        key "name";
        leaf name {
          type string;
        }
        uses ncs_template_interface-common-pre-grouping;
        uses ncs_template_interface-common-grouping;
        container cable {
          leaf bundle {
            type string;
          }
          container rf-channel {
            list rf-channel-list {
              // NCS patched for predictable order
              ordered-by user;
              key "rf-port";
              leaf rf-port {
                type string;
              }
              leaf bandwidth-percent {
                type string;
              }
              container remaining {
                leaf ratio {
                  type string;
                }
              }
            }
          }
        }
      }
      list Bundle {
        // NCS patched for predictable order
        ordered-by user;
        key "name";
        leaf name {
          type string;
        }
        uses ncs_template_interface-common-pre-grouping;
        uses ncs_template_interface-common-grouping;
        container cable {
          leaf nd {
            type string;
            // NCS drop default statement
          }
          container arp {
            container filter {
              container request-send {
                presence "true";
                leaf number {
                  type string;
                }
                leaf window-size {
                  type string;
                }
              }
              container reply-accept {
                presence "true";
                leaf number {
                  type string;
                }
                leaf window-size {
                  type string;
                }
              }
            }
          }
          container conf {
            leaf arp {
              type string;
              // NCS drop default statement
            }
          }
          container ipv6 {
            container source-verify {
              container dhcp {
                presence "true";
                leaf server {
                  type string;
                }
              }
              container leasequery-filter {
                container upstream {
                  leaf threshold {
                    type string;
                  }
                  leaf interval {
                    type string;
                  }
                }
              }
              leaf leasetimer {
                type string;
              }
            }
          }
          container source-verify {
            container dhcp {
              presence "true";
              leaf server {
                type string;
              }
            }
            container leasequery-filter {
              container upstream {
                leaf threshold {
                  type string;
                }
                leaf interval {
                  type string;
                }
              }
            }
            leaf leasetimer {
              type string;
            }
          }
          container dhcp-parse {
            leaf option-43 {
              type empty;
            }
            leaf option-60 {
              type empty;
            }
          }
          container dhcp-giaddr {
            choice dhcp-giaddr-choice {
              container policy {
                presence "true";
              }
              leaf primary {
                type empty;
              }
            }
          }
          list helper-address {
            // NCS patched for predictable order
            ordered-by user;
            key "IP-address";
            leaf IP-address {
              type string;
            }
          }
        }
      }
      list Cellular {
        // NCS patched for predictable order
        ordered-by user;
        key "name";
        leaf name {
          type string;
        }
        uses ncs_template_interface-common-pre-grouping;
        uses ncs_template_interface-common-grouping;
        uses ncs_template_interface-pointtopoint-grouping;
      }
      list Vlan {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-grouping;
        uses ncs_template_interface-common-grouping;
        uses ncs_template_interface-zone-member-grouping;
      }
      list Async {
        // NCS patched for predictable order
        ordered-by user;
        key "name";
        leaf name {
          type string;
        }
        uses ncs_template_interface-common-pre-grouping;
        uses ncs_template_interface-common-grouping;
      }
      list Group-Async {
        // NCS patched for predictable order
        ordered-by user;
        key "name";
        leaf name {
          type string;
        }
        leaf physical-layer {
          type string;
        }
        uses ncs_template_interface-common-pre-grouping;
        uses ncs_template_interface-common-grouping;
      }
      list Serial {
        // NCS patched for predictable order
        ordered-by user;
        key "name";
        leaf name {
          type string;
        }
        uses ncs_template_interface-common-pre-grouping;
        uses ncs_template_interface-common-grouping;
        uses ncs_template_interface-pointtopoint-grouping;
      }
      container Serial-subinterface {
        list Serial {
          // NCS patched for predictable order
          ordered-by user;
          key "name";
          leaf name {
            type string;
          }
          leaf type {
            type string;
          }
          uses ncs_template_interface-common-pre-grouping;
          uses ncs_template_interface-common-grouping;
          uses ncs_template_interface-pointtopoint-grouping;
        }
      }
      list Virtual-Template {
        // NCS patched for predictable order
        ordered-by user;
        key "name";
        leaf name {
          type string;
        }
        leaf type {
          type string;
        }
        uses ncs_template_interface-common-pre-grouping;
        uses ncs_template_interface-ethernet-pre-grouping;
        uses ncs_template_interface-switch-grouping;
        uses ncs_template_interface-ethernet-grouping;
        uses ncs_template_interface-common-grouping;
        uses ncs_template_interface-zone-member-grouping;
        uses ncs_template_interface-pointtopoint-grouping;
        uses ncs_template_interface-tunnel-grouping;
      }
      list pseudowire {
        // NCS patched for predictable order
        ordered-by user;
        key "name";
        leaf name {
          type string;
        }
        leaf description {
          type string;
        }
        leaf encapsulation {
          type string;
        }
        container neighbor {
          leaf address {
            type string;
          }
          leaf vcid {
            type string;
          }
        }
        container label {
          leaf local-pseudowire-label {
            type string;
          }
          leaf remote-pseudowire-label {
            type string;
          }
        }
        container signaling {
          leaf protocol {
            type string;
          }
        }
        leaf control-word {
          type string;
        }
        leaf shutdown {
          type empty;
        }
        container service-policy {
          uses ncs_template_service-policy-grouping;
        }
      }
      list LISP {
        // NCS patched for predictable order
        ordered-by user;
        key "name";
        leaf name {
          type string;
        }
        uses ncs_template_interface-common-pre-grouping;
        uses ncs_template_interface-common-grouping;
      }
      container LISP-subinterface {
        list LISP {
          // NCS patched for predictable order
          ordered-by user;
          key "name";
          leaf name {
            type string;
          }
          uses ncs_template_interface-common-pre-grouping;
          uses ncs_template_interface-common-grouping;
        }
      }
    }
    container access-list {
      list access-list-standard-range {
        // NCS patched for predictable order
        ordered-by user;
        key "listnumber";
        leaf listnumber {
          type string;
        }
        list std-access-list-rule {
          // NCS patched for predictable order
          ordered-by user;
          key "rule";
          leaf rule {
            type string;
          }
        }
      }
      list access-list-extended-range {
        // NCS patched for predictable order
        ordered-by user;
        key "listnumber";
        leaf listnumber {
          type string;
        }
        list ext-access-list-rule {
          // NCS patched for predictable order
          ordered-by user;
          key "rule";
          leaf rule {
            type string;
          }
        }
      }
      list access-list-standard-expanded {
        // NCS patched for predictable order
        ordered-by user;
        key "listnumber";
        leaf listnumber {
          type string;
        }
        list ext-access-list-rule {
          // NCS patched for predictable order
          ordered-by user;
          key "rule";
          leaf rule {
            type string;
          }
        }
      }
      list access-list-extended-expanded {
        // NCS patched for predictable order
        ordered-by user;
        key "listnumber";
        leaf listnumber {
          type string;
        }
        list ext-access-list-rule {
          // NCS patched for predictable order
          ordered-by user;
          key "rule";
          leaf rule {
            type string;
          }
        }
      }
    }
    list virtual-service {
      // NCS patched for predictable order
      ordered-by user;
      key "name";
      leaf name {
        type string;
      }
      leaf description {
        type string;
      }
    }
    list route-map {
      // NCS patched for predictable order
      ordered-by user;
      key "name sequence";
      leaf name {
        type string;
      }
      leaf sequence {
        type string;
      }
      leaf operation {
        type string;
      }
      leaf description {
        type string;
      }
      container match {
        container as-path {
          leaf-list path-list-number {
            // NCS patched for predictable order
            ordered-by user;
            type string;
          }
        }
        container ip {
          container address {
            choice address-choice {
              leaf access-list {
                type string;
              }
              leaf prefix-list {
                type string;
              }
            }
          }
        }
        container ipv6 {
          container address {
            choice address-choice {
              leaf access-list {
                type string;
              }
              leaf prefix-list {
                type string;
              }
            }
          }
        }
        container community {
          leaf-list name {
            // NCS patched for predictable order
            ordered-by user;
            type string;
          }
        }
      }
      container set {
        container as-path {
          container prepend {
            container as-container {
              leaf as-number {
                type string;
              }
            }
            container last-as-cont {
              leaf last-as {
                type string;
              }
            }
          }
          container tag {
            presence "tag";
          }
        }
        container community {
          leaf-list community-number {
            // NCS patched for predictable order
            ordered-by user;
            type string;
          }
        }
        container comm-list {
          leaf name {
            type string;
          }
          leaf delete {
            type empty;
          }
        }
        container extcommunity {
          leaf-list rt {
            // NCS patched for predictable order
            ordered-by user;
            type string;
          }
        }
        container ip {
          container next-hop {
            choice next-hop-choice {
              leaf-list address {
                // NCS patched for predictable order
                ordered-by user;
                type string;
              }
              container dynamic {
                leaf dhcp {
                  type empty;
                }
              }
              container encapsulate {
                leaf l3vpn {
                  type string;
                }
              }
              leaf peer-address {
                type empty;
              }
            }
          }
          container df {
            presence "true";
            leaf bit {
              type string;
            }
          }
        }
        container ipv6 {
          container next-hop {
            choice next-hop-choice {
              leaf-list address {
                // NCS patched for predictable order
                ordered-by user;
                type string;
              }
              leaf peer-address {
                type empty;
              }
            }
          }
        }
        container local-preference {
          presence "true";
          leaf value {
            type string;
          }
        }
        leaf metric {
          type string;
        }
        leaf metric-type {
          type string;
        }
        leaf weight {
          type string;
        }
        container origin {
          choice origin-choice {
            leaf origin-value {
              type string;
            }
            leaf egp {
              type string;
            }
          }
        }
        leaf vrf {
          // NCS drop tailf-common:cli-diff-dependency statement
          // NCS drop tailf-common:cli-diff-dependency statement
          type string;
        }
        leaf tag {
          type string;
        }
      }
      leaf continue {
        type string;
      }
    }
    container dialer {
      list watch-list {
        // NCS patched for predictable order
        ordered-by user;
        key "id";
        leaf id {
          type string;
        }
        container ip {
          leaf address {
            type string;
          }
          leaf mask {
            type string;
          }
        }
        container delay {
          container route-check {
            leaf initial {
              type string;
            }
          }
          leaf connect {
            type string;
          }
          leaf disconnect {
            type string;
          }
        }
      }
    }
    list dialer-list {
      // NCS patched for predictable order
      ordered-by user;
      key "id";
      leaf id {
        type string;
      }
      container protocol {
        leaf ip {
          type string;
        }
      }
    }
    container authentication {
      container mac-move {
        leaf permit {
          type empty;
        }
      }
    }
    container banner {
      leaf exec {
        type string;
      }
      leaf login {
        type string;
      }
      leaf prompt-timeout {
        type string;
      }
      leaf motd {
        type string;
      }
    }
    list pseudowire-class {
      // NCS patched for predictable order
      ordered-by user;
      key "name";
      leaf name {
        type string;
      }
      leaf encapsulation {
        type string;
      }
      leaf control-word {
        type empty;
      }
      container status {
        container peer {
          container topology {
            leaf dual-homed {
              type empty;
            }
          }
        }
      }
    }
    container control-plane {
      presence "true";
      container service-policy {
        uses ncs_template_service-policy-grouping;
      }
    }
    container cops {
      container listener {
        leaf access-list {
          type string;
        }
      }
      container ip {
        leaf dscp {
          type string;
        }
      }
    }
    list connect {
      // NCS patched for predictable order
      ordered-by user;
      key "interface1 interface2";
      leaf name {
        type string;
      }
      leaf interface1 {
        type string;
      }
      leaf number1 {
        type string;
      }
      leaf interface2 {
        type string;
      }
      leaf number2 {
        type string;
      }
      container backup {
        container peer {
          leaf peer-router-ip-addr {
            type string;
          }
          leaf vcid {
            type string;
          }
          leaf pw-class {
            type string;
          }
        }
      }
    }
    list voice-port {
      // NCS patched for predictable order
      ordered-by user;
      key "name";
      leaf name {
        type string;
      }
      container timeouts {
        leaf interdigit {
          type string;
        }
      }
      container busyout {
        leaf action {
          type string;
        }
        container monitor {
          container action {
            choice action-choice {
              leaf graceful {
                type empty;
              }
              leaf shutdown {
                type empty;
              }
              container alarm {
                leaf blue {
                  type empty;
                }
              }
            }
          }
          list state {
            // NCS patched for predictable order
            ordered-by user;
            key "name";
            leaf name {
              type string;
            }
            leaf in-service {
              type empty;
            }
          }
        }
      }
    }
    container dial-peer {
      list voice {
        // NCS patched for predictable order
        ordered-by user;
        key "id";
        leaf id {
          type string;
        }
        leaf peer {
          type string;
        }
        leaf answer-address {
          type string;
        }
        leaf trunkgroup {
          type string;
        }
        leaf description {
          type string;
        }
        container translation-profile {
          leaf incoming {
            type string;
          }
          leaf outgoing {
            type string;
          }
        }
        leaf huntstop {
          type empty;
        }
        leaf max-conn {
          type string;
        }
        leaf destination-pattern {
          type string;
        }
        container modem {
          container passthrough {
            choice passthrough-choice {
              leaf system {
                type string;
                // NCS drop default statement
              }
              container nse {
                leaf payload-type {
                  type string;
                }
                leaf codec {
                  type string;
                }
                leaf redundancy {
                  type empty;
                }
              }
            }
          }
        }
        container session {
          leaf protocol {
            type string;
          }
          leaf target {
            type string;
          }
        }
        container dtmf-relay {
          leaf cisco-rtp {
            type empty;
          }
          leaf h245-alphanumeric {
            type empty;
          }
          leaf h245-signal {
            type empty;
          }
          leaf rtp-nte {
            type empty;
          }
        }
        container incoming {
          leaf called-number {
            type string;
          }
        }
        leaf direct-inward-dial {
          type empty;
        }
        leaf forward-digits {
          type string;
        }
        container codec {
          leaf name {
            type string;
          }
          leaf bytes {
            type string;
          }
          leaf mode {
            type string;
          }
        }
        container fax {
          container protocol {
            choice protocol-option {
              leaf none {
                type empty;
              }
              leaf cisco {
                type empty;
              }
              leaf pass-through {
                type string;
              }
            }
          }
        }
        container ip {
          container qos {
            list dscp {
              // NCS patched for predictable order
              ordered-by user;
              key "name";
              leaf name {
                type string;
              }
              choice dscp-choice {
                leaf media {
                  type empty;
                }
                leaf signaling {
                  type empty;
                }
                leaf video {
                  type string;
                }
              }
            }
          }
        }
        leaf vad {
          type string;
          // NCS drop default statement
        }
      }
      container outbound {
        container status-check {
          leaf pots {
            type string;
            // NCS drop default statement
          }
        }
      }
      container cor {
        container custom {
          presence "true";
          list name {
            // NCS patched for predictable order
            ordered-by user;
            key "name";
            leaf name {
              type string;
            }
          }
        }
      }
    }
    leaf config-register {
      type string;
    }
    container network-clock-participate {
      container wic {
        list wic-enabled {
          // NCS patched for predictable order
          ordered-by user;
          key "slot";
          leaf slot {
            type string;
          }
        }
        list wic-disabled {
          // NCS patched for predictable order
          ordered-by user;
          key "slot";
          leaf slot {
            type string;
          }
        }
      }
    }
    container mgcp {
      container fax {
        container t38 {
          leaf ecm {
            type empty;
          }
        }
      }
      container behavior {
        container g729-variants {
          leaf static-pt {
            type empty;
          }
        }
      }
      list profile {
        // NCS patched for predictable order
        ordered-by user;
        key "name";
        leaf name {
          type string;
        }
      }
    }
    container gatekeeper {
      leaf shutdown {
        type empty;
      }
    }
    container line {
      list console {
        // NCS patched for predictable order
        ordered-by user;
        key "first";
        // NCS drop max-elements statement
        leaf first {
          type string;
        }
        uses ncs_template_line-grouping;
      }
      list aux {
        // NCS patched for predictable order
        ordered-by user;
        key "first";
        // NCS drop max-elements statement
        leaf first {
          type string;
        }
        uses ncs_template_line-grouping;
      }
      container vty-single {
        list vty {
          // NCS patched for predictable order
          ordered-by user;
          key "first";
          leaf first {
            type string;
          }
          uses ncs_template_line-grouping;
        }
      }
      list vty {
        // NCS patched for predictable order
        ordered-by user;
        key "first last";
        leaf first {
          type string;
        }
        leaf last {
          type string;
        }
        uses ncs_template_line-grouping;
      }
      list number-single {
        // NCS patched for predictable order
        ordered-by user;
        key "first";
        leaf first {
          type string;
        }
        uses ncs_template_line-grouping;
      }
      list number {
        // NCS patched for predictable order
        ordered-by user;
        key "first last";
        leaf first {
          type string;
        }
        leaf last {
          type string;
        }
        uses ncs_template_line-grouping;
      }
    }
    container pnp {
      list profile {
        // NCS patched for predictable order
        ordered-by user;
        key "name";
        leaf name {
          type string;
        }
        container transport {
          leaf protocol {
            type string;
          }
          leaf over {
            // NCS drop when statement
            type string;
          }
          choice address-choice {
            leaf host {
              type string;
            }
            leaf ipv4 {
              type string;
            }
            leaf ipv6 {
              type string;
            }
          }
          leaf port {
            type string;
          }
          container source {
            uses ncs_template_interface-name-grouping;
          }
        }
        container reconnect {
          leaf seconds {
            type string;
          }
        }
      }
      leaf startup-vlan {
        type string;
      }
      leaf tag {
        type string;
      }
    }
    container onep {
      leaf start {
        type string;
      }
      container transport {
        container tipc {
          presence "true";
        }
      }
    }
    container logging {
      list discriminator {
        // NCS patched for predictable order
        ordered-by user;
        key "discr-name";
        leaf discr-name {
          type string;
        }
        container mnemonics {
          choice mnemonics-choice {
            leaf drops {
              type string;
            }
            leaf includes {
              type string;
            }
          }
        }
        container msg-body {
          choice mnemonics-choice {
            leaf drops {
              type string;
            }
            leaf includes {
              type string;
            }
          }
        }
      }
      container cmts {
        container ipc-cable {
          leaf log-level {
            type string;
          }
        }
        container sea {
          leaf syslog-level {
            type string;
          }
        }
      }
      leaf alarm {
        type string;
      }
      container buffered {
        leaf xxml {
          tailf:alt-name "xml";
          type empty;
        }
        leaf discriminator {
          type string;
        }
        leaf buffer-size {
          type string;
        }
        leaf severity-level {
          type string;
          // NCS drop default statement
        }
      }
      container console {
        leaf xxml {
          tailf:alt-name "xml";
          type empty;
        }
        leaf discriminator {
          type string;
        }
        leaf severity-level {
          type string;
          // NCS drop default statement
        }
      }
      container event {
        container link-status {
          leaf boot {
            type empty;
          }
          leaf global {
            type empty;
          }
          leaf default {
            type empty;
          }
        }
      }
      container esm {
        leaf config {
          type empty;
        }
      }
      leaf facility {
        type string;
      }
      container history {
        leaf size {
          type string;
        }
        leaf severity-level {
          type string;
        }
      }
      list hostname {
        // NCS patched for predictable order
        ordered-by user;
        key "host";
        leaf host {
          type string;
        }
      }
      list host {
        // NCS patched for predictable order
        ordered-by user;
        key "host";
        leaf host {
          type string;
        }
        leaf vrf {
          // NCS drop tailf-common:cli-diff-dependency statement
          // NCS drop tailf-common:cli-diff-dependency statement
          type string;
        }
        leaf discriminator {
          type string;
        }
      }
      container rate-limit {
        leaf console {
          type empty;
        }
        leaf all {
          type empty;
        }
        leaf rate {
          type string;
        }
      }
      container source-interface {
        uses ncs_template_interface-name-grouping;
        leaf vrf {
          type string;
        }
      }
      leaf trap {
        type string;
      }
    }
    container cpd {
      presence "true";
      leaf cr-id {
        type string;
      }
    }
    container nls {
      presence "true";
      leaf resp-timeout {
        type string;
      }
    }
    list flow-sampler-map {
      // NCS patched for predictable order
      ordered-by user;
      key "name";
      leaf name {
        type string;
      }
      container mode {
        container random {
          leaf one-out-of {
            type string;
          }
        }
      }
    }
    container frame-relay {
      leaf switching {
        type empty;
      }
    }
    container scheduler {
      container allocate {
        leaf interrupt-time {
          type string;
        }
        leaf process-time {
          type string;
        }
      }
      leaf isr-watchdog {
        type empty;
      }
    }
    container process {
      container cpu {
        container threshold {
          container type {
            container total {
              uses ncs_template_process-cpu-threshold-grouping;
            }
            container interrupt {
              uses ncs_template_process-cpu-threshold-grouping;
            }
            container process {
              uses ncs_template_process-cpu-threshold-grouping;
            }
          }
        }
      }
    }
    container ntp {
      // NCS drop tailf-common:cli-diff-dependency statement
      // NCS drop tailf-common:cli-diff-dependency statement
      leaf max-associations {
        type string;
      }
      leaf passive {
        type empty;
      }
      leaf logging {
        type empty;
      }
      container panic {
        leaf update {
          type empty;
        }
      }
      list authentication-key {
        // NCS patched for predictable order
        ordered-by user;
        key "number";
        leaf number {
          type string;
        }
        leaf md5 {
          type string;
        }
        leaf encryption-type {
          type string;
        }
      }
      leaf authenticate {
        type empty;
      }
      list trusted-key {
        // NCS patched for predictable order
        ordered-by user;
        key "key-number";
        leaf key-number {
          type string;
        }
        leaf hyphen {
          tailf:alt-name "-";
          type empty;
        }
        leaf end-key-number {
          type string;
        }
      }
      leaf orphan {
        type string;
      }
      leaf mindistance {
        type string;
      }
      leaf maxdistance {
        type string;
      }
      leaf broadcastdelay {
        type string;
      }
      container source {
        uses ncs_template_interface-name-grouping;
      }
      container access-group {
        container peer {
          leaf access-list {
            type string;
          }
          leaf kod {
            type empty;
          }
        }
        container query-only {
          leaf access-list {
            type string;
          }
          leaf kod {
            type empty;
          }
        }
        container serve {
          leaf access-list {
            type string;
          }
          leaf kod {
            type empty;
          }
        }
        container serve-only {
          leaf access-list {
            type string;
          }
          leaf kod {
            type empty;
          }
        }
      }
      container master {
        presence "true";
        leaf stratum {
          type string;
        }
      }
      container peer {
        uses ncs_template_ntp-peer-grouping;
        container ip {
          uses ncs_template_ntp-peer-grouping;
        }
        container ipv6 {
          uses ncs_template_ntp-peer-grouping;
        }
        list vrf {
          // NCS patched for predictable order
          ordered-by user;
          key "name";
          leaf name {
            type string;
          }
          uses ncs_template_ntp-peer-grouping;
        }
      }
      container server {
        uses ncs_template_ntp-peer-grouping;
        container ip {
          uses ncs_template_ntp-peer-grouping;
        }
        container ipv6 {
          uses ncs_template_ntp-peer-grouping;
        }
        list vrf {
          // NCS patched for predictable order
          ordered-by user;
          key "name";
          leaf name {
            type string;
          }
          uses ncs_template_ntp-peer-grouping;
        }
      }
      container allow {
        container mode {
          leaf private {
            type empty;
          }
        }
      }
      leaf update-calendar {
        type empty;
      }
    }
    container sntp {
      leaf logging {
        type empty;
      }
      list authentication-key {
        // NCS patched for predictable order
        ordered-by user;
        key "number";
        leaf number {
          type string;
        }
        leaf md5 {
          type string;
        }
        leaf encryption-type {
          type string;
        }
      }
      leaf authenticate {
        type empty;
      }
      list trusted-key {
        // NCS patched for predictable order
        ordered-by user;
        key "key-number";
        leaf key-number {
          type string;
        }
        leaf hyphen {
          tailf:alt-name "-";
          type empty;
        }
        leaf end-key-number {
          type string;
        }
      }
      container server {
        uses ncs_template_sntp-server-grouping;
        container ip {
          uses ncs_template_sntp-server-grouping;
        }
        container ipv6 {
          uses ncs_template_sntp-server-grouping;
        }
        list vrf {
          // NCS patched for predictable order
          ordered-by user;
          key "name";
          leaf name {
            type string;
          }
          uses ncs_template_sntp-server-grouping;
        }
      }
      container broadcast {
        leaf client {
          type empty;
        }
      }
      container multicast {
        container client {
          presence "true";
          leaf address {
            type string;
          }
        }
      }
      container source-interface {
        uses ncs_template_interface-name-grouping;
      }
    }
    container ptp {
      container clock {
        container ordinary {
          list domain {
            // NCS patched for predictable order
            ordered-by user;
            key "id";
            // NCS drop max-elements statement
            leaf id {
              type string;
            }
            leaf hybrid {
              type empty;
            }
            list clock-port {
              // NCS patched for predictable order
              ordered-by user;
              key "name mode";
              // NCS drop max-elements statement
              leaf name {
                type string;
              }
              leaf mode {
                type string;
              }
              container transport {
                leaf proto {
                  type string;
                }
                leaf unicast {
                  type empty;
                }
                leaf interface {
                  // NCS drop when statement
                  type string;
                }
                leaf negotiation {
                  type empty;
                }
              }
              container clock {
                leaf source {
                  type string;
                }
              }
            }
          }
        }
      }
    }
    container mac-address-table {
      container notification {
        leaf mac-move {
          type empty;
        }
      }
      container limit {
        list bdomain {
          // NCS patched for predictable order
          ordered-by user;
          key "id";
          leaf id {
            type string;
          }
          leaf maximum {
            type string;
          }
          leaf action {
            type string;
          }
          leaf flood {
            type empty;
          }
        }
      }
    }
    container no {
      container mac-address-table {
        container learning {
          list vlan {
            // NCS patched for predictable order
            ordered-by user;
            key "id";
            leaf id {
              type string;
            }
            leaf module {
              type string;
            }
          }
        }
      }
    }
    container privilege {
      container exec {
        list level {
          // NCS patched for predictable order
          ordered-by user;
          key "privilege";
          leaf privilege {
            type string;
          }
          list command-list {
            // NCS patched for predictable order
            ordered-by user;
            key "command";
            leaf command {
              type string;
            }
          }
        }
      }
    }
    container spanning-tree {
      container etherchannel {
        container guard {
          leaf misconfig {
            type empty;
          }
        }
      }
      container extend {
        leaf system-id {
          type empty;
        }
      }
      container loopguard {
        leaf default {
          type empty;
        }
      }
      container mst {
        list instance-range {
          // NCS patched for predictable order
          ordered-by user;
          key "id";
          leaf id {
            type string;
          }
          leaf priority {
            type string;
          }
        }
        container configuration {
          leaf name {
            type string;
          }
          list instance {
            // NCS patched for predictable order
            ordered-by user;
            key "id";
            leaf id {
              type string;
            }
            leaf-list vlan {
              // NCS patched for predictable order
              ordered-by user;
              type string;
            }
          }
        }
      }
      container optimize {
        container bpdu {
          leaf transmission {
            type string;
          }
        }
      }
      container portfast {
        leaf bdpu {
          type string;
        }
        leaf default {
          type empty;
        }
      }
      leaf mode {
        type string;
      }
      container vlans-max-age {
        list vlan {
          // NCS patched for predictable order
          ordered-by user;
          key "id";
          leaf id {
            type string;
          }
          leaf max-age {
            type string;
          }
        }
      }
      container vlans-forward-time {
        list vlan {
          // NCS patched for predictable order
          ordered-by user;
          key "id";
          leaf id {
            type string;
          }
          leaf forward-time {
            type string;
          }
        }
      }
      container vlans-hello-time {
        list vlan {
          // NCS patched for predictable order
          ordered-by user;
          key "id";
          leaf id {
            type string;
          }
          leaf hello-time {
            type string;
          }
        }
      }
      container vlans-priority {
        list vlan {
          // NCS patched for predictable order
          ordered-by user;
          key "id";
          leaf id {
            type string;
          }
          leaf priority {
            type string;
          }
        }
      }
      container vlans-root {
        list vlan {
          // NCS patched for predictable order
          ordered-by user;
          key "id";
          leaf id {
            type string;
          }
          container root {
            container primary {
              leaf diameter {
                type string;
              }
              leaf hello-time {
                type string;
              }
            }
            container secondary {
              leaf diameter {
                type string;
              }
              leaf hello-time {
                type string;
              }
            }
          }
        }
      }
    }
    container dot1x {
      container critical {
        leaf eapol {
          type empty;
        }
        container recovery {
          leaf delay {
            type string;
          }
        }
      }
      leaf system-auth-control {
        type empty;
      }
    }
    container power {
      leaf redundancy-mode {
        type string;
      }
    }
    container parameter-map {
      container type {
        list inspect {
          // NCS patched for predictable order
          ordered-by user;
          key "name";
          leaf name {
            type string;
          }
          leaf alert {
            type string;
          }
          leaf audit-trail {
            type string;
          }
          leaf dns-timeout {
            type string;
          }
          container icmp {
            leaf idle-time {
              type string;
            }
          }
          container max-incomplete {
            leaf high {
              type string;
            }
            leaf low {
              type string;
            }
          }
          container one-minute {
            leaf high {
              type string;
            }
            leaf low {
              type string;
            }
          }
          container sessions {
            leaf maximum {
              type string;
            }
          }
          container tcp {
            leaf finwait-time {
              type string;
            }
            leaf idle-time {
              type string;
            }
            container max-incomplete {
              leaf host {
                type string;
              }
            }
            leaf synwait-time {
              type string;
            }
          }
          container udp {
            leaf idle-time {
              type string;
            }
          }
        }
      }
    }
    container vpdn {
      leaf authen-before-forward {
        type empty;
      }
      leaf enable {
        type empty;
      }
      leaf-list search-order {
        // NCS patched for predictable order
        ordered-by user;
        type string;
      }
    }
    container bba-group {
      list pppoe {
        // NCS patched for predictable order
        ordered-by user;
        key "id";
        leaf id {
          type string;
        }
        container vendor-tag {
          container circuit-id {
            leaf service {
              type empty;
            }
          }
          container dsl-sync-rate {
            leaf service {
              type empty;
            }
          }
          container remote-id {
            leaf service {
              type empty;
            }
          }
          leaf strip {
            type empty;
          }
        }
        leaf virtual-template {
          type string;
        }
      }
    }
    container mac {
      container access-list {
        list extended {
          // NCS patched for predictable order
          ordered-by user;
          key "id";
          leaf id {
            type string;
          }
          container deny {
            container source {
              choice target-choice {
                leaf any {
                  type empty;
                }
                leaf host {
                  type string;
                }
              }
            }
            container dest {
              choice target-choice {
                leaf any {
                  type empty;
                }
                leaf host {
                  type string;
                }
              }
            }
          }
          container permit {
            container source {
              choice target-choice {
                leaf any {
                  type empty;
                }
                leaf host {
                  type string;
                }
              }
            }
            container dest {
              choice target-choice {
                leaf any {
                  type empty;
                }
                leaf host {
                  type string;
                }
              }
            }
          }
        }
      }
    }
    container tacacs-server {
      list host {
        // NCS patched for predictable order
        ordered-by user;
        key "name";
        leaf name {
          type string;
        }
        leaf port {
          type string;
        }
        leaf timeout {
          type string;
        }
        container key {
          leaf encryption {
            type string;
          }
          leaf key {
            type string;
          }
        }
      }
      leaf timeout {
        type string;
        // NCS drop default statement
      }
      container directed-request {
        presence "true";
        leaf restricted {
          type empty;
        }
        leaf no-truncate {
          type empty;
        }
      }
      container key {
        leaf encryption {
          type string;
        }
        leaf key {
          type string;
        }
      }
    }
    container udld {
      leaf aggressive {
        type empty;
      }
      container message {
        leaf time {
          type string;
        }
      }
    }
    container vtp {
      leaf file {
        type string;
      }
      leaf interface {
        type string;
      }
      leaf password {
        type string;
      }
      leaf pruning {
        type empty;
      }
      leaf version {
        type string;
      }
      leaf domain {
        type string;
      }
      leaf mode {
        type string;
      }
    }
    container rep {
      container admin {
        list vlan {
          // NCS patched for predictable order
          ordered-by user;
          key "name";
          leaf name {
            type string;
          }
        }
      }
    }
    container xconnect {
      container logging {
        container pseudowire {
          leaf status {
            type empty;
          }
        }
        leaf redundancy {
          type empty;
        }
      }
    }
    container fabric {
      container switching-mode {
        container allow {
          choice allow-choice {
            leaf bus-mode {
              type empty;
            }
            container truncated {
              presence "true";
              leaf threshold {
                type string;
              }
            }
          }
        }
        container force {
          leaf bus-mode {
            type empty;
          }
        }
      }
    }
    container port-channel {
      leaf load-balance {
        type string;
      }
      leaf load-balance-hash-algo {
        type string;
      }
    }
    container l2 {
      list vfi {
        // NCS patched for predictable order
        ordered-by user;
        key "name";
        leaf name {
          type string;
        }
        leaf point-to-point {
          type empty;
        }
        leaf manual {
          type empty;
        }
        container vpn {
          leaf id {
            type string;
          }
        }
        leaf bridge-domain {
          type string;
        }
        leaf mtu {
          type string;
        }
        list neighbor {
          // NCS patched for predictable order
          ordered-by user;
          key "id";
          leaf id {
            type string;
          }
          leaf vcid {
            type string;
          }
          leaf encapsulation {
            type string;
          }
          leaf pw-class {
            type string;
          }
          leaf no-split-horizon {
            type empty;
          }
        }
      }
    }
    container l2protocol-tunnel {
      leaf cos {
        type string;
      }
      container global {
        leaf drop-threshold {
          type string;
        }
      }
    }
    container l2vpn {
      presence "true";
    }
    container l2vpn-vfi {
      container l2vpn {
        container vfi {
          list context {
            // NCS patched for predictable order
            ordered-by user;
            key "name";
            leaf name {
              type string;
            }
            container vpn {
              leaf id {
                type string;
              }
            }
            container autodiscovery {
              container bgp {
                container signaling {
                  container bgp {
                    container ve {
                      leaf id {
                        type string;
                      }
                    }
                    container route-target {
                      uses ncs_template_vrf-route-target-grouping;
                    }
                  }
                }
              }
            }
            container member {
              list pseudowire {
                // NCS patched for predictable order
                ordered-by user;
                key "name";
                leaf name {
                  type string;
                }
              }
            }
          }
        }
      }
    }
    container l2vpn-xconnect {
      container l2vpn {
        container xconnect {
          list context {
            // NCS patched for predictable order
            ordered-by user;
            key "name";
            leaf name {
              type string;
            }
            container member {
              list member-list {
                // NCS patched for predictable order
                ordered-by user;
                key "name";
                leaf name {
                  type string;
                }
                leaf service-instance {
                  type string;
                }
                leaf group {
                  type string;
                }
                leaf priority {
                  type string;
                }
              }
              list pseudowire {
                // NCS patched for predictable order
                ordered-by user;
                key "name";
                leaf name {
                  type string;
                }
              }
              list address-list {
                // NCS patched for predictable order
                ordered-by user;
                key "name";
                leaf name {
                  type string;
                }
                leaf vcid {
                  type string;
                }
                leaf encapsulation {
                  type string;
                }
                leaf group {
                  type string;
                }
                leaf priority {
                  type string;
                }
              }
            }
            container redundancy {
              leaf predictive {
                type string;
              }
              list delay {
                // NCS patched for predictable order
                ordered-by user;
                key "group";
                leaf group {
                  type string;
                }
                leaf enable-delay {
                  type string;
                }
                leaf disable-delay {
                  type string;
                }
              }
            }
          }
        }
      }
    }
    container system {
      container env {
        container temperature {
          container threshold {
            leaf yellow {
              type string;
            }
          }
        }
      }
      container mtu {
        leaf size {
          type string;
        }
        leaf jumbo {
          type string;
        }
        leaf routing {
          type string;
        }
      }
    }
    container diagnostic {
      container bootup {
        leaf level {
          type string;
        }
      }
      container cns {
        leaf publish {
          type string;
        }
        leaf subscribe {
          type string;
        }
      }
    }
    container errdisable {
      container detect {
        container cause {
          leaf all {
            type empty;
          }
          leaf arp-inspection {
            type empty;
          }
          leaf bpduguard {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf loopback {
            type empty;
          }
          leaf mlacp-minlink {
            type empty;
          }
          leaf pagp-flap {
            type empty;
          }
          leaf pppoe-ia-rate-limit {
            type empty;
          }
          leaf security-violation {
            type empty;
          }
          leaf sfp-config-mismatch {
            type empty;
          }
          leaf small-frame {
            type empty;
          }
        }
      }
      container flap-setting {
        container cause {
          container dtp-flap {
            leaf max-flaps {
              type string;
            }
            leaf time {
              type string;
            }
          }
          container link-flap {
            leaf max-flaps {
              type string;
            }
            leaf time {
              type string;
            }
          }
          container pagp-flap {
            leaf max-flaps {
              type string;
            }
            leaf time {
              type string;
            }
          }
        }
      }
      container recovery {
        container cause {
          leaf all {
            type empty;
          }
          leaf arp-inspection {
            type empty;
          }
          leaf bpduguard {
            type empty;
          }
          leaf channel-misconfig {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf link-monitor-failure {
            type empty;
          }
          leaf loopback {
            type empty;
          }
          leaf mac-limit {
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            type empty;
          }
          leaf port-mode-failure {
            type empty;
          }
          leaf pppoe-ia-rate-limit {
            type empty;
          }
          leaf psp {
            type empty;
          }
          leaf psecure-violation {
            type empty;
          }
          leaf security-violation {
            type empty;
          }
          leaf sfp-config-mismatch {
            type empty;
          }
          leaf small-frame {
            type empty;
          }
          leaf storm-control {
            type empty;
          }
          leaf udld {
            type empty;
          }
          leaf unicast-flood {
            type empty;
          }
          leaf vmps {
            type empty;
          }
        }
        leaf interval {
          type string;
        }
      }
    }
    container monitor {
      list session {
        // NCS patched for predictable order
        ordered-by user;
        key "id";
        leaf id {
          type string;
        }
        container destination {
          leaf interface {
            type string;
          }
          leaf encapsulation {
            type string;
          }
          leaf ingress {
            type empty;
          }
          leaf ingress-encap {
            // NCS drop when statement
            type string;
          }
          leaf vlan {
            // NCS drop when statement
            type string;
          }
        }
        container source {
          container interface {
            uses ncs_template_interface-name-grouping;
          }
          container vlan {
            leaf vlan {
              type string;
            }
            leaf direction {
              type string;
            }
          }
        }
      }
      container event-trace {
        list event-trace-list {
          // NCS patched for predictable order
          ordered-by user;
          key "name";
          leaf name {
            type string;
          }
        }
      }
    }
    list tftp-server {
      // NCS patched for predictable order
      ordered-by user;
      key "name";
      leaf name {
        type string;
      }
      leaf alias {
        type string;
      }
      leaf access-list {
        type string;
      }
    }
    container radius-server {
      list host {
        // NCS patched for predictable order
        ordered-by user;
        key "id";
        leaf id {
          type string;
        }
        leaf acct-port {
          type string;
        }
        leaf auth-port {
          type string;
        }
        leaf key {
          type string;
        }
      }
      leaf retransmit {
        type string;
        // NCS drop default statement
      }
      leaf timeout {
        type string;
        // NCS drop default statement
      }
      container key {
        uses ncs_template_password-07-grouping;
      }
    }
    container radius {
      list filter {
        // NCS patched for predictable order
        ordered-by user;
        key "id";
        leaf id {
          type string;
        }
        leaf match {
          type string;
        }
      }
      list server {
        // NCS patched for predictable order
        ordered-by user;
        key "id";
        leaf id {
          type string;
        }
        container address {
          container ipv4 {
            leaf host {
              type string;
            }
            leaf auth-port {
              type string;
            }
            leaf acct-port {
              type string;
            }
          }
        }
        container backoff {
          container exponential {
            presence "true";
            leaf max-delay {
              type string;
            }
            leaf backoff-retry {
              type string;
            }
          }
        }
        container key {
          leaf encryption {
            type string;
          }
          leaf key {
            type string;
          }
        }
      }
    }
    container zone {
      list security {
        // NCS patched for predictable order
        ordered-by user;
        key "id";
        leaf id {
          type string;
        }
        leaf description {
          type string;
        }
      }
    }
    container zone-pair {
      list security {
        // NCS patched for predictable order
        ordered-by user;
        key "id";
        leaf id {
          type string;
        }
        leaf source {
          type string;
        }
        leaf destination {
          type string;
        }
        leaf description {
          type string;
        }
        container service-policy {
          container type {
            leaf inspect {
              type string;
            }
          }
        }
      }
    }
    list alarm-contact {
      // NCS patched for predictable order
      ordered-by user;
      key "name";
      leaf name {
        type string;
      }
      leaf description {
        type string;
      }
      leaf severity {
        type string;
      }
      leaf trigger {
        type string;
      }
    }
    container mpls {
      container atm {
        leaf disable-headend-vc {
          type empty;
        }
      }
      leaf cos-map {
        type string;
      }
      container conf {
        leaf ip {
          type string;
          // NCS drop default statement
        }
      }
      container ip {
        leaf default-route {
          type empty;
        }
        choice propagate-ttl-choice {
          container propagate-ttl-conf {
            leaf propagate-ttl {
              type string;
              // NCS drop default statement
            }
          }
          container propagate-ttl {
            leaf forwarded {
              type string;
              // NCS drop default statement
            }
          }
        }
        container ttl-expiration {
          leaf pop {
            type string;
          }
        }
      }
      container label {
        container atm {
          leaf disable-headend-vc {
            type empty;
          }
        }
        leaf protocol {
          type string;
        }
        container range {
          leaf min {
            type string;
          }
          leaf max {
            type string;
          }
        }
      }
      container ldp {
        leaf advertise-labels {
          type string;
          // NCS drop default statement
        }
        container advertise-labels-conf {
          container advertise-labels {
            container for {
              leaf from {
                type string;
              }
              leaf to {
                type string;
              }
            }
            container interface {
              uses ncs_template_interface-name-grouping;
            }
            leaf oldstyle {
              type empty;
            }
          }
        }
        container atm {
          leaf control-mode {
            type string;
          }
          leaf vc-merge {
            type string;
            // NCS drop default statement
          }
        }
        container backoff {
          leaf initial {
            type string;
          }
          leaf max {
            type string;
          }
        }
        container discovery {
          container hello {
            leaf holdtime {
              type string;
            }
            leaf interval {
              type string;
            }
          }
          container targeted-hello {
            container accept {
              presence "Accept targeted hellos";
              leaf from {
                type string;
              }
            }
            leaf holdtime {
              type string;
            }
            leaf interval {
              type string;
            }
          }
        }
        container explicit-null {
          presence "true";
          leaf for {
            type string;
          }
          leaf to {
            type string;
          }
        }
        leaf loop-detection {
          type empty;
        }
        container graceful-restart {
          presence "Configure Graceful Restart timers";
          container timers {
            leaf forwarding-holding {
              type string;
            }
            leaf max-recovery {
              type string;
            }
            leaf neighbor-liveness {
              type string;
            }
          }
        }
        leaf holdtime {
          type string;
        }
        container logging {
          leaf neighbor-changes {
            type empty;
          }
        }
        leaf maxhops {
          type string;
        }
        list neighbor {
          // NCS patched for predictable order
          ordered-by user;
          key "address";
          leaf address {
            type string;
          }
          leaf implicit-withdraw {
            type empty;
          }
          container lables {
            leaf accept {
              type string;
            }
          }
          container password {
            leaf enctype {
              type string;
              // NCS drop default statement
            }
            leaf text {
              type string;
            }
          }
          container targeted {
            presence "Establish targeted session";
            leaf protocol {
              type string;
            }
          }
        }
        container request-labels {
          leaf for {
            type string;
          }
        }
        container router-id {
          leaf interface {
            type string;
          }
          leaf force {
            type empty;
          }
        }
        container session {
          container protection {
            presence "true";
            leaf duration {
              type string;
            }
          }
        }
        container label {
          container allocate {
            container global {
              presence "true";
              choice global-choice {
                leaf host-routes {
                  type empty;
                }
                leaf prefix-list {
                  type string;
                }
              }
            }
          }
        }
      }
      container prefix-map {
        leaf nr {
          type string;
        }
        leaf access-list {
          type string;
        }
        leaf cos-map {
          type string;
        }
      }
      container traffic-eng {
        container auto-bw {
          container timers {
            presence "Enable auto-bw Timers Collection and Application";
            leaf frequency {
              type string;
            }
          }
        }
        container link-management {
          container timers {
            leaf bandwidth-hold {
              type string;
            }
            leaf periodic-flooding {
              type string;
            }
          }
        }
        container logging {
          container lsp {
            container path-errors {
              presence "Log LSP Path Error traps";
              leaf access-list {
                type string;
              }
            }
            container preemption {
              presence "Log LSP Preemption traps";
              leaf access-list {
                type string;
              }
            }
            container reservation-errors {
              presence "Log LSP Reservation Error traps";
              leaf access-list {
                type string;
              }
            }
            container setups {
              presence "Log LSP Establishment Traps";
              leaf access-list {
                type string;
              }
            }
            container teardowns {
              presence "Log LSP Teardown Traps";
              leaf access-list {
                type string;
              }
            }
          }
          container tunnel {
            container lsp-selection {
              presence "Log Tunnel LSP Selection traps";
              leaf access-list {
                type string;
              }
            }
            container path {
              container change {
                presence "Log Tunnel Path change traps";
                leaf access-list {
                  type string;
                }
              }
            }
          }
        }
        container path-selection {
          leaf metric {
            type string;
          }
          container overload {
            container allow {
              leaf head {
                type empty;
              }
              leaf middle {
                type empty;
              }
              leaf tail {
                type empty;
              }
            }
          }
        }
        container reoptimize {
          container events {
            leaf link-up {
              type empty;
            }
          }
          container timers {
            container delay {
              leaf cleanup {
                type string;
              }
              leaf installation {
                type string;
              }
            }
            leaf frequency {
              type string;
            }
          }
        }
        container signalling {
          container advertise {
            container implicit-null {
              presence "Use MPLS encoding for Implicit-Null Label in signalling messages";
              leaf nr {
                type string;
              }
            }
          }
          container forwarding {
            leaf sync {
              type empty;
            }
          }
          container restart {
            container neighbors {
              presence "Identify signalling restart capable neighbors";
              leaf nr {
                type string;
              }
            }
          }
        }
        container topology {
          container holddown {
            leaf sigerr {
              type string;
            }
          }
        }
        leaf tunnels {
          type empty;
        }
      }
    }
    container l3vpn {
      container encapsulation {
        list ip {
          // NCS patched for predictable order
          ordered-by user;
          key "name";
          leaf name {
            type string;
          }
          container transport {
            container ipv4 {
              presence "true";
              container source {
                // NCS drop tailf-common:cli-diff-dependency statement
                uses ncs_template_interface-name-grouping;
              }
            }
          }
        }
      }
    }
    container router {
      container mobile {
        // NCS drop tailf-common:cli-diff-dependency statement
        presence "true";
      }
      list bgp {
        // NCS patched for predictable order
        ordered-by user;
        // NCS drop tailf-common:cli-diff-dependency statement
        // NCS drop tailf-common:cli-diff-dependency statement
        // NCS drop tailf-common:cli-diff-dependency statement
        key "as-no";
        // NCS drop max-elements statement
        leaf as-no {
          type string;
        }
        uses ncs_template_router-bgp-af-grouping;
        uses ncs_template_router-bgp-grouping;
        container template {
          list peer-policy {
            // NCS patched for predictable order
            ordered-by user;
            key "name";
            leaf name {
              type string;
            }
            uses ncs_template_router-bgp-peer-policy-grouping;
          }
          list peer-session {
            // NCS patched for predictable order
            ordered-by user;
            key "name";
            leaf name {
              type string;
            }
            uses ncs_template_router-bgp-peer-session-grouping;
          }
        }
        container address-family {
          list ipv4 {
            // NCS patched for predictable order
            ordered-by user;
            key "af";
            leaf af {
              type string;
            }
            uses ncs_template_router-bgp-af-grouping;
          }
          list ipv6 {
            // NCS patched for predictable order
            ordered-by user;
            key "af";
            leaf af {
              type string;
            }
            uses ncs_template_router-bgp-af-grouping;
          }
          container with-vrf {
            list ipv4 {
              // NCS patched for predictable order
              ordered-by user;
              key "af";
              leaf af {
                type string;
              }
              list vrf {
                // NCS patched for predictable order
                ordered-by user;
                // NCS drop tailf-common:cli-diff-dependency statement
                // NCS drop tailf-common:cli-diff-dependency statement
                key "name";
                leaf name {
                  type string;
                }
                uses ncs_template_router-bgp-af-grouping;
              }
            }
          }
          container ipv6-with-vrf {
            list ipv6 {
              // NCS patched for predictable order
              ordered-by user;
              key "af";
              leaf af {
                type string;
              }
              list vrf {
                // NCS patched for predictable order
                ordered-by user;
                // NCS drop tailf-common:cli-diff-dependency statement
                key "name";
                leaf name {
                  type string;
                }
                uses ncs_template_router-bgp-af-grouping;
              }
              uses ncs_template_router-bgp-af-grouping;
            }
          }
          list vpnv4 {
            // NCS patched for predictable order
            ordered-by user;
            key "af";
            leaf af {
              type string;
            }
            uses ncs_template_router-bgp-af-grouping;
          }
          list vpnv6 {
            // NCS patched for predictable order
            ordered-by user;
            key "af";
            leaf af {
              type string;
            }
            uses ncs_template_router-bgp-af-grouping;
          }
          list l2vpn {
            // NCS patched for predictable order
            ordered-by user;
            key "af";
            leaf af {
              type string;
            }
            uses ncs_template_router-bgp-af-grouping;
          }
          list nsap {
            // NCS patched for predictable order
            ordered-by user;
            key "af";
            leaf af {
              type string;
            }
            uses ncs_template_router-bgp-af-grouping;
          }
          list rtfilter {
            // NCS patched for predictable order
            ordered-by user;
            key "af";
            leaf af {
              type string;
            }
            uses ncs_template_router-bgp-af-grouping;
          }
        }
      }
      list eigrp {
        // NCS patched for predictable order
        ordered-by user;
        // NCS drop tailf-common:cli-diff-dependency statement
        key "id";
        leaf id {
          type string;
        }
        list network {
          // NCS patched for predictable order
          ordered-by user;
          key "ip";
          leaf ip {
            type string;
          }
          leaf mask {
            type string;
          }
        }
        container redistribute {
          container connected {
            presence "true";
            uses ncs_template_eigrp-metric-route-map-grouping;
          }
          container bgp {
            leaf as-number {
              type string;
            }
            uses ncs_template_eigrp-metric-route-map-grouping;
          }
          list eigrp {
            // NCS patched for predictable order
            ordered-by user;
            key "as-number";
            leaf as-number {
              type string;
            }
            uses ncs_template_eigrp-metric-route-map-grouping;
          }
          container isis {
            presence "true";
            list isis-list {
              // NCS patched for predictable order
              ordered-by user;
              key "name";
              leaf name {
                type string;
              }
              leaf level {
                type string;
              }
              uses ncs_template_eigrp-metric-route-map-grouping;
            }
            leaf level {
              type string;
            }
            uses ncs_template_eigrp-metric-route-map-grouping;
          }
          container iso-igrp {
            presence "true";
            list iso-igrp-list {
              // NCS patched for predictable order
              ordered-by user;
              key "name";
              leaf name {
                type string;
              }
              uses ncs_template_eigrp-metric-route-map-grouping;
            }
            uses ncs_template_eigrp-metric-route-map-grouping;
          }
          container mobile {
            presence "true";
            uses ncs_template_eigrp-metric-route-map-grouping;
          }
          container odr {
            presence "true";
            uses ncs_template_eigrp-metric-route-map-grouping;
          }
          list ospf {
            // NCS patched for predictable order
            ordered-by user;
            key "id";
            leaf id {
              type string;
            }
            uses ncs_template_eigrp-metric-route-map-grouping;
            container match {
              uses ncs_template_redistribute-ospf-match-grouping;
              uses ncs_template_eigrp-metric-route-map-grouping;
            }
          }
          container static {
            presence "Static routes";
            uses ncs_template_eigrp-metric-route-map-grouping;
          }
          container rip {
            presence "true";
            uses ncs_template_eigrp-metric-route-map-grouping;
          }
        }
        leaf auto-summary {
          type empty;
        }
      }
      list ospfv3 {
        // NCS patched for predictable order
        ordered-by user;
        // NCS drop tailf-common:cli-diff-dependency statement
        key "id";
        leaf id {
          type string;
        }
        uses ncs_template_router-ospfv3-grouping;
        uses ncs_template_router-ospf-common-grouping;
        container address-family {
          container ipv4 {
            container unicast {
              uses ncs_template_router-ospfv3-grouping;
              uses ncs_template_router-ospf-common-grouping;
              uses ncs_template_router-ospf-common-af-grouping;
              uses ncs_template_router-ospfv3-af-grouping;
            }
          }
          container ipv6 {
            container unicast {
              uses ncs_template_router-ospfv3-grouping;
              uses ncs_template_router-ospf-common-grouping;
              uses ncs_template_router-ospf-common-af-grouping;
              uses ncs_template_router-ospfv3-af-grouping;
            }
          }
        }
      }
      list ospf {
        // NCS patched for predictable order
        ordered-by user;
        // NCS drop tailf-common:cli-diff-dependency statement
        key "id";
        leaf id {
          type string;
        }
        leaf vrf {
          // NCS drop tailf-common:cli-diff-dependency statement
          // NCS drop tailf-common:cli-diff-dependency statement
          type string;
        }
        uses ncs_template_router-ospf-common-grouping;
        uses ncs_template_router-ospf-common-af-grouping;
        uses ncs_template_router-ospf-grouping;
      }
      container isis {
        // NCS drop tailf-common:cli-diff-dependency statement
        presence "true";
        uses ncs_template_router-isis-grouping;
      }
      container isis-container {
        list isis {
          // NCS patched for predictable order
          ordered-by user;
          // NCS drop tailf-common:cli-diff-dependency statement
          key "area-tag";
          leaf area-tag {
            type string;
          }
          uses ncs_template_router-isis-grouping;
        }
      }
      container rip {
        uses ncs_template_router-rip-grouping;
        container address-family {
          container ipv4 {
            container unicast {
              // NCS drop tailf-common:cli-diff-dependency statement
              uses ncs_template_router-rip-grouping;
            }
            list vrf {
              // NCS patched for predictable order
              ordered-by user;
              // NCS drop tailf-common:cli-diff-dependency statement
              // NCS drop tailf-common:cli-diff-dependency statement
              // NCS drop tailf-common:cli-diff-dependency statement
              key "name";
              leaf name {
                type string;
              }
              uses ncs_template_router-rip-af-grouping;
            }
          }
        }
      }
      container lisp {
        presence "true";
        uses ncs_template_router-lisp-grouping;
      }
      container router-lisp {
        list lisp {
          // NCS patched for predictable order
          ordered-by user;
          key "id";
          leaf id {
            type string;
          }
          uses ncs_template_router-lisp-grouping;
        }
      }
    }
    container snmp {
      container ifmib {
        container ifindex {
          leaf persist {
            type empty;
          }
        }
        container ifalias {
          leaf long {
            type empty;
          }
        }
      }
      container mib {
        container bulkstat {
          list object-list {
            // NCS patched for predictable order
            ordered-by user;
            key "name";
            leaf name {
              type string;
            }
          }
        }
        leaf persist {
          type string;
        }
      }
    }
    container snmp-server {
      leaf chassis-id {
        type string;
      }
      list community {
        // NCS patched for predictable order
        ordered-by user;
        key "name";
        leaf name {
          type string;
        }
        leaf view {
          type string;
        }
        choice access-choice {
          leaf RO {
            type empty;
          }
          leaf RW {
            type empty;
          }
        }
        leaf ipv6 {
          type string;
        }
        leaf access-list-name {
          type string;
        }
      }
      leaf contact {
        type string;
      }
      list context {
        // NCS patched for predictable order
        ordered-by user;
        key "name";
        leaf name {
          type string;
        }
      }
      container drop {
        leaf vrf-traffic {
          type empty;
        }
      }
      container enable {
        choice enable-choice {
          leaf informs {
            type empty;
          }
          list traps {
            // NCS patched for predictable order
            ordered-by user;
            key "name";
            leaf name {
              type string;
            }
          }
        }
      }
      container engineID {
        leaf local {
          type string;
        }
        list remote {
          // NCS patched for predictable order
          ordered-by user;
          key "address";
          leaf address {
            type string;
          }
          leaf udp-port {
            type string;
          }
          leaf vrf {
            // NCS drop tailf-common:cli-diff-dependency statement
            // NCS drop tailf-common:cli-diff-dependency statement
            type string;
          }
          leaf engineid-string {
            type string;
          }
        }
      }
      list group {
        // NCS patched for predictable order
        ordered-by user;
        key "id";
        leaf id {
          type string;
        }
        choice security-model {
          container v1;
          container v2c;
          container v3 {
            leaf security-level {
              type string;
            }
            leaf context {
              type string;
            }
            leaf match {
              type string;
            }
            leaf read {
              type string;
            }
            leaf write {
              type string;
            }
            leaf notify {
              type string;
            }
            leaf access {
              type string;
            }
          }
        }
      }
      list host {
        // NCS patched for predictable order
        ordered-by user;
        key "ip-address";
        leaf ip-address {
          type string;
        }
        list vrf {
          // NCS patched for predictable order
          ordered-by user;
          // NCS drop tailf-common:cli-diff-dependency statement
          // NCS drop tailf-common:cli-diff-dependency statement
          key "name";
          leaf name {
            type string;
          }
          uses ncs_template_snmp-server-host-grouping;
        }
        uses ncs_template_snmp-server-host-grouping;
      }
      container ip {
        leaf dscp {
          type string;
        }
        leaf precedence {
          type string;
        }
      }
      container ifindex {
        leaf persist {
          type empty;
        }
      }
      leaf location {
        type string;
      }
      container manager {
        presence "true";
        leaf session-timeout {
          type string;
        }
      }
      leaf packetsize {
        type string;
      }
      leaf queue-length {
        type string;
      }
      container queue-limit {
        leaf notification-host {
          type string;
        }
      }
      container source-interface {
        container informs {
          uses ncs_template_interface-name-grouping;
        }
        container traps {
          uses ncs_template_interface-name-grouping;
        }
      }
      container trap {
        leaf timeout {
          type string;
        }
      }
      container trap-source {
        uses ncs_template_interface-name-grouping;
      }
      leaf trap-timeout {
        type string;
      }
      list view {
        // NCS patched for predictable order
        ordered-by user;
        key "name mib";
        leaf name {
          type string;
        }
        leaf mib {
          type string;
        }
        leaf inc-exl {
          type string;
        }
      }
    }
    container dot11 {
      leaf syslog {
        type empty;
      }
    }
    container ipc {
      container zone {
        container default {
          presence "true";
        }
      }
    }
    container cts {
      container logging {
        leaf verbose {
          type empty;
        }
      }
    }
    container license {
      container accept {
        container end {
          container user {
            leaf agreement {
              type empty;
            }
          }
        }
      }
      container udi {
        leaf pid {
          type string;
        }
        leaf sn {
          type string;
        }
      }
      list boot {
        // NCS patched for predictable order
        ordered-by user;
        key "line";
        leaf line {
          type string;
        }
      }
      container smart {
        leaf enable {
          type empty;
        }
      }
    }
    container trunk {
      list group {
        // NCS patched for predictable order
        ordered-by user;
        key "name";
        leaf name {
          type string;
        }
        container hunt-scheme {
          choice hunt-scheme-choice {
            container round-robin {
              presence "true";
            }
            leaf random {
              type empty;
            }
            leaf sequential {
              type empty;
            }
          }
        }
      }
    }
    list voice-card {
      // NCS patched for predictable order
      ordered-by user;
      key "slot";
      leaf slot {
        type string;
      }
      leaf dspfarm {
        type empty;
      }
    }
    container voice {
      container service {
        container voip {
          container sip {
            presence "true";
            container bind {
              container control {
                container source-interface {
                  uses ncs_template_interface-name-grouping;
                }
              }
              container media {
                container source-interface {
                  uses ncs_template_interface-name-grouping;
                }
              }
            }
          }
        }
      }
      container iec {
        leaf syslog {
          type empty;
        }
      }
      list translation-rule {
        // NCS patched for predictable order
        ordered-by user;
        key "tag";
        leaf tag {
          type string;
        }
        list rule {
          // NCS patched for predictable order
          ordered-by user;
          key "tag";
          leaf tag {
            type string;
          }
          leaf reject {
            type empty;
          }
          leaf pattern {
            type string;
          }
        }
      }
      list translation-profile {
        // NCS patched for predictable order
        ordered-by user;
        key "name";
        leaf name {
          type string;
        }
        container translate {
          list called {
            // NCS patched for predictable order
            ordered-by user;
            key "tag";
            leaf tag {
              type string;
            }
          }
        }
      }
    }
    container event {
      container manager {
        list environment {
          // NCS patched for predictable order
          ordered-by user;
          key "name";
          leaf name {
            type string;
          }
          leaf value {
            type string;
          }
        }
        container directory {
          container user {
            leaf policy {
              type string;
            }
          }
        }
        list applet {
          // NCS patched for predictable order
          ordered-by user;
          key "name";
          leaf name {
            type string;
          }
          leaf description {
            type string;
          }
          leaf authorization {
            type string;
          }
          leaf class {
            type string;
          }
          leaf trap {
            type empty;
          }
          container event {
            uses ncs_template_event-manager-applet-event-grouping;
            list tag {
              // NCS patched for predictable order
              ordered-by user;
              key "name";
              leaf name {
                type string;
              }
              uses ncs_template_event-manager-applet-event-grouping;
            }
          }
          list action {
            // NCS patched for predictable order
            ordered-by user;
            key "name";
            leaf name {
              type string;
            }
            leaf cmd {
              type string;
            }
          }
          container trigger;
        }
        list policy {
          // NCS patched for predictable order
          ordered-by user;
          key "name";
          leaf name {
            type string;
          }
          leaf type {
            type string;
          }
        }
      }
    }
    leaf disable-eadi {
      type empty;
    }
    container memory-size {
      leaf iomem {
        type string;
      }
    }
    container transceiver {
      container type {
        container all {
          container monitoring {
            presence "true";
            leaf interval {
              type string;
            }
          }
        }
      }
    }
    list alias {
      // NCS patched for predictable order
      ordered-by user;
      key "line";
      leaf line {
        type string;
      }
    }
  }
}
